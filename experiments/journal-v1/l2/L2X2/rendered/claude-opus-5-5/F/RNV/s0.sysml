package L2Model {
    item def AdviceOnConditionsItem { doc /* @S084 */ }
    item def AdviceOnForecastChangesItem { doc /* @S232 */ }
    item def AdviceOnForecastConditionsItem { doc /* @S522 */ }
    item def AuthorizedOperatingSignalsItem { doc /* @S201 */ }
    item def BackorderExceptionSlipItem { doc /* @S262 */ }
    item def BerthSlotConfirmationItem { doc /* @S473 */ }
    item def ChangeInDestinationOrTransferPlanItem { doc /* @S402 */ }
    item def ChangesToWorkProgressItem { doc /* @S096 */ }
    item def CrewCountCorrectionItem { doc /* @S573 */ }
    item def CurrentGenerationExportAndEquipmentStatusItem { doc /* @S540 */ }
    item def CurrentOperationalStatusItem { doc /* @S171 */ }
    item def DeferredTaskRationaleItem { doc /* @S430 */ }
    item def DiscrepancyAndTheImmediateControlActionsItem { doc /* @S578 */ }
    item def ElectricalPowerItem { doc /* @S199 */ }
    item def EnvironmentalInformationItem { doc /* @S067 */ }
    item def ExportLimitAdvisoryItem { doc /* @S541 */ }
    item def ExternalOperatingRequirementsItem { doc /* @S769 */ }
    item def FirmwareHashAttestationItem { doc /* @S593 */ }
    item def HarnessAuditCardItem { doc /* @S312 */ }
    item def IncompleteRequestsItem { doc /* @S162 */ }
    item def InputItem { doc /* @S076 */ }
    item def IsolationBoundarySketchItem { doc /* @S716 */ }
    item def LeadingEdgeTileImageItem { doc /* @S445 */ }
    item def MarineAndWeatherInformationItem { doc /* @S764 */ }
    item def MaterialChangesItem { doc /* @S626 */ }
    item def OperatingMeasurementsItem { doc /* @S294 */ }
    item def OperationalDataItem { doc /* @S767 */ }
    item def OperationalRestrictionsItem { doc /* @S947 */ }
    item def PitchDeviationNoticeItem { doc /* @S159 */ }
    item def PositionQualityFlagItem { doc /* @S225 */ }
    item def PowerItem { doc /* @S180 */ }
    item def RecoveryBasketLoadSheetItem { doc /* @S646 */ }
    item def RelayStatusAndInterfaceMeasurementsItem { doc /* @S211 */ }
    item def ResultingPlanItem { doc /* @S269 */ }
    item def SessionRevocationReceiptItem { doc /* @S357 */ }
    item def SharedViewOfVesselAssignmentsPlannedMovementsAndDispatchStatusItem { doc /* @S081 */ }
    item def SquallWindowBulletinItem { doc /* @S213 */ }
    item def StartTestTraceItem { doc /* @S532 */ }
    item def SupervisoryDataItem { doc /* @S052 */ }
    item def SupplyAlarmsAndGeneratorStatusItem { doc /* @S192 */ }
    item def SwitchingWindowAcknowledgmentItem { doc /* @S752 */ }
    item def TimeStampedObservationsItem { doc /* @S295 */ }
    item def TransferManifestAddendumItem { doc /* @S278 */ }
    item def TransformerTapSnapshotItem { doc /* @S374 */ }
    item def TurbineStatusAndControlAvailabilityItem { doc /* @S133 */ }
    item def UnexplainedAbsenceOrOverdueCheckInItem { doc /* @S412 */ }
    item def UnresolvedDiscrepancyItem { doc /* @S583 */ }
    item def UnresolvedPersonnelOrAccessConcernsItem { doc /* @S809 */ }
    item def UrgentConcernsItem { doc /* @S419 */ }
    item def VisibilityConfidenceNoteItem { doc /* @S669 */ }
    item def WaveBurstRecordItem { doc /* @S323 */ }
    part def AffectedTeams { doc /* @S269 */ }
    part def AuthorizedShorePersonnel { doc /* @S133 */ }
    part def AutomaticControls { doc /* @S177 */ }
    part def BladeInspectionDrone { doc /* @S142,S313,S314,S445 */ }
    part def BladeSpecialist { doc /* @S143,S315,S445 */ }
    part def ControlEngineer { doc /* @S063,S135,S193,S310,S544 */ }
    part def ConverterCabinet { doc /* @S005,S131,S294 */ }
    part def CrewTransferVessel { doc /* @S087,S215,S312 */ }
    part def CybersecurityAnalyst { doc /* @S117,S419,S428,S593 */ }
    part def CybersecurityGateway { doc /* @S111,S287,S357,S416 */ }
    part def DutyPlanner { doc /* @S065,S076,S096,S126,S153,S164,S224,S247,S260,S269,S278,S319,S340,S519,S522,S583,S669,S764,S947 */ }
    part def EastServiceLift { doc /* @S859 */ }
    part def ElectricalTechnician { doc /* @S185,S331,S650,S716 */ }
    part def EmergencyDistributionBus { doc /* @S180 */ }
    part def EmergencyGenerator { doc /* @S180,S353,S532 */ }
    part def ExportCableMonitor { doc /* @S006 */ }
    part def FarmMonitoringEnvironment { doc /* @S211 */ }
    part def FieldSupervisor { doc /* @S076,S096,S167,S253,S412,S430,S809 */ }
    part def FireDetectionPanel { doc /* @S786 */ }
    part def FleetDispatchConsole { doc /* @S081,S203,S225,S260,S370,S947 */ }
    part def GridConnectionPoint { doc /* @S199 */ }
    part def GridDispatcher { doc /* @S202,S367,S541,S769 */ }
    part def GridInterfaceRelay { doc /* @S190,S201,S372,S373,S541,S769,S942 */ }
    part def HSEOfficer { doc /* @S095,S157,S237,S312 */ }
    part def MainTransformer { doc /* @S006,S038 */ }
    part def MaintenancePlanningEngine { doc /* @S076,S188,S195,S213,S246,S285,S308,S430 */ }
    part def MarineActivity { doc /* @S086 */ }
    part def MarineCoordinator { doc /* @S077,S081,S082,S084,S160,S223,S232,S245,S290,S412,S473,S576,S578,S583,S764 */ }
    part def MetoceanBuoy { doc /* @S102,S194,S231,S323 */ }
    part def NacelleConditionMonitor { doc /* @S005,S132,S294 */ }
    part def NorthAccessScanner { doc /* @S235,S394,S810,S831 */ }
    part def OffshoreAssets { doc /* @S052 */ }
    part def OffshoreSubstation { doc /* @S003,S037,S038,S189,S267,S361,S374,S752 */ }
    part def OffshoreWindFarm { doc /* @S003,S006,S199,S205 */ }
    part def OnDutyOperationsLead { doc /* @S419 */ }
    part def OnboardLogger { doc /* @S104 */ }
    part def OperationalPlanning { doc /* @S067 */ }
    part def OperationsTeam { doc /* @S540 */ }
    part def PermitReviewers { doc /* @S171 */ }
    part def Personnel { doc /* @S402,S847 */ }
    part def PersonnelTrackingConsole { doc /* @S234,S573 */ }
    part def PitchSystem { doc /* @S005,S130,S294,S546,S790 */ }
    part def PortAgent { doc /* @S240,S324,S473 */ }
    part def RemoteAdministrativeFunctions { doc /* @S118 */ }
    part def Requester { doc /* @S162 */ }
    part def RescueCoordinator { doc /* @S244,S614,S626,S646 */ }
    part def RotorBrakeUnit { doc /* @S005,S791 */ }
    part def SCADAEngineer { doc /* @S062,S593,S954 */ }
    part def SCADAGateway { doc /* @S006,S133,S159,S171,S192,S211,S212,S295,S357,S417,S540,S767 */ }
    part def ServiceOperationsVessel { doc /* @S461,S646 */ }
    part def ShoreBasedOperations { doc /* @S052 */ }
    part def ShoreControlRoom { doc /* @S192,S214,S295,S303,S374,S531,S578,S613,S752,S767,S809,S937 */ }
    part def SouthAccessScanner { doc /* @S236,S395,S843 */ }
    part def StationServiceTransformers { doc /* @S173 */ }
    part def Storekeeper { doc /* @S092,S242,S262 */ }
    part def SubstationOperator { doc /* @S216,S326,S532,S559 */ }
    part def System { doc /* @S015,S183 */ }
    part def TransmissionSystem { doc /* @S201 */ }
    part def Turbine { doc /* @S005,S328 */ }
    part def TurbineController { doc /* @S005,S060,S061,S127,S129,S159,S191,S294,S377,S545,S789,S937 */ }
    part def TurbineSensorBus { doc /* @S005,S251,S294 */ }
    part def Turbines { doc /* @S003 */ }
    part def VesselAISReceiver { doc /* @S105,S139,S140,S225,S288,S401 */ }
    part def VesselMaster { doc /* @S085,S161,S226,S278,S390,S402,S573 */ }
    part def WarehouseSystem { doc /* @S091,S163,S241,S262 */ }
    part def WeatherAnalyst { doc /* @S084,S232,S323,S472,S522,S626,S669 */ }
    part def WeatherService { doc /* @S067,S083,S128,S213,S230 */ }
    part def WestServiceLift { doc /* @S884,S891,S893,S894 */ }
    part def WorkPermitPortal { doc /* @S155,S162,S169,S321,S492,S716 */ }
    part system {
        part affectedTeams : AffectedTeams;
        part authorizedShorePersonnel : AuthorizedShorePersonnel;
        part automaticControls : AutomaticControls {
            perform action a0 { doc /* initiate the Emergency Generator start sequence @S177 */ }
        }
        part bladeInspectionDrone : BladeInspectionDrone {
            perform action a0 { doc /* captures close-range visual observations of accessible blade surfaces @S142 */ }
            perform action a1 { doc /* produces the Leading Edge Tile Image @S313 */ }
        }
        part bladeSpecialist : BladeSpecialist {
            perform action a0 { doc /* plans inspection passes @S143 */ }
        }
        part controlEngineer : ControlEngineer {
            perform action a0 { doc /* assess equipment status and coordinate response @S063 */ }
            perform action a1 { doc /* reviews alarms and operating conditions @S135 */ }
            perform action a2 { doc /* issuing a remote command @S135 */ }
            perform action a3 { doc /* reviews persistent alarms @S193 */ }
            perform action a4 { doc /* coordinates electrical support with the Substation Operator @S193 */ }
            perform action a5 { doc /* requests an on-site inspection @S310 */ }
            perform action a6 { doc /* reduces active power in controlled steps @S544 */ }
        }
        part converterCabinet : ConverterCabinet {
            perform action a0 { doc /* manages electrical conversion @S131 */ }
        }
        part crewTransferVessel : CrewTransferVessel {
            perform action a0 { doc /* transports authorized personnel and routine tools between shore and offshore work locations @S087 */ }
        }
        part cybersecurityAnalyst : CybersecurityAnalyst {
            perform action a0 { doc /* monitors gateway events @S117 */ }
            perform action a1 { doc /* produces the Firmware Hash Attestation @S428 */ }
        }
        part cybersecurityGateway : CybersecurityGateway {
            perform action a0 { doc /* establishes a controlled boundary between authorized shore-side services and offshore operational networks @S111 */ }
            perform action a1 { doc /* blocks a route change @S287 */ }
            perform action a2 { doc /* monitors traffic between operational networks and approved external connections @S416 */ }
        }
        part dutyPlanner : DutyPlanner {
            perform action a0 { doc /* prepare and review maintenance activities @S065 */ }
            perform action a1 { doc /* develops daily work priorities @S076 */ }
            perform action a2 { doc /* prepares the Transfer Manifest Addendum @S126 */ }
            perform action a3 { doc /* reviews the request for completeness @S153 */ }
            perform action a4 { doc /* assigns it to the appropriate planning queue @S153 */ }
            perform action a5 { doc /* resolves outstanding supply and scheduling issues @S164 */ }
            perform action a6 { doc /* submitting the request for authorization @S164 */ }
            perform action a7 { doc /* updates work priorities @S224 */ }
            perform action a8 { doc /* reviews the ranked queue @S247 */ }
            perform action a9 { doc /* confirms the operating priority @S260 */ }
            perform action a10 { doc /* submits a defined task scope, work location, crew, and requested operating window for review @S319 */ }
            perform action a11 { doc /* closes the work authorization @S340 */ }
            perform action a12 { doc /* reassess the sequence and obtain revised authorization @S519 */ }
        }
        part eastServiceLift : EastServiceLift {
            perform action a0 { doc /* runs a door-interlock and overload check @S859 */ }
        }
        part electricalTechnician : ElectricalTechnician {
            perform action a0 { doc /* verifies protective device settings and transfer interlocks @S185 */ }
            perform action a1 { doc /* tests for absence of voltage @S331 */ }
            perform action a2 { doc /* isolates and protects recovered electrical equipment @S650 */ }
        }
        part emergencyDistributionBus : EmergencyDistributionBus;
        part emergencyGenerator : EmergencyGenerator {
            perform action a0 { doc /* produces the Start Test Trace @S353 */ }
        }
        part exportCableMonitor : ExportCableMonitor;
        part farmMonitoringEnvironment : FarmMonitoringEnvironment;
        part fieldSupervisor : FieldSupervisor {
            perform action a0 { doc /* coordinates task execution offshore @S096 */ }
            perform action a1 { doc /* verifies that the approved conditions remain valid @S167 */ }
            perform action a2 { doc /* checks reported faults against available evidence @S253 */ }
        }
        part fireDetectionPanel : FireDetectionPanel {
            perform action a0 { doc /* supervises detection circuits and annunciates alarms @S786 */ }
        }
        part fleetDispatchConsole : FleetDispatchConsole {
            perform action a0 { doc /* allocates requested farm output among available generating units @S203 */ }
            perform action a1 { doc /* assigns vessel and crew resources to approved work packages @S260 */ }
            perform action a2 { doc /* compares the requested output with available turbine capability @S370 */ }
        }
        part gridConnectionPoint : GridConnectionPoint;
        part gridDispatcher : GridDispatcher {
            perform action a0 { doc /* sets external dispatch requirements @S202 */ }
        }
        part gridInterfaceRelay : GridInterfaceRelay {
            perform action a0 { doc /* produces an Export Limit Advisory @S372 */ }
            perform action a1 { doc /* applies the accepted export ceiling to control outputs @S373 */ }
            perform action a2 { doc /* applies the configured response to a Grid Constraint @S942 */ }
        }
        part hSEOfficer : HSEOfficer {
            perform action a0 { doc /* verifies that work arrangements account for applicable safety controls @S095 */ }
            perform action a1 { doc /* reviews the proposed controls @S157 */ }
            perform action a2 { doc /* produces the Harness Audit Card @S237 */ }
        }
        part mainTransformer : MainTransformer;
        part maintenancePlanningEngine : MaintenancePlanningEngine {
            perform action a0 { doc /* schedules inspections and corrective work @S188 */ }
            perform action a1 { doc /* schedules periodic reviews of standby electrical maintenance requirements @S195 */ }
            perform action a2 { doc /* ranks planned and corrective work @S246 */ }
            perform action a3 { doc /* produces the Deferred Task Rationale @S285 */ }
        }
        part marineActivity : MarineActivity {
            exhibit state modes {
                state s0 { doc /* Weather Hold @S086 */ }
            }
        }
        part marineCoordinator : MarineCoordinator {
            perform action a0 { doc /* aligns vessel availability with crew readiness, port access, and the planned work locations @S077 */ }
            perform action a1 { doc /* coordinate the Crew Transfer Vessel, the Service Operations Vessel, and the Daughter Craft @S082 */ }
            perform action a2 { doc /* checks that the planned access method and timing are practical @S160 */ }
            perform action a3 { doc /* maintains the daily marine plan @S223 */ }
            perform action a4 { doc /* records changes to the movement plan @S245 */ }
            perform action a5 { doc /* seeks an updated forecast @S290 */ }
            perform action a6 { doc /* confirming a departure or transfer plan @S290 */ }
            perform action a7 { doc /* pauses further personnel transfers @S576 */ }
        }
        part metoceanBuoy : MetoceanBuoy {
            perform action a0 { doc /* measures wind speed and direction, wave height and period, current, air temperature, and barometric pressure @S102 */ }
            perform action a1 { doc /* produces the Wave Burst Record @S194 */ }
        }
        part nacelleConditionMonitor : NacelleConditionMonitor;
        part northAccessScanner : NorthAccessScanner {
            perform action a0 { doc /* records authorized entry at the north access point @S235 */ }
            perform action a1 { doc /* records identity checks at the north shore access point @S394 */ }
            perform action a2 { doc /* validates each presented credential against current access authorization @S810 */ }
            perform action a3 { doc /* displays a clear outcome @S831 */ }
        }
        part offshoreAssets : OffshoreAssets;
        part offshoreSubstation : OffshoreSubstation {
            perform action a0 { doc /* provides the farm's offshore electrical collection and switching environment @S037 */ }
            perform action a1 { doc /* maintains the designated emergency distribution bus @S189 */ }
            perform action a2 { doc /* sends a Transformer Tap Snapshot @S267 */ }
            exhibit state modes {
                state s0 { doc /* Substation Degraded @S361 */ }
            }
        }
        part offshoreWindFarm : OffshoreWindFarm;
        part onDutyOperationsLead : OnDutyOperationsLead;
        part onboardLogger : OnboardLogger {
            perform action a0 { doc /* timestamps observations @S104 */ }
        }
        part operationalPlanning : OperationalPlanning;
        part operationsTeam : OperationsTeam;
        part permitReviewers : PermitReviewers;
        part personnel : Personnel;
        part personnelTrackingConsole : PersonnelTrackingConsole {
            perform action a0 { doc /* maintains the offshore personnel roster and expected return times @S234 */ }
        }
        part pitchSystem : PitchSystem {
            perform action a0 { doc /* changes blade angle @S130 */ }
            perform action a1 { doc /* adjusts blade angle within its operating envelope @S546 */ }
            perform action a2 { doc /* moves the blades to the defined safe position @S790 */ }
        }
        part portAgent : PortAgent {
            perform action a0 { doc /* coordinates port services @S240 */ }
            perform action a1 { doc /* issues the Berth Slot Confirmation @S324 */ }
        }
        part remoteAdministrativeFunctions : RemoteAdministrativeFunctions {
            exhibit state modes {
                state s0 { doc /* restricted state @S118 */ }
            }
        }
        part requester : Requester;
        part rescueCoordinator : RescueCoordinator {
            perform action a0 { doc /* maintains the response arrangements @S244 */ }
            perform action a1 { doc /* leads rescue planning @S614 */ }
        }
        part rotorBrakeUnit : RotorBrakeUnit {
            perform action a0 { doc /* applies braking @S791 */ }
        }
        part sCADAEngineer : SCADAEngineer {
            perform action a0 { doc /* maintains the configuration and technical integrity of supervisory interfaces @S062 */ }
            perform action a1 { doc /* verifies that status, alarms, and command feedback are consistent @S954 */ }
        }
        part sCADAGateway : SCADAGateway {
            perform action a0 { doc /* flag work packages that may require technical review @S159 */ }
            perform action a1 { doc /* produces the Session Revocation Receipt @S212 */ }
            perform action a2 { doc /* records security-relevant access and control events @S417 */ }
        }
        part serviceOperationsVessel : ServiceOperationsVessel {
            perform action a0 { doc /* prepares the Recovery Basket Load Sheet @S461 */ }
        }
        part shoreBasedOperations : ShoreBasedOperations;
        part shoreControlRoom : ShoreControlRoom {
            perform action a0 { doc /* coordinates operational notices and control-room decisions @S214 */ }
            perform action a1 { doc /* escalates an alert @S303 */ }
            perform action a2 { doc /* sends the Switching Window Acknowledgment @S531 */ }
            perform action a3 { doc /* maintains the incident log @S613 */ }
            perform action a4 { doc /* monitors the loss of visibility @S937 */ }
        }
        part southAccessScanner : SouthAccessScanner {
            perform action a0 { doc /* records authorized entry at the south access point @S236 */ }
            perform action a1 { doc /* records identity checks at the south shore access point @S395 */ }
            perform action a2 { doc /* records each successful entry and each denied attempt @S843 */ }
        }
        part stationServiceTransformers : StationServiceTransformers {
            perform action a0 { doc /* supply the facility's auxiliary electrical loads @S173 */ }
        }
        part storekeeper : Storekeeper {
            perform action a0 { doc /* checks requested materials against available stock @S092 */ }
            perform action a1 { doc /* coordinates replenishment with the Spares Hub @S092 */ }
            perform action a2 { doc /* prepares requested equipment for dispatch @S242 */ }
            perform action a3 { doc /* validate an unavailable part @S262 */ }
        }
        part substationOperator : SubstationOperator {
            perform action a0 { doc /* confirms that switching actions affecting the export path are within the authorized work scope @S216 */ }
            perform action a1 { doc /* applies authorized switching actions @S326 */ }
        }
        part systemPart : System {
            perform action a0 { doc /* raises an alarm @S183 */ }
            exhibit state modes {
                state s0 { doc /* construction control @S015 */ }
                state s1 { doc /* operations control @S015 */ }
            }
        }
        part transmissionSystem : TransmissionSystem;
        part turbine : Turbine {
            exhibit state modes {
                state s0 { doc /* Turbine Lockout @S328 */ }
            }
        }
        part turbineController : TurbineController {
            perform action a0 { doc /* performs local turbine control functions @S060 */ }
            perform action a1 { doc /* produces the Pitch Deviation Notice @S061 */ }
            perform action a2 { doc /* adjusts turbine output within approved operating limits @S127 */ }
            perform action a3 { doc /* blocks commands that conflict with active protection conditions @S127 */ }
            perform action a4 { doc /* executes authorized control actions @S129 */ }
            perform action a5 { doc /* adjusts output @S377 */ }
            perform action a6 { doc /* applies the accepted output target @S545 */ }
            perform action a7 { doc /* initiates the configured shutdown response @S789 */ }
            perform action a8 { doc /* retains protective control locally @S937 */ }
            exhibit state modes {
                state s0 { doc /* safe operating mode @S191 */ }
            }
        }
        part turbineSensorBus : TurbineSensorBus;
        part turbines : Turbines;
        part vesselAISReceiver : VesselAISReceiver {
            perform action a0 { doc /* produces a Position Quality Flag @S105 */ }
            perform action a1 { doc /* collects vessel position broadcasts @S139 */ }
            perform action a2 { doc /* maintains a time-stamped view of nearby vessel movements @S140 */ }
        }
        part vesselMaster : VesselMaster {
            perform action a0 { doc /* evaluates local conditions before departure @S085 */ }
            perform action a1 { doc /* confirms that the vessel plan can support the approved personnel and equipment transfer @S161 */ }
            perform action a2 { doc /* produces the Crew Count Correction @S390 */ }
        }
        part warehouseSystem : WarehouseSystem {
            perform action a0 { doc /* records stock status @S091 */ }
            perform action a1 { doc /* produces a Backorder Exception Slip @S163 */ }
            perform action a2 { doc /* records stock movements @S241 */ }
        }
        part weatherAnalyst : WeatherAnalyst {
            perform action a0 { doc /* reviews available forecasts @S084 */ }
            perform action a1 { doc /* produces the Visibility Confidence Note @S472 */ }
        }
        part weatherService : WeatherService {
            perform action a0 { doc /* produces the Squall Window Bulletin @S083 */ }
        }
        part westServiceLift : WestServiceLift {
            perform action a0 { doc /* provides vertical access along the west route @S884 */ }
        }
        part workPermitPortal : WorkPermitPortal {
            perform action a0 { doc /* maintains the request record and its revision history @S155 */ }
            perform action a1 { doc /* records review decisions @S162 */ }
            perform action a2 { doc /* records the start, pause, resumption, and completion of authorized work @S169 */ }
            perform action a3 { doc /* produces the Isolation Boundary Sketch @S492 */ }
        }
        flow f0 of SupervisoryDataItem from offshoreAssets to shoreBasedOperations { doc /* @S052 */ }
        flow f1 of PitchDeviationNoticeItem from turbineController to sCADAGateway { doc /* @S159 */ }
        flow f2 of EnvironmentalInformationItem from weatherService to operationalPlanning { doc /* @S067 */ }
        flow f3 of InputItem from fieldSupervisor to dutyPlanner { doc /* @S076 */ }
        flow f4 of InputItem from maintenancePlanningEngine to dutyPlanner { doc /* @S076 */ }
        flow f5 of SharedViewOfVesselAssignmentsPlannedMovementsAndDispatchStatusItem from fleetDispatchConsole to marineCoordinator { doc /* @S081 */ }
        flow f6 of SquallWindowBulletinItem from weatherService to maintenancePlanningEngine { doc /* @S213 */ }
        flow f7 of AdviceOnConditionsItem from weatherAnalyst to marineCoordinator { doc /* @S084 */ }
        flow f8 of ChangesToWorkProgressItem from fieldSupervisor to dutyPlanner { doc /* @S096 */ }
        flow f9 of PositionQualityFlagItem from vesselAISReceiver to fleetDispatchConsole { doc /* @S225 */ }
        flow f10 of TransferManifestAddendumItem from dutyPlanner to vesselMaster { doc /* @S278 */ }
        flow f11 of TurbineStatusAndControlAvailabilityItem from sCADAGateway to authorizedShorePersonnel { doc /* @S133 */ }
        flow f12 of IncompleteRequestsItem from workPermitPortal to requester { doc /* @S162 */ }
        flow f13 of BackorderExceptionSlipItem from warehouseSystem to storekeeper { doc /* @S262 */ }
        flow f14 of CurrentOperationalStatusItem from sCADAGateway to permitReviewers { doc /* @S171 */ }
        flow f15 of PowerItem from emergencyGenerator to emergencyDistributionBus { doc /* @S180 */ }
        flow f16 of SupplyAlarmsAndGeneratorStatusItem from sCADAGateway to shoreControlRoom { doc /* @S192 */ }
        flow f17 of WaveBurstRecordItem from metoceanBuoy to weatherAnalyst { doc /* @S323 */ }
        flow f18 of ElectricalPowerItem from offshoreWindFarm to gridConnectionPoint { doc /* @S199 */ }
        flow f19 of AuthorizedOperatingSignalsItem from gridInterfaceRelay to transmissionSystem { doc /* @S201 */ }
        flow f20 of RelayStatusAndInterfaceMeasurementsItem from sCADAGateway to farmMonitoringEnvironment { doc /* @S211 */ }
        flow f21 of SessionRevocationReceiptItem from sCADAGateway to cybersecurityGateway { doc /* @S357 */ }
        flow f22 of AdviceOnForecastChangesItem from weatherAnalyst to marineCoordinator { doc /* @S232 */ }
        flow f23 of HarnessAuditCardItem from hSEOfficer to crewTransferVessel { doc /* @S312 */ }
        flow f24 of TransformerTapSnapshotItem from offshoreSubstation to shoreControlRoom { doc /* @S374 */ }
        flow f25 of ResultingPlanItem from dutyPlanner to affectedTeams { doc /* @S269 */ }
        flow f26 of DeferredTaskRationaleItem from maintenancePlanningEngine to fieldSupervisor { doc /* @S430 */ }
        flow f27 of OperatingMeasurementsItem from turbineController to turbineSensorBus { doc /* @S294 */ }
        flow f28 of OperatingMeasurementsItem from pitchSystem to turbineSensorBus { doc /* @S294 */ }
        flow f29 of OperatingMeasurementsItem from converterCabinet to turbineSensorBus { doc /* @S294 */ }
        flow f30 of OperatingMeasurementsItem from nacelleConditionMonitor to turbineSensorBus { doc /* @S294 */ }
        flow f31 of TimeStampedObservationsItem from sCADAGateway to shoreControlRoom { doc /* @S295 */ }
        flow f32 of LeadingEdgeTileImageItem from bladeInspectionDrone to bladeSpecialist { doc /* @S445 */ }
        flow f33 of BerthSlotConfirmationItem from portAgent to marineCoordinator { doc /* @S473 */ }
        flow f34 of StartTestTraceItem from emergencyGenerator to substationOperator { doc /* @S532 */ }
        flow f35 of ExportLimitAdvisoryItem from gridInterfaceRelay to gridDispatcher { doc /* @S541 */ }
        flow f36 of CrewCountCorrectionItem from vesselMaster to personnelTrackingConsole { doc /* @S573 */ }
        flow f37 of ChangeInDestinationOrTransferPlanItem from personnel to vesselMaster { doc /* @S402 */ }
        flow f38 of UnexplainedAbsenceOrOverdueCheckInItem from fieldSupervisor to marineCoordinator { doc /* @S412 */ }
        flow f39 of UrgentConcernsItem from cybersecurityAnalyst to onDutyOperationsLead { doc /* @S419 */ }
        flow f40 of FirmwareHashAttestationItem from cybersecurityAnalyst to sCADAEngineer { doc /* @S593 */ }
        flow f41 of RecoveryBasketLoadSheetItem from serviceOperationsVessel to rescueCoordinator { doc /* @S646 */ }
        flow f42 of VisibilityConfidenceNoteItem from weatherAnalyst to dutyPlanner { doc /* @S669 */ }
        flow f43 of IsolationBoundarySketchItem from workPermitPortal to electricalTechnician { doc /* @S716 */ }
        flow f44 of AdviceOnForecastConditionsItem from weatherAnalyst to dutyPlanner { doc /* @S522 */ }
        flow f45 of SwitchingWindowAcknowledgmentItem from shoreControlRoom to offshoreSubstation { doc /* @S752 */ }
        flow f46 of CurrentGenerationExportAndEquipmentStatusItem from sCADAGateway to operationsTeam { doc /* @S540 */ }
        flow f47 of DiscrepancyAndTheImmediateControlActionsItem from marineCoordinator to shoreControlRoom { doc /* @S578 */ }
        flow f48 of UnresolvedDiscrepancyItem from marineCoordinator to dutyPlanner { doc /* @S583 */ }
        flow f49 of MaterialChangesItem from weatherAnalyst to rescueCoordinator { doc /* @S626 */ }
        flow f50 of MarineAndWeatherInformationItem from marineCoordinator to dutyPlanner { doc /* @S764 */ }
        flow f51 of OperationalDataItem from sCADAGateway to shoreControlRoom { doc /* @S767 */ }
        flow f52 of ExternalOperatingRequirementsItem from gridDispatcher to gridInterfaceRelay { doc /* @S769 */ }
        flow f53 of UnresolvedPersonnelOrAccessConcernsItem from fieldSupervisor to shoreControlRoom { doc /* @S809 */ }
        flow f54 of OperationalRestrictionsItem from fleetDispatchConsole to dutyPlanner { doc /* @S947 */ }
    }
    requirement def R0 { doc /* Juniper Vale shall provide current operational status to permit reviewers when requested as part of the authorization check. @S171 */ subject s : SCADAGateway; }
    requirement def R1 { doc /* Larkspur shall repeat a close-range pass when image coverage is insufficient to assess the suspected surface condition. @S314 */ subject s : BladeInspectionDrone; }
    requirement def R2 { doc /* Redoubt shall block permit release until required risk reviews and isolation references are complete. @S321 */ subject s : WorkPermitPortal; }
    requirement def R3 { doc /* Personnel must not hold the barrier open for another entrant. @S847 */ subject s : Personnel; }
    requirement def R4 { doc /* Lighting inside the car and at each landing must be adequate for safe movement and inspection. @S891 */ subject s : WestServiceLift; }
    requirement def R5 { doc /* Door interlocks and other protective devices must be functional before the lift is placed in service. @S893 */ subject s : WestServiceLift; }
    requirement def R6 { doc /* Protective devices must not be bypassed to maintain access or avoid delay. @S894 */ subject s : WestServiceLift; }
}
