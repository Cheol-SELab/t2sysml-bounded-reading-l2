package L2Model {
    item def ActivePowerTargetsAndRampInstructionsItem { doc /* @S368 */ }
    item def AdviceOnConditionsItem { doc /* @S084,S232 */ }
    item def AlarmsWithLocationAndFaultInformationItem { doc /* @S798 */ }
    item def AlertItem { doc /* @S316,S419 */ }
    item def ApprovedBoundaryItem { doc /* @S713 */ }
    item def AuthorizedOperatingSignalsItem { doc /* @S201 */ }
    item def BackorderExceptionSlipItem { doc /* @S262 */ }
    item def BerthSlotConfirmationItem { doc /* @S473 */ }
    item def BoundaryAccessRestrictionsAndConditionsThatRequireWorkToStopItem { doc /* @S717 */ }
    item def ChangeInDestinationOrTransferPlanItem { doc /* @S402 */ }
    item def ChangesToWorkProgressItem { doc /* @S096 */ }
    item def CredentialItem { doc /* @S812,S840 */ }
    item def CrewCountCorrectionItem { doc /* @S573 */ }
    item def CurrentGenerationExportAndEquipmentStatusItem { doc /* @S540 */ }
    item def CurrentOperationalStatusItem { doc /* @S171 */ }
    item def DeferredTaskRationaleItem { doc /* @S430 */ }
    item def DiscrepancyAndTheImmediateControlActionsItem { doc /* @S578 */ }
    item def ElectricalPowerItem { doc /* @S199 */ }
    item def EmergencyPowerItem { doc /* @S180 */ }
    item def EnvironmentalObservationsItem { doc /* @S106 */ }
    item def ExportLimitAdvisoryItem { doc /* @S541 */ }
    item def ExternalOperatingRequirementsItem { doc /* @S769 */ }
    item def FirmwareHashAttestationItem { doc /* @S593 */ }
    item def ForecastConditionsItem { doc /* @S522 */ }
    item def ForecastDataItem { doc /* @S272 */ }
    item def ForecastUpdatesItem { doc /* @S232 */ }
    item def ForecastsItem { doc /* @S641 */ }
    item def HarnessAuditCardItem { doc /* @S312 */ }
    item def IncompleteRequestsItem { doc /* @S162 */ }
    item def IndependentSignalsItem { doc /* @S299 */ }
    item def InputItem { doc /* @S076 */ }
    item def InspectionResultAndObservedDefectsItem { doc /* @S869 */ }
    item def IsolationBoundarySketchItem { doc /* @S716 */ }
    item def LeadingEdgeTileImageItem { doc /* @S445 */ }
    item def MaterialChangesItem { doc /* @S626 */ }
    item def OperatingMeasurementsItem { doc /* @S294 */ }
    item def OperationalDataItem { doc /* @S767 */ }
    item def OperationalRestrictionsItem { doc /* @S947 */ }
    item def PermitLimitsIsolationBoundariesCommunicationsAndConditionsRequiringWorkToStopItem { doc /* @S330 */ }
    item def PitchDeviationNoticeItem { doc /* @S159 */ }
    item def PlannedWorkPeriodItem { doc /* @S737 */ }
    item def PositionQualityFlagItem { doc /* @S225 */ }
    item def RelayStatusAndInterfaceMeasurementsItem { doc /* @S211 */ }
    item def ReleaseStatusItem { doc /* @S881 */ }
    item def RelevantMarineAndWeatherInformationItem { doc /* @S764 */ }
    item def RemainingOperationalLimitationItem { doc /* @S734 */ }
    item def RemoteObservationsItem { doc /* @S145 */ }
    item def ResourceChangesItem { doc /* @S261 */ }
    item def ResultingPlanItem { doc /* @S269 */ }
    item def SharedViewOfVesselAssignmentsPlannedMovementsAndDispatchStatusItem { doc /* @S081,S082 */ }
    item def SiteConditionsAccessStatusAndOutstandingHazardsItem { doc /* @S512 */ }
    item def SquallWindowBulletinItem { doc /* @S213 */ }
    item def StartTestTraceItem { doc /* @S532 */ }
    item def SupplyAlarmsAndGeneratorStatusItem { doc /* @S192 */ }
    item def SwitchingInstructionsItem { doc /* @S530 */ }
    item def SwitchingWindowAcknowledgmentItem { doc /* @S752 */ }
    item def TaskDurationResourceDemandAndDependencyStatusItem { doc /* @S470 */ }
    item def TheRecoveryBasketLoadSheetItem { doc /* @S646 */ }
    item def TheSessionRevocationReceiptItem { doc /* @S357 */ }
    item def TheTransferManifestAddendumItem { doc /* @S278 */ }
    item def TimeStampedObservationsItem { doc /* @S295 */ }
    item def TrafficPictureItem { doc /* @S141 */ }
    item def TransformerTapSnapshotItem { doc /* @S374 */ }
    item def TurbineStatusAndControlAvailabilityItem { doc /* @S133,S448 */ }
    item def UnexplainedAbsenceOrOverdueCheckInItem { doc /* @S412 */ }
    item def UnresolvedDiscrepancyItem { doc /* @S583,S586 */ }
    item def UnresolvedPersonnelOrAccessConcernsItem { doc /* @S809 */ }
    item def UpdateItem { doc /* @S245 */ }
    item def UrgentConcernsItem { doc /* @S419 */ }
    item def VisibilityConfidenceNoteItem { doc /* @S669 */ }
    item def WaveBurstRecordItem { doc /* @S323 */ }
    item def WeatherAdviceItem { doc /* @S522 */ }
    part def AccountabilityRecords { doc /* @S414 */ }
    part def ActionsTaken { doc /* @S584 */ }
    part def AdjacentEquipment { doc /* @S715 */ }
    part def AffectedEquipment { doc /* @S740 */ }
    part def AffectedTeams { doc /* @S245,S269 */ }
    part def ApplicableHandlingRequirements { doc /* @S699 */ }
    part def ApprovedProcedures { doc /* @S972 */ }
    part def ApprovedWindow { doc /* @S740 */ }
    part def Approver { doc /* @S978,S979 */ }
    part def Architecture { doc /* @S072 */ }
    part def AssetOperator { doc /* @S959 */ }
    part def AssuranceEvidence { doc /* @S972 */ }
    part def AuditFindings { doc /* @S972 */ }
    part def AuditRecord { doc /* @S823 */ }
    part def AuthorizedShorePersonnel { doc /* @S133 */ }
    part def AutomaticControls { doc /* @S177 */ }
    part def BladeInspectionDrone { doc /* @S036,S142,S145,S146,S254,S313,S314,S444,S445 */ }
    part def BladeSpecialist { doc /* @S143,S315,S445,S452,S455,S463,S651 */ }
    part def CompetenceRecords { doc /* @S972 */ }
    part def Consumables { doc /* @S686 */ }
    part def ContingencyProcess { doc /* @S829 */ }
    part def ControlEngineer { doc /* @S063,S135,S193,S217,S297,S299,S302,S305,S310,S316,S338,S349,S368,S375,S384,S423,S434,S516,S528,S530,S534,S542,S544,S552,S560,S562,S594,S630,S658,S718,S734,S742,S768,S799,S920,S938,S951,S964 */ }
    part def ControlRoomStaff { doc /* @S729 */ }
    part def ControlTeam { doc /* @S713 */ }
    part def ConverterCabinet { doc /* @S005,S131,S294 */ }
    part def Crew { doc /* @S167,S330,S495,S504,S506,S511,S717 */ }
    part def CrewTransferVessel { doc /* @S021,S045,S087,S215,S279,S312,S620,S643,S678 */ }
    part def CurrentStatus { doc /* @S584 */ }
    part def CybersecurityAnalyst { doc /* @S117,S419,S428,S435,S593,S781,S929,S969 */ }
    part def CybersecurityGateway { doc /* @S049,S071,S111,S112,S287,S357,S416 */ }
    part def CybersecurityOperations { doc /* @S415 */ }
    part def DaughterCraft { doc /* @S021,S045,S088,S621,S644,S679 */ }
    part def DecisionRecords { doc /* @S293 */ }
    part def DeferredTaskRationale { doc /* @S286 */ }
    part def DeliveredEnergy { doc /* @S910 */ }
    part def DeliveryLocation { doc /* @S699 */ }
    part def DesignatedAuthorizingRole { doc /* @S165 */ }
    part def DesignatedGridConnectionPoint { doc /* @S199 */ }
    part def Discrepancy { doc /* @S575 */ }
    part def DispatchRecord { doc /* @S708 */ }
    part def DocumentOwner { doc /* @S976 */ }
    part def DoorInterlocks { doc /* @S893 */ }
    part def DurationOfGridRelatedRestrictions { doc /* @S910 */ }
    part def DutyPlanner { doc /* @S065,S076,S096,S126,S153,S164,S224,S247,S258,S260,S263,S269,S274,S278,S292,S304,S319,S334,S340,S388,S396,S442,S459,S464,S469,S470,S491,S515,S519,S522,S527,S536,S537,S539,S553,S561,S583,S639,S669,S695,S702,S737,S758,S764,S779,S872,S925,S947,S955,S965 */ }
    part def EastServiceLift { doc /* @S859 */ }
    part def ElectricalRecoveryWork { doc /* @S631 */ }
    part def ElectricalTechnician { doc /* @S185,S325,S327,S331,S336,S363,S434,S496,S529,S650,S716,S750,S801,S867 */ }
    part def EmergencyDistributionBus { doc /* @S180 */ }
    part def EmergencyGenerator { doc /* @S180,S353,S355,S356,S532,S803,S945 */ }
    part def EmergencyResponseOrganizations { doc /* @S024 */ }
    part def EndTime { doc /* @S740 */ }
    part def EnergyProductionMeasures { doc /* @S910 */ }
    part def Entrant { doc /* @S839 */ }
    part def EntryBarrier { doc /* @S846 */ }
    part def EventInvestigations { doc /* @S972 */ }
    part def ExpectedCount { doc /* @S584 */ }
    part def ExpectedOperatingState { doc /* @S740 */ }
    part def ExportCableMonitor { doc /* @S006,S200,S252 */ }
    part def ExternalInterfaces { doc /* @S024 */ }
    part def Farm { doc /* @S199,S205 */ }
    part def FarmMonitoringEnvironment { doc /* @S211 */ }
    part def FieldSupervisor { doc /* @S076,S096,S145,S167,S253,S320,S329,S330,S333,S335,S340,S405,S412,S429,S430,S457,S493,S503,S509,S536,S615,S649,S660,S717,S726,S778,S809,S826,S860,S869,S879,S881,S886,S887,S906,S927,S970 */ }
    part def FieldTeam { doc /* @S729 */ }
    part def FireDetectionPanel { doc /* @S629,S786,S798,S945 */ }
    part def FleetDispatchConsole { doc /* @S041,S069,S081,S082,S203,S225,S259,S260,S370,S385,S543,S917,S947 */ }
    part def Gate { doc /* @S816 */ }
    part def GridConstraint { doc /* @S210,S376,S746 */ }
    part def GridDispatch { doc /* @S024 */ }
    part def GridDispatcher { doc /* @S202,S362,S367,S368,S383,S518,S541,S739,S769,S942 */ }
    part def GridInterfaceRelay { doc /* @S190,S197,S201,S221,S372,S373,S541,S551,S743,S769,S942 */ }
    part def HSEOfficer { doc /* @S095,S157,S237,S266,S312,S322,S408,S451,S481,S505,S526,S579,S617,S647,S808,S827,S949,S967 */ }
    part def Helideck { doc /* @S021,S623 */ }
    part def IncidentLead { doc /* @S432,S436,S619 */ }
    part def IncomingSupervisor { doc /* @S512 */ }
    part def IncomingTeam { doc /* @S731 */ }
    part def InspectionRecord { doc /* @S456 */ }
    part def Inspector { doc /* @S862,S865,S868 */ }
    part def InstallationTeam { doc /* @S853 */ }
    part def InventoryRecord { doc /* @S686 */ }
    part def IsolationBoundary { doc /* @S711 */ }
    part def Lighting { doc /* @S891 */ }
    part def LocalVisualIndicator { doc /* @S845 */ }
    part def LowStockAlert { doc /* @S701 */ }
    part def MainTransformer { doc /* @S006,S038,S604 */ }
    part def MaintenancePlanningEngine { doc /* @S042,S054,S058,S066,S076,S148,S154,S188,S195,S213,S246,S285,S308,S430,S441,S458,S470,S520,S554,S670,S694,S737,S738,S918,S948 */ }
    part def MaintenanceRecords { doc /* @S972 */ }
    part def MaintenanceSystem { doc /* @S869 */ }
    part def MarineActivity { doc /* @S086 */ }
    part def MarineCoordination { doc /* @S021,S075,S222 */ }
    part def MarineCoordinator { doc /* @S068,S077,S081,S082,S084,S141,S160,S223,S232,S245,S257,S261,S277,S283,S290,S397,S400,S410,S412,S466,S473,S483,S488,S499,S523,S565,S576,S578,S583,S585,S586,S618,S638,S659,S676,S682,S749,S764,S944,S966 */ }
    part def MetoceanBuoy { doc /* @S044,S102,S106,S194,S231,S271,S309,S323,S443,S625,S665,S766 */ }
    part def MetoceanObservations { doc /* @S024 */ }
    part def MonitoringRules { doc /* @S418 */ }
    part def NacelleConditionMonitor { doc /* @S005,S132,S250,S294,S299,S793,S915 */ }
    part def NeedDate { doc /* @S699 */ }
    part def NorthAccessScanner { doc /* @S022,S235,S394,S569,S810,S811 */ }
    part def ObservedCount { doc /* @S584 */ }
    part def Occupants { doc /* @S899,S902,S905 */ }
    part def OffshoreSubstation { doc /* @S003,S037,S038,S173,S189,S267,S361,S374,S752,S941 */ }
    part def OffshoreWindFarm { doc /* @S003,S005,S006,S009,S011,S015,S019,S028 */ }
    part def OnDutyOperationsLead { doc /* @S419 */ }
    part def OnboardLogger { doc /* @S104 */ }
    part def OperatingOrganization { doc /* @S075,S098 */ }
    part def OperationalAndTechnicalRepresentatives { doc /* @S978 */ }
    part def OperationalPersonnel { doc /* @S073 */ }
    part def OperationalSystem { doc /* @S058 */ }
    part def OperationsRadioConsole { doc /* @S239,S627,S762,S806 */ }
    part def OperationsTeam { doc /* @S540,S558 */ }
    part def Operator { doc /* @S356,S359,S360,S361,S376,S549,S878,S888,S890,S892,S895,S898,S900,S901,S904,S905,S983 */ }
    part def Operators { doc /* @S184,S832,S935 */ }
    part def Organization { doc /* @S782 */ }
    part def OutgoingSupervisor { doc /* @S512 */ }
    part def Passengers { doc /* @S896 */ }
    part def PermitReviewers { doc /* @S171 */ }
    part def Person { doc /* @S812,S840 */ }
    part def Personnel { doc /* @S393,S402,S405,S406,S411,S431,S451,S457,S482,S501,S585,S734,S771,S802,S804,S828,S847,S856,S903,S981 */ }
    part def PersonnelTrackingConsole { doc /* @S022,S047,S094,S234,S332,S392,S571,S573,S619,S648,S805,S874 */ }
    part def PersonsStillUnaccountedFor { doc /* @S584 */ }
    part def PitchSystem { doc /* @S005,S034,S130,S294,S546,S790 */ }
    part def PortAgent { doc /* @S093,S240,S324,S473 */ }
    part def PortStagingAreas { doc /* @S477 */ }
    part def PortSupport { doc /* @S024 */ }
    part def ProductionLostDuringDowntime { doc /* @S910 */ }
    part def ProtectiveDevices { doc /* @S894 */ }
    part def QualifiedTechnician { doc /* @S719 */ }
    part def Receiver { doc /* @S773 */ }
    part def Record { doc /* @S584 */ }
    part def RemoteSessions { doc /* @S427 */ }
    part def RepairableUnits { doc /* @S686 */ }
    part def ReplenishmentRequest { doc /* @S699 */ }
    part def Requester { doc /* @S152,S162 */ }
    part def RequiredQuantity { doc /* @S699 */ }
    part def RescueCoordinator { doc /* @S244,S580,S614,S626,S634,S637,S646 */ }
    part def ResponsibleAuthority { doc /* @S657,S732 */ }
    part def ResponsibleManager { doc /* @S784 */ }
    part def ResponsibleOperationalAuthority { doc /* @S500 */ }
    part def ResponsibleOperator { doc /* @S952 */ }
    part def ResponsiblePersonnel { doc /* @S086 */ }
    part def ResponsibleSupervisor { doc /* @S413 */ }
    part def ResponsibleTeam { doc /* @S170,S450 */ }
    part def ReviewTeams { doc /* @S922 */ }
    part def RiskAssessments { doc /* @S972 */ }
    part def RotorBrakeUnit { doc /* @S005,S034,S791 */ }
    part def SCADAEngineer { doc /* @S062,S423,S437,S558,S593,S946,S954,S968 */ }
    part def SCADAGateway { doc /* @S006,S052,S058,S059,S114,S133,S159,S171,S192,S211,S212,S295,S357,S369,S417,S447,S448,S540,S767,S800,S914,S946 */ }
    part def Sender { doc /* @S773 */ }
    part def ServiceOperationsVessel { doc /* @S021,S045,S089,S228,S281,S461,S622,S645,S646,S680 */ }
    part def ServiceableParts { doc /* @S686 */ }
    part def ShiftHandover { doc /* @S586,S730 */ }
    part def ShiftRecords { doc /* @S389 */ }
    part def ShoreBasedPlanning { doc /* @S075 */ }
    part def ShoreControlRoom { doc /* @S013,S040,S056,S058,S064,S097,S099,S134,S192,S214,S238,S295,S303,S316,S317,S339,S364,S371,S374,S386,S419,S420,S448,S531,S578,S606,S613,S683,S752,S761,S767,S798,S809,S937,S963 */ }
    part def ShorePersonnel { doc /* @S410 */ }
    part def Signs { doc /* @S852 */ }
    part def SouthAccessScanner { doc /* @S022,S236,S395,S570,S812,S813,S814,S816,S828,S831,S835,S838,S840,S843,S856 */ }
    part def SouthernEntryRoute { doc /* @S853,S855 */ }
    part def SparesHub { doc /* @S023,S689 */ }
    part def StaleOrImplausibleValue { doc /* @S300 */ }
    part def StartTime { doc /* @S740 */ }
    part def StationServiceTransformers { doc /* @S173 */ }
    part def Storekeeper { doc /* @S092,S242,S262,S460,S479,S690,S703,S876 */ }
    part def SubstationOperator { doc /* @S216,S268,S326,S337,S342,S343,S345,S351,S354,S382,S497,S517,S530,S532,S559,S741,S753,S971 */ }
    part def Substitution { doc /* @S704 */ }
    part def SupplyInterfaces { doc /* @S023 */ }
    part def SwitchingOperator { doc /* @S533,S757 */ }
    part def System { doc /* @S824,S908,S934,S935,S957 */ }
    part def SystemArchitecture { doc /* @S051 */ }
    part def TechnicalReviewers { doc /* @S158 */ }
    part def TechnicalTeams { doc /* @S433,S439 */ }
    part def Technicians { doc /* @S075 */ }
    part def TemporaryPersonnel { doc /* @S849 */ }
    part def Transaction { doc /* @S821,S822 */ }
    part def TransmissionSystem { doc /* @S201 */ }
    part def Turbine { doc /* @S034,S444,S657,S940 */ }
    part def TurbineController { doc /* @S005,S060,S061,S127,S129,S159,S191,S294,S299,S377,S545,S789,S937 */ }
    part def TurbineLockout { doc /* @S802 */ }
    part def TurbineSensorBus { doc /* @S005,S251,S294,S788 */ }
    part def Turbines { doc /* @S003 */ }
    part def UrgentPurchase { doc /* @S707 */ }
    part def Users { doc /* @S882 */ }
    part def VesselAISReceiver { doc /* @S105,S139,S140,S141,S225,S288,S401 */ }
    part def VesselCrews { doc /* @S075 */ }
    part def VesselMaster { doc /* @S079,S085,S161,S226,S261,S278,S279,S284,S390,S398,S402,S403,S409,S476,S498,S524,S567,S573,S577,S616,S634,S642,S677,S682,S763,S807,S944 */ }
    part def VesselRecoverySupport { doc /* @S636 */ }
    part def Visitors { doc /* @S849 */ }
    part def WarehouseSystem { doc /* @S023,S091,S163,S241,S262,S478,S655,S687,S928 */ }
    part def WeatherAnalyst { doc /* @S084,S107,S232,S256,S272,S323,S472,S522,S626,S641,S669,S765,S939 */ }
    part def WeatherHold { doc /* @S259 */ }
    part def WeatherService { doc /* @S067,S083,S106,S128,S213,S230,S232,S255,S270,S272,S309,S443,S521,S522,S557,S624,S640,S641,S664,S748,S766,S939 */ }
    part def WeatherServices { doc /* @S024 */ }
    part def WestServiceLift { doc /* @S884,S907 */ }
    part def WorkParty { doc /* @S713,S720,S881 */ }
    part def WorkPermitPortal { doc /* @S049,S070,S155,S162,S169,S265,S321,S492,S713,S716,S728,S780 */ }
    part def WorkforceInterfaces { doc /* @S022 */ }
    part system {
        part accountabilityRecords : AccountabilityRecords {
            perform action a0 { doc /* retain the time, location, responsible role, and disposition of each material movement @S414 */ }
        }
        part actionsTaken : ActionsTaken;
        part adjacentEquipment : AdjacentEquipment;
        part affectedEquipment : AffectedEquipment;
        part affectedTeams : AffectedTeams;
        part applicableHandlingRequirements : ApplicableHandlingRequirements;
        part approvedProcedures : ApprovedProcedures;
        part approvedWindow : ApprovedWindow;
        part approver : Approver {
            perform action a0 { doc /* confirms that comments are resolved or explicitly accepted @S979 */ }
        }
        part architecture : Architecture {
            perform action a0 { doc /* assigns defined responsibilities to interfaces @S072 */ }
        }
        part assetOperator : AssetOperator {
            perform action a0 { doc /* assigns an accountable owner @S959 */ }
        }
        part assuranceEvidence : AssuranceEvidence;
        part auditFindings : AuditFindings;
        part auditRecord : AuditRecord {
            perform action a0 { doc /* distinguishes a rejected credential from an authorization that lacks the required scope @S823 */ }
        }
        part authorizedShorePersonnel : AuthorizedShorePersonnel;
        part automaticControls : AutomaticControls {
            perform action a0 { doc /* initiate the Emergency Generator start sequence @S177 */ }
        }
        part bladeInspectionDrone : BladeInspectionDrone {
            perform action a0 { doc /* used for turbine blade assessment @S036 */ }
            perform action a1 { doc /* captures close-range visual observations of accessible blade surfaces @S142 */ }
            perform action a2 { doc /* support inspection planning @S254 */ }
            perform action a3 { doc /* produces the Leading Edge Tile Image @S313 */ }
            perform action a4 { doc /* repeat a close-range pass @S314 */ }
            perform action a5 { doc /* capture repeatable views of blade surfaces @S444 */ }
            exhibit state modes {
                state s0 { doc /* suspended @S146 */ }
            }
        }
        part bladeSpecialist : BladeSpecialist {
            perform action a0 { doc /* plans inspection passes @S143 */ }
            perform action a1 { doc /* reviews available inspection evidence @S315 */ }
            perform action a2 { doc /* reports whether further examination is warranted @S315 */ }
            perform action a3 { doc /* reviews the Leading Edge Tile Image to classify visible damage @S445 */ }
            perform action a4 { doc /* identify areas requiring closer assessment @S445 */ }
            perform action a5 { doc /* examines the affected surface using suitable lighting, measurement tools, and nondestructive inspection methods @S452 */ }
            perform action a6 { doc /* distinguishes cosmetic damage from conditions that could affect structural integrity or safe turbine operation @S455 */ }
            perform action a7 { doc /* records the completed work @S463 */ }
            perform action a8 { doc /* verifies that the repaired area meets the applicable acceptance criteria @S463 */ }
            perform action a9 { doc /* identifies fragile blade components @S651 */ }
            perform action a10 { doc /* specifies padding or restraints to prevent handling damage @S651 */ }
        }
        part competenceRecords : CompetenceRecords;
        part consumables : Consumables;
        part contingencyProcess : ContingencyProcess;
        part controlEngineer : ControlEngineer {
            perform action a0 { doc /* uses the shore-based operational picture to assess equipment status @S063 */ }
            perform action a1 { doc /* coordinate response @S063 */ }
            perform action a2 { doc /* reviews alarms and operating conditions @S135 */ }
            perform action a3 { doc /* issuing a remote command @S135 */ }
            perform action a4 { doc /* reviews persistent alarms @S193 */ }
            perform action a5 { doc /* coordinates electrical support with the Substation Operator @S193 */ }
            perform action a6 { doc /* verifies that dispatch changes are reflected in the applicable control settings before implementation @S217 */ }
            perform action a7 { doc /* reviews alarms alongside recent operating trends @S297 */ }
            perform action a8 { doc /* compares disputed readings with independent signals @S299 */ }
            perform action a9 { doc /* records the evidence considered and the basis for accepting, rejecting, or continuing to monitor an alert @S302 */ }
            perform action a10 { doc /* follows the approved operating procedure @S305 */ }
            perform action a11 { doc /* confirms the resulting state through available indications @S305 */ }
            perform action a12 { doc /* requests an on-site inspection @S310 */ }
            perform action a13 { doc /* reassesses the alert @S316 */ }
            perform action a14 { doc /* reviews the restored equipment state @S338 */ }
            perform action a15 { doc /* confirms that required operational checks are complete @S338 */ }
            perform action a16 { doc /* investigates unexplained discrepancies @S349 */ }
            perform action a17 { doc /* reviews each instruction @S368 */ }
            perform action a18 { doc /* applying it @S368 */ }
            perform action a19 { doc /* confirms that the control response follows the instruction @S375 */ }
            perform action a20 { doc /* records the reason for any temporary deviation from the requested output and the action taken @S384 */ }
            perform action a21 { doc /* use individually assigned accounts rather than shared credentials for interactive work @S423 */ }
            perform action a22 { doc /* coordinate any operational changes with the relevant duty role @S434 */ }
            perform action a23 { doc /* checks the current network configuration @S516 */ }
            perform action a24 { doc /* confirms that the proposed sequence supports the approved work @S516 */ }
            perform action a25 { doc /* prepares clear switching instructions with one action per step and an explicit hold point where needed @S528 */ }
            perform action a26 { doc /* monitors available indications @S534 */ }
            perform action a27 { doc /* confirms that each reported state change matches the approved sequence @S534 */ }
            perform action a28 { doc /* verifies the permitted level, its effective time, and any required ramp rate @S542 */ }
            perform action a29 { doc /* changing operating targets @S542 */ }
            perform action a30 { doc /* reduces active power in controlled steps @S544 */ }
            perform action a31 { doc /* checks that measured export follows the revised target @S544 */ }
            perform action a32 { doc /* compares actual export with the permitted level @S552 */ }
            perform action a33 { doc /* investigates any persistent mismatch @S552 */ }
            perform action a34 { doc /* escalates any condition that threatens equipment limits, protection coordination, or safe operation @S560 */ }
            perform action a35 { doc /* confirms authorization @S562 */ }
            perform action a36 { doc /* restores output gradually while monitoring equipment response @S562 */ }
            perform action a37 { doc /* confirms that proposed changes have a clear operational purpose and defined scope @S594 */ }
            perform action a38 { doc /* supports remote shutdown actions @S630 */ }
            perform action a39 { doc /* provides technical guidance @S658 */ }
            perform action a40 { doc /* checks that remote indications agree with the approved switching state @S718 */ }
            perform action a41 { doc /* authorizing access @S718 */ }
            perform action a42 { doc /* verifies the restoration state @S734 */ }
            perform action a43 { doc /* communicates any remaining operational limitation to affected personnel @S734 */ }
            perform action a44 { doc /* checks that turbine operations can be managed safely while the substation work is in progress @S742 */ }
            perform action a45 { doc /* reviews alarms and operating trends with the SCADA Engineer @S768 */ }
            perform action a46 { doc /* verifies the equipment state @S799 */ }
            perform action a47 { doc /* checks that protection actions have completed @S799 */ }
            perform action a48 { doc /* authorizing any further operational action @S799 */ }
            perform action a49 { doc /* examines significant operational deviations @S920 */ }
            perform action a50 { doc /* records the technical findings for review @S920 */ }
            perform action a51 { doc /* suspends those commands @S938 */ }
            perform action a52 { doc /* uses approved local procedures @S938 */ }
            perform action a53 { doc /* coordinates technical recovery with the relevant field and shore roles @S951 */ }
            perform action a54 { doc /* reviews control-room practices @S964 */ }
            perform action a55 { doc /* confirms that operational procedures remain consistent with the concept @S964 */ }
        }
        part controlRoomStaff : ControlRoomStaff {
            perform action a0 { doc /* use the same revision when confirming isolation status @S729 */ }
        }
        part controlTeam : ControlTeam;
        part converterCabinet : ConverterCabinet {
            perform action a0 { doc /* manages electrical conversion while observing equipment limits and protective interlocks @S131 */ }
        }
        part crew : Crew {
            perform action a0 { doc /* starts work @S167 */ }
            perform action a1 { doc /* confirms that the marked limits match the current isolation points and the approved maintenance scope @S495 */ }
            perform action a2 { doc /* inspects personal protective equipment, communications equipment, and rescue equipment for serviceability @S504 */ }
            perform action a3 { doc /* tests the required radio channel with the Operations Radio Console @S506 */ }
            perform action a4 { doc /* separating into work teams @S506 */ }
            perform action a5 { doc /* maintains clear access to fire equipment, escape routes, and lifting areas @S511 */ }
        }
        part crewTransferVessel : CrewTransferVessel {
            perform action a0 { doc /* may support offshore work @S045 */ }
            perform action a1 { doc /* transports authorized personnel and routine tools between shore and offshore work locations @S087 */ }
            perform action a2 { doc /* reports its approach and departure status @S215 */ }
            perform action a3 { doc /* proceeds @S279 */ }
            perform action a4 { doc /* uses the Harness Audit Card to verify the applicable equipment checks @S312 */ }
            perform action a5 { doc /* transports personnel and small equipment @S643 */ }
            perform action a6 { doc /* remain clear of a transfer location @S678 */ }
            exhibit state modes {
                state s0 { doc /* suspended @S620 */ }
            }
        }
        part currentStatus : CurrentStatus;
        part cybersecurityAnalyst : CybersecurityAnalyst {
            perform action a0 { doc /* monitors gateway events for unusual access patterns and configuration changes @S117 */ }
            perform action a1 { doc /* reviews alerts @S419 */ }
            perform action a2 { doc /* assesses their operational significance @S419 */ }
            perform action a3 { doc /* escalates urgent concerns to the on-duty operations lead @S419 */ }
            perform action a4 { doc /* produces the Firmware Hash Attestation for controlled software releases @S428 */ }
            perform action a5 { doc /* preserves relevant logs and technical evidence @S435 */ }
            perform action a6 { doc /* limiting access to personnel assigned to the investigation @S435 */ }
            perform action a7 { doc /* protects access logs and communication records against unauthorized alteration or disclosure @S781 */ }
            perform action a8 { doc /* reviews performance records for evidence that cybersecurity controls affect operational availability or recovery @S929 */ }
            perform action a9 { doc /* assesses changes that could affect access, communications, or the integrity of operational records @S969 */ }
        }
        part cybersecurityGateway : CybersecurityGateway {
            perform action a0 { doc /* support controlled and secure operations @S049 */ }
            perform action a1 { doc /* provides a security boundary for connected operational services @S071 */ }
            perform action a2 { doc /* establishes a controlled boundary between authorized shore-side services and offshore operational networks @S111 */ }
            perform action a3 { doc /* permits only approved protocols, destinations, and service accounts @S112 */ }
            perform action a4 { doc /* blocks a route change @S287 */ }
            perform action a5 { doc /* uses the revocation receipt to support access control @S357 */ }
            perform action a6 { doc /* monitors traffic between operational networks and approved external connections @S416 */ }
        }
        part cybersecurityOperations : CybersecurityOperations {
            perform action a0 { doc /* protect the wind farm control environment @S415 */ }
        }
        part daughterCraft : DaughterCraft {
            perform action a0 { doc /* may support offshore work @S045 */ }
            perform action a1 { doc /* support short-range transfers @S088 */ }
            perform action a2 { doc /* support a local response @S621 */ }
            perform action a3 { doc /* assigned close-in support @S644 */ }
        }
        part decisionRecords : DecisionRecords {
            perform action a0 { doc /* capture the forecast basis, applicable limits, observed conditions, and the reason for proceeding, holding, or returning to port @S293 */ }
        }
        part deferredTaskRationale : DeferredTaskRationale {
            perform action a0 { doc /* supports later reprioritization @S286 */ }
        }
        part deliveredEnergy : DeliveredEnergy;
        part deliveryLocation : DeliveryLocation;
        part designatedAuthorizingRole : DesignatedAuthorizingRole {
            perform action a0 { doc /* grants permission @S165 */ }
        }
        part designatedGridConnectionPoint : DesignatedGridConnectionPoint;
        part discrepancy : Discrepancy {
            exhibit state modes {
                state s0 { doc /* unresolved @S575 */ }
            }
        }
        part dispatchRecord : DispatchRecord {
            perform action a0 { doc /* identifies the quantity, destination, handling conditions, and responsible receiving location @S708 */ }
        }
        part documentOwner : DocumentOwner {
            perform action a0 { doc /* schedules periodic review @S976 */ }
            perform action a1 { doc /* initiates an additional review @S976 */ }
        }
        part doorInterlocks : DoorInterlocks;
        part durationOfGridRelatedRestrictions : DurationOfGridRelatedRestrictions;
        part dutyPlanner : DutyPlanner {
            perform action a0 { doc /* prepare and review maintenance activities @S065 */ }
            perform action a1 { doc /* develops daily work priorities @S076 */ }
            perform action a2 { doc /* prepares the Transfer Manifest Addendum @S126 */ }
            perform action a3 { doc /* reviews the request for completeness @S153 */ }
            perform action a4 { doc /* assigns it to the appropriate planning queue @S153 */ }
            perform action a5 { doc /* resolves outstanding supply and scheduling issues @S164 */ }
            perform action a6 { doc /* submitting the request for authorization @S164 */ }
            perform action a7 { doc /* updates work priorities @S224 */ }
            perform action a8 { doc /* reviews the ranked queue @S247 */ }
            perform action a9 { doc /* confirms that urgent work has a clear technical basis and a feasible execution path @S247 */ }
            perform action a10 { doc /* considers Crew Transfer Vessel, Daughter Craft, Service Operations Vessel, and Helideck access @S258 */ }
            perform action a11 { doc /* selecting a mobilization method @S258 */ }
            perform action a12 { doc /* confirms the operating priority @S260 */ }
            perform action a13 { doc /* accounts for part availability, technician competence, and estimated task duration @S263 */ }
            perform action a14 { doc /* committing a work window @S263 */ }
            perform action a15 { doc /* revises priorities @S269 */ }
            perform action a16 { doc /* communicates the resulting plan to affected teams @S269 */ }
            perform action a17 { doc /* checks that the expected conditions remain within the limits @S274 */ }
            perform action a18 { doc /* adjusts the executable plan @S292 */ }
            perform action a19 { doc /* reviews accepted alerts @S304 */ }
            perform action a20 { doc /* submits a defined task scope, work location, crew, and requested operating window @S319 */ }
            perform action a21 { doc /* coordinates any revised work window with the relevant operational roles @S334 */ }
            perform action a22 { doc /* closes the work authorization @S340 */ }
            perform action a23 { doc /* considers active dispatch constraints @S388 */ }
            perform action a24 { doc /* scheduling work @S388 */ }
            perform action a25 { doc /* verifies that planned crew assignments match the approved work schedule @S396 */ }
            perform action a26 { doc /* confirms the inspection priority @S442 */ }
            perform action a27 { doc /* coordinates access with the Marine Coordinator or the Field Supervisor @S442 */ }
            perform action a28 { doc /* assigns a target repair window @S459 */ }
            perform action a29 { doc /* coordinates required personnel, equipment, and vessel capacity @S459 */ }
            perform action a30 { doc /* updates the maintenance record @S464 */ }
            perform action a31 { doc /* schedules follow-up inspection @S464 */ }
            perform action a32 { doc /* compares task readiness with the expected departure window @S469 */ }
            perform action a33 { doc /* committing crews and equipment to a marine campaign @S469 */ }
            perform action a34 { doc /* checks that the planned task matches the approved work authorization and that required personnel and equipment are available @S491 */ }
            perform action a35 { doc /* develops the proposed sequence with the Control Engineer @S515 */ }
            perform action a36 { doc /* identifies affected equipment and operating limits @S515 */ }
            perform action a37 { doc /* reassess the sequence @S519 */ }
            perform action a38 { doc /* obtain revised authorization @S519 */ }
            perform action a39 { doc /* records the proposed sequence, required approvals, execution roles, and planned communications in the operating record @S527 */ }
            perform action a40 { doc /* authorizes restoration or release of the work area @S536 */ }
            perform action a41 { doc /* records the final equipment state, approvals, deviations, and handover information for the incoming shift @S537 */ }
            perform action a42 { doc /* treats a confirmed restriction as a Grid Constraint @S539 */ }
            perform action a43 { doc /* records the revised operating basis @S553 */ }
            perform action a44 { doc /* coordinates updated targets @S553 */ }
            perform action a45 { doc /* maintains a clear record of the restriction, response actions, approvals, and outstanding checks for shift handover @S561 */ }
            perform action a46 { doc /* confirms that the recovery task does not conflict with other offshore work @S639 */ }
            perform action a47 { doc /* uses the Visibility Confidence Note @S669 */ }
            perform action a48 { doc /* reviews forecast demand against current stock @S695 */ }
            perform action a49 { doc /* confirming work readiness @S695 */ }
            perform action a50 { doc /* consolidates proposed work periods @S737 */ }
            perform action a51 { doc /* identifies tasks that require a change to substation configuration @S737 */ }
            perform action a52 { doc /* records actual start and finish times @S758 */ }
            perform action a53 { doc /* links relevant communications and work records to the applicable work package and operating plan @S779 */ }
            perform action a54 { doc /* confirms that the planned work can proceed within the lift capacity and operating limits @S872 */ }
            perform action a55 { doc /* uses reliability findings to adjust work priorities and planned maintenance intervals @S925 */ }
            perform action a56 { doc /* prioritize urgent safety work and maintainable generation capacity @S947 */ }
            perform action a57 { doc /* updates operating priorities and deferred work @S955 */ }
            perform action a58 { doc /* checks that maintenance priorities, resource plans, and operational constraints are reflected in planned work @S965 */ }
        }
        part eastServiceLift : EastServiceLift {
            perform action a0 { doc /* runs a door-interlock and overload check @S859 */ }
            perform action a1 { doc /* accepting a movement request @S859 */ }
        }
        part electricalRecoveryWork : ElectricalRecoveryWork;
        part electricalTechnician : ElectricalTechnician {
            perform action a0 { doc /* verifies protective device settings and transfer interlocks @S185 */ }
            perform action a1 { doc /* identifies the electrical sources, isolation points, and verification steps @S325 */ }
            perform action a2 { doc /* verifies the relevant local isolation @S327 */ }
            perform action a3 { doc /* secures the equipment against unintended energization @S327 */ }
            perform action a4 { doc /* proves the test instrument @S331 */ }
            perform action a5 { doc /* tests for absence of voltage @S331 */ }
            perform action a6 { doc /* proves the instrument again @S331 */ }
            perform action a7 { doc /* checks that the work area is ready for restoration @S336 */ }
            perform action a8 { doc /* reports any outstanding defects or restrictions @S336 */ }
            perform action a9 { doc /* supports fault diagnosis and maintenance @S363 */ }
            perform action a10 { doc /* coordinate any operational changes with the relevant duty role @S434 */ }
            perform action a11 { doc /* verifies electrical isolation at the work location @S496 */ }
            perform action a12 { doc /* verifies equipment labels @S529 */ }
            perform action a13 { doc /* confirms the intended switching points before execution @S529 */ }
            perform action a14 { doc /* isolates and protects recovered electrical equipment @S650 */ }
            perform action a15 { doc /* uses the boundary sketch to identify the approved isolation points @S716 */ }
            perform action a16 { doc /* starting the work @S716 */ }
            perform action a17 { doc /* confirms that the work scope and test requirements fit the approved duration @S750 */ }
            perform action a18 { doc /* performs local inspection @S801 */ }
            perform action a19 { doc /* verifies that the lift supply and protective devices show no active fault indication @S867 */ }
        }
        part emergencyDistributionBus : EmergencyDistributionBus;
        part emergencyGenerator : EmergencyGenerator {
            perform action a0 { doc /* supplies the designated emergency distribution bus @S180 */ }
            perform action a1 { doc /* produces the Start Test Trace @S353 */ }
            perform action a2 { doc /* confirm reliable backup starting and stable output @S355 */ }
            perform action a3 { doc /* fails to start or sustain its required load @S356 */ }
            perform action a4 { doc /* supports essential functions @S803 */ }
            perform action a5 { doc /* remain essential services during degraded operation @S945 */ }
        }
        part emergencyResponseOrganizations : EmergencyResponseOrganizations;
        part endTime : EndTime;
        part energyProductionMeasures : EnergyProductionMeasures;
        part entrant : Entrant {
            perform action a0 { doc /* presents an individually assigned credential for validation @S839 */ }
        }
        part entryBarrier : EntryBarrier {
            exhibit state modes {
                state s0 { doc /* closed @S846 */ }
            }
        }
        part eventInvestigations : EventInvestigations;
        part expectedCount : ExpectedCount;
        part expectedOperatingState : ExpectedOperatingState;
        part exportCableMonitor : ExportCableMonitor {
            perform action a0 { doc /* provides measurements that support assessment of the export path @S200 */ }
            perform action a1 { doc /* helps planners assess whether cable condition warrants inspection or corrective intervention @S252 */ }
        }
        part externalInterfaces : ExternalInterfaces;
        part farm : Farm {
            perform action a0 { doc /* exports electrical power through the Offshore Substation, Main Transformer, and export cable to the designated grid connection point @S199 */ }
            perform action a1 { doc /* reports measured active power at the grid boundary @S205 */ }
        }
        part farmMonitoringEnvironment : FarmMonitoringEnvironment;
        part fieldSupervisor : FieldSupervisor {
            perform action a0 { doc /* coordinates task execution offshore @S096 */ }
            perform action a1 { doc /* keeps the Duty Planner informed of changes to work progress @S096 */ }
            perform action a2 { doc /* considers remote observations alongside site conditions @S145 */ }
            perform action a3 { doc /* recommending follow-up work @S145 */ }
            perform action a4 { doc /* verifies that the approved conditions remain valid @S167 */ }
            perform action a5 { doc /* checks reported faults against available evidence @S253 */ }
            perform action a6 { doc /* identifies work that requires an offshore visit @S253 */ }
            perform action a7 { doc /* confirms that the proposed method, access arrangements, and work party are suitable for the task @S320 */ }
            perform action a8 { doc /* confirms that the permit is active and the required isolations have been independently verified @S329 */ }
            perform action a9 { doc /* briefs the crew on the permit limits, isolation boundaries, communications, and conditions requiring work to stop @S330 */ }
            perform action a10 { doc /* pause work and reassess the authorization @S333 */ }
            perform action a11 { doc /* confirms that tools, temporary connections, and personnel are clear @S335 */ }
            perform action a12 { doc /* requesting isolation removal @S335 */ }
            perform action a13 { doc /* confirms completion or formally records any remaining work @S340 */ }
            perform action a14 { doc /* confirms the work party is complete @S405 */ }
            perform action a15 { doc /* escalates any unexplained absence or overdue check-in to Marine Coordinator @S412 */ }
            perform action a16 { doc /* checks that cybersecurity requirements are included in the work briefing @S429 */ }
            perform action a17 { doc /* uses the Deferred Task Rationale @S430 */ }
            perform action a18 { doc /* confirms that close-access findings are documented @S457 */ }
            perform action a19 { doc /* reviews the worksite limits with the crew @S493 */ }
            perform action a20 { doc /* verifies each worker's authorization, competence, and fitness for the assigned task @S503 */ }
            perform action a21 { doc /* pauses the job @S509 */ }
            perform action a22 { doc /* confirms personnel are clear of affected equipment @S536 */ }
            perform action a23 { doc /* directs personnel at the affected work site @S615 */ }
            perform action a24 { doc /* maintains control of the work area @S649 */ }
            perform action a25 { doc /* stops handling @S649 */ }
            perform action a26 { doc /* reports remaining hazards @S660 */ }
            perform action a27 { doc /* confirms that temporary securing arrangements are adequate for transit @S660 */ }
            perform action a28 { doc /* briefs the crew on the boundary, access restrictions, and conditions that require work to stop @S717 */ }
            perform action a29 { doc /* confirms that every crew member understands the limits of the approved work area @S726 */ }
            perform action a30 { doc /* ensures that field observations and work outcomes are entered promptly @S778 */ }
            perform action a31 { doc /* confirms work party status @S809 */ }
            perform action a32 { doc /* reports unresolved personnel or access concerns @S809 */ }
            perform action a33 { doc /* reviews unusual denial patterns and unresolved access exceptions @S826 */ }
            perform action a34 { doc /* coordinates the inspection @S860 */ }
            perform action a35 { doc /* records the inspection result and any observed defects in the maintenance system @S869 */ }
            perform action a36 { doc /* confirms that no person is exposed to a suspended or shifting load during movement @S879 */ }
            perform action a37 { doc /* communicates the release status to the work party @S881 */ }
            perform action a38 { doc /* records the time that service is authorized @S881 */ }
            perform action a39 { doc /* confirms that the work authorization covers the intended landing and task @S886 */ }
            perform action a40 { doc /* verifies that the landing is accessible and that the route is clear of obstructions @S887 */ }
            perform action a41 { doc /* ensures that the lift is left secure and that any irregularity is reported through the established site process @S906 */ }
            perform action a42 { doc /* provides feedback on whether revised procedures and controls are practical during offshore work @S927 */ }
            perform action a43 { doc /* confirms that field execution practices and escalation routes are workable for offshore personnel @S970 */ }
        }
        part fieldTeam : FieldTeam {
            perform action a0 { doc /* use the same revision when confirming isolation status @S729 */ }
        }
        part fireDetectionPanel : FireDetectionPanel {
            perform action a0 { doc /* provides alarm indications @S629 */ }
            perform action a1 { doc /* supervises detection circuits @S786 */ }
            perform action a2 { doc /* annunciates alarms with location and fault information @S786 */ }
            perform action a3 { doc /* remain essential services during degraded operation @S945 */ }
        }
        part fleetDispatchConsole : FleetDispatchConsole {
            perform action a0 { doc /* supports the coordination of operational resources across the farm @S041 */ }
            perform action a1 { doc /* provides a fleet-level view of dispatch activity @S069 */ }
            perform action a2 { doc /* gives the Marine Coordinator a shared view of vessel assignments, planned movements, and dispatch status @S081 */ }
            perform action a3 { doc /* allocates requested farm output among available generating units @S203 */ }
            perform action a4 { doc /* uses the quality flag to support movement planning @S225 */ }
            perform action a5 { doc /* assigns vessel and crew resources to approved work packages @S260 */ }
            perform action a6 { doc /* compares the requested output with available turbine capability and known operating restrictions @S370 */ }
            perform action a7 { doc /* retains the instruction history and the corresponding plant response @S385 */ }
            perform action a8 { doc /* supports coordinated adjustment of turbine output across the affected operating area @S543 */ }
            perform action a9 { doc /* provides a fleet-level view of operating status and response to emerging constraints @S917 */ }
            perform action a10 { doc /* presents operational restrictions @S947 */ }
            exhibit state modes {
                state s0 { doc /* Weather Hold @S259 */ }
            }
        }
        part gate : Gate {
            exhibit state modes {
                state s0 { doc /* secured @S816 */ }
            }
        }
        part gridConstraint : GridConstraint {
            perform action a0 { doc /* may require reduced export, revised dispatch, or temporary disconnection @S210 */ }
            perform action a1 { doc /* require the requested window to be shortened, moved, or divided into separate periods @S746 */ }
            exhibit state modes {
                state s0 { doc /* active @S376 */ }
            }
        }
        part gridDispatch : GridDispatch;
        part gridDispatcher : GridDispatcher {
            perform action a0 { doc /* sets external dispatch requirements within the applicable connection agreement @S202 */ }
            perform action a1 { doc /* issues active-power targets and ramp instructions @S367 */ }
            perform action a2 { doc /* confirms applicable grid requirements and any restrictions on changing the connection state @S518 */ }
            perform action a3 { doc /* receives the Export Limit Advisory @S541 */ }
            perform action a4 { doc /* set the permitted export level @S541 */ }
            perform action a5 { doc /* confirms that the requested period is compatible with export requirements and network operating limits @S739 */ }
            perform action a6 { doc /* communicates external operating requirements to the Grid Interface Relay and the responsible control personnel @S769 */ }
        }
        part gridInterfaceRelay : GridInterfaceRelay {
            perform action a0 { doc /* provides status indications @S190 */ }
            perform action a1 { doc /* defines the operational boundary between the offshore farm and the external transmission system @S197 */ }
            perform action a2 { doc /* exchanges authorized operating signals with the transmission system at the agreed interface @S201 */ }
            perform action a3 { doc /* maintains the farm's dispatch boundary @S221 */ }
            perform action a4 { doc /* allowing local systems to manage turbine-level operation @S221 */ }
            perform action a5 { doc /* produces an Export Limit Advisory @S372 */ }
            perform action a6 { doc /* applies the accepted export ceiling to control outputs @S373 */ }
            perform action a7 { doc /* records its effective time for audit @S373 */ }
            perform action a8 { doc /* retains its protection settings @S551 */ }
            perform action a9 { doc /* remains available for the required protection and control functions @S743 */ }
            perform action a10 { doc /* applies the configured response to a Grid Constraint @S942 */ }
            exhibit state modes {
                state s0 { doc /* Grid Constraint @S942 */ }
                state s1 { doc /* available @S743 */ }
            }
        }
        part hSEOfficer : HSEOfficer {
            perform action a0 { doc /* verifies that work arrangements account for applicable safety controls and personnel responsibilities @S095 */ }
            perform action a1 { doc /* reviews the proposed controls @S157 */ }
            perform action a2 { doc /* produces the Harness Audit Card @S237 */ }
            perform action a3 { doc /* reviews hazards @S266 */ }
            perform action a4 { doc /* confirms that proposed controls match the task scope and site conditions @S266 */ }
            perform action a5 { doc /* reviews task hazards @S322 */ }
            perform action a6 { doc /* confirms that required controls are assigned @S322 */ }
            perform action a7 { doc /* verifies that personnel expected at the work site are accounted for @S408 */ }
            perform action a8 { doc /* reviews the work method, exposure controls, and emergency arrangements @S451 */ }
            perform action a9 { doc /* checks that access controls, emergency arrangements, and handling precautions are suitable for the planned activity @S481 */ }
            perform action a10 { doc /* checks that emergency routes, muster points, and rescue arrangements are understood by everyone at the worksite @S505 */ }
            perform action a11 { doc /* reviews task hazards @S526 */ }
            perform action a12 { doc /* confirms that required controls are in place @S526 */ }
            perform action a13 { doc /* assesses any safety implications @S579 */ }
            perform action a14 { doc /* advises whether the affected activity can continue @S579 */ }
            perform action a15 { doc /* advises on personnel hazards, rescue procedures, and the use of emergency equipment @S617 */ }
            perform action a16 { doc /* reviews the handling method, lifting points, and exclusion zones @S647 */ }
            perform action a17 { doc /* advises on exposure, evacuation, and re-entry criteria @S808 */ }
            perform action a18 { doc /* use the recorded entry history to support personnel accountability @S827 */ }
            perform action a19 { doc /* reviews any proposed workaround @S949 */ }
            perform action a20 { doc /* evaluates safety controls, emergency arrangements, and lessons from reported events @S967 */ }
        }
        part helideck : Helideck {
            perform action a0 { doc /* is used for evacuation @S623 */ }
        }
        part incidentLead : IncidentLead {
            perform action a0 { doc /* classifies each report @S432 */ }
            perform action a1 { doc /* assigns an owner @S432 */ }
            perform action a2 { doc /* records its time, scope, and current status @S432 */ }
            perform action a3 { doc /* confirms that the threat is contained and the affected system is suitable for return to service @S436 */ }
            perform action a4 { doc /* verifies headcounts with the teams involved @S619 */ }
        }
        part incomingSupervisor : IncomingSupervisor;
        part incomingTeam : IncomingTeam {
            perform action a0 { doc /* independently checks the boundary status @S731 */ }
        }
        part inspectionRecord : InspectionRecord {
            perform action a0 { doc /* identifies the uncertainty @S456 */ }
            perform action a1 { doc /* specifies additional measurements or imagery needed @S456 */ }
        }
        part inspector : Inspector {
            perform action a0 { doc /* confirms that the car floor and landing thresholds are clear of loose material and standing water @S862 */ }
            perform action a1 { doc /* checks the operating controls for damage, legibility, and secure mounting @S865 */ }
            perform action a2 { doc /* confirms that the rated capacity and operating instructions remain legible at the car entrance @S868 */ }
        }
        part installationTeam : InstallationTeam {
            perform action a0 { doc /* verifies the scanner, barrier, and communications @S853 */ }
        }
        part inventoryRecord : InventoryRecord;
        part isolationBoundary : IsolationBoundary {
            perform action a0 { doc /* defines the equipment and energy sources @S711 */ }
        }
        part lighting : Lighting;
        part localVisualIndicator : LocalVisualIndicator {
            perform action a0 { doc /* communicates whether entry is permitted or denied @S845 */ }
        }
        part lowStockAlert : LowStockAlert {
            perform action a0 { doc /* identify items approaching their reorder point @S701 */ }
            perform action a1 { doc /* show open purchase commitments @S701 */ }
        }
        part mainTransformer : MainTransformer {
            exhibit state modes {
                state s0 { doc /* subject to their separate engineering approval process @S604 */ }
            }
        }
        part maintenancePlanningEngine : MaintenancePlanningEngine {
            perform action a0 { doc /* supports the preparation and sequencing of maintenance activities @S042 */ }
            perform action a1 { doc /* supports work preparation by organizing maintenance needs, resource considerations, and planning constraints @S054 */ }
            perform action a2 { doc /* supports planning decisions @S066 */ }
            perform action a3 { doc /* can use reviewed condition information when prioritizing future maintenance activities @S148 */ }
            perform action a4 { doc /* can use reviewed condition information when prioritizing future maintenance activities @S154 */ }
            perform action a5 { doc /* schedules inspections and corrective work @S188 */ }
            perform action a6 { doc /* schedules periodic reviews of standby electrical maintenance requirements and outstanding corrective work @S195 */ }
            perform action a7 { doc /* uses the Squall Window Bulletin when reviewing the timing of planned work @S213 */ }
            perform action a8 { doc /* ranks planned and corrective work using asset condition, safety exposure, production impact, access feasibility, and resource availability @S246 */ }
            perform action a9 { doc /* produces the Deferred Task Rationale @S285 */ }
            perform action a10 { doc /* receives validated condition information @S308 */ }
            perform action a11 { doc /* combines inspection intervals, prior defect history, and turbine availability @S441 */ }
            perform action a12 { doc /* propose survey dates @S441 */ }
            perform action a13 { doc /* uses the assessed severity, defect growth rate, weather exposure, and production impact to support repair prioritization @S458 */ }
            perform action a14 { doc /* presenting task duration, resource demand, and dependency status @S470 */ }
            perform action a15 { doc /* provides the planned work period @S520 */ }
            perform action a16 { doc /* identifies dependencies with other scheduled tasks @S520 */ }
            perform action a17 { doc /* review whether the constraint affects planned work or equipment availability @S554 */ }
            perform action a18 { doc /* identify tasks that may be rescheduled @S670 */ }
            perform action a19 { doc /* uses planned work demand and part criticality to support replenishment forecasts @S694 */ }
            perform action a20 { doc /* checks task durations, dependencies, and resource assumptions @S738 */ }
            perform action a21 { doc /* supports review of planned work, resource demand, and maintenance completion performance @S918 */ }
            perform action a22 { doc /* separates safety-critical work from tasks that can safely wait @S948 */ }
        }
        part maintenanceRecords : MaintenanceRecords;
        part maintenanceSystem : MaintenanceSystem;
        part marineActivity : MarineActivity {
            exhibit state modes {
                state s0 { doc /* Weather Hold @S086 */ }
            }
        }
        part marineCoordination : MarineCoordination {
            perform action a0 { doc /* aligns vessel movements, personnel transfers, and shore-side support with the approved work schedule @S222 */ }
        }
        part marineCoordinator : MarineCoordinator {
            perform action a0 { doc /* considers offshore conditions and vessel availability @S068 */ }
            perform action a1 { doc /* coordinating access to work sites @S068 */ }
            perform action a2 { doc /* aligns vessel availability with crew readiness, port access, and the planned work locations @S077 */ }
            perform action a3 { doc /* coordinate the Crew Transfer Vessel, the Service Operations Vessel, and the Daughter Craft @S082 */ }
            perform action a4 { doc /* uses the available traffic picture @S141 */ }
            perform action a5 { doc /* checks that the planned access method and timing are practical for the work location @S160 */ }
            perform action a6 { doc /* maintains the daily marine plan @S223 */ }
            perform action a7 { doc /* resolves conflicts between planned activities @S223 */ }
            perform action a8 { doc /* records changes to the movement plan @S245 */ }
            perform action a9 { doc /* ensures that affected teams receive the update @S245 */ }
            perform action a10 { doc /* compares expected access conditions with vessel capability, transit time, and worksite limits @S257 */ }
            perform action a11 { doc /* coordinates resource changes with the Vessel Master and affected work teams @S261 */ }
            perform action a12 { doc /* reviews access options and vessel availability @S277 */ }
            perform action a13 { doc /* reassesses the route @S283 */ }
            perform action a14 { doc /* seeks an updated forecast @S290 */ }
            perform action a15 { doc /* confirming a departure or transfer plan @S290 */ }
            perform action a16 { doc /* reviews the intended crew movement against vessel capacity and operating conditions @S397 */ }
            perform action a17 { doc /* monitors reported vessel movements @S400 */ }
            perform action a18 { doc /* reviews return movements @S410 */ }
            perform action a19 { doc /* maintains a rolling view of berth occupancy, planned arrivals, departure estimates, and vessel service requirements @S466 */ }
            perform action a20 { doc /* uses the Berth Slot Confirmation @S473 */ }
            perform action a21 { doc /* align an approved vessel arrival with the assigned berth window @S473 */ }
            perform action a22 { doc /* resolves competing berth requests by considering task urgency, vessel compatibility, and the consequences of delay @S483 */ }
            perform action a23 { doc /* reviews safe alternatives such as a later slot, a different suitable berth, or vessel standby @S488 */ }
            perform action a24 { doc /* suspends access @S499 */ }
            perform action a25 { doc /* aligns vessel movements with the approved access plan and operational constraints @S523 */ }
            perform action a26 { doc /* establishes the expected personnel count and destination for each movement @S565 */ }
            perform action a27 { doc /* pauses further personnel transfers @S576 */ }
            perform action a28 { doc /* informs the Shore Control Room of the discrepancy and the immediate control actions @S578 */ }
            perform action a29 { doc /* escalates any unresolved discrepancy to the Duty Planner @S583 */ }
            perform action a30 { doc /* records the time of escalation @S583 */ }
            perform action a31 { doc /* confirms that the count is reconciled or an authorized response is in place @S585 */ }
            perform action a32 { doc /* maintains awareness of vessel locations, access constraints, and available marine support @S618 */ }
            perform action a33 { doc /* assigns suitable vessels @S638 */ }
            perform action a34 { doc /* maintains a common plan for their approach and departure @S638 */ }
            perform action a35 { doc /* pauses the recovery @S659 */ }
            perform action a36 { doc /* agrees a safe holding position with the Vessel Master @S659 */ }
            perform action a37 { doc /* reviews how uncertainty affects the planned transit, transfer location, and available alternatives @S676 */ }
            perform action a38 { doc /* reassess the route and the suitability of continuing toward the work site @S682 */ }
            perform action a39 { doc /* checks vessel movements and crew transfer timing against the proposed period @S749 */ }
            perform action a40 { doc /* shares relevant marine and weather information @S764 */ }
            perform action a41 { doc /* confirm that personnel and vessels can remain safely accounted for @S944 */ }
            perform action a42 { doc /* reviews vessel coordination arrangements @S966 */ }
            perform action a43 { doc /* verifies that marine responsibilities are understood @S966 */ }
        }
        part metoceanBuoy : MetoceanBuoy {
            perform action a0 { doc /* measures wind speed and direction, wave height and period, current, air temperature, and barometric pressure @S102 */ }
            perform action a1 { doc /* produces the Wave Burst Record @S194 */ }
            perform action a2 { doc /* reports local sea conditions @S231 */ }
            perform action a3 { doc /* provide contextual conditions @S309 */ }
            perform action a4 { doc /* provide measured conditions @S443 */ }
            perform action a5 { doc /* provides site measurements @S625 */ }
            perform action a6 { doc /* provides a local reference @S665 */ }
            perform action a7 { doc /* provide inputs @S766 */ }
        }
        part metoceanObservations : MetoceanObservations;
        part monitoringRules : MonitoringRules {
            perform action a0 { doc /* identify unusual login patterns, unexpected configuration changes, and communications outside approved operating windows @S418 */ }
        }
        part nacelleConditionMonitor : NacelleConditionMonitor {
            perform action a0 { doc /* provides equipment measurements @S132 */ }
            perform action a1 { doc /* provides condition data @S250 */ }
            perform action a2 { doc /* provides condition information @S793 */ }
            perform action a3 { doc /* supports assessment of equipment condition and emerging degradation @S915 */ }
        }
        part needDate : NeedDate;
        part northAccessScanner : NorthAccessScanner {
            perform action a0 { doc /* records authorized entry at the north access point @S235 */ }
            perform action a1 { doc /* records identity checks at the north shore access point @S394 */ }
            perform action a2 { doc /* records personnel access events at the north access point @S569 */ }
            perform action a3 { doc /* validates each presented credential against current access authorization @S810 */ }
            perform action a4 { doc /* enabling controlled entry @S810 */ }
            perform action a5 { doc /* accepts only credentials that can be read reliably @S811 */ }
        }
        part observedCount : ObservedCount;
        part occupants : Occupants {
            perform action a0 { doc /* remain inside the car and avoid interfering with the controls or doors @S899 */ }
            perform action a1 { doc /* use the designated alarm or communication method and remain inside the car @S902 */ }
            perform action a2 { doc /* exit without crowding @S905 */ }
        }
        part offshoreSubstation : OffshoreSubstation {
            perform action a0 { doc /* provides the farm's offshore electrical collection and switching environment @S037 */ }
            perform action a1 { doc /* maintains the designated emergency distribution bus within its approved operating limits @S189 */ }
            perform action a2 { doc /* sends a Transformer Tap Snapshot @S267 */ }
            perform action a3 { doc /* confirm that the approved switching window is available for the planned work @S752 */ }
            perform action a4 { doc /* enters Substation Degraded @S941 */ }
            exhibit state modes {
                state s0 { doc /* Substation Degraded @S361,S941 */ }
                state s1 { doc /* normal operation @S173 */ }
            }
        }
        part offshoreWindFarm : OffshoreWindFarm {
            perform action a0 { doc /* generate electricity reliably @S009 */ }
            perform action a1 { doc /* operates in a variable marine environment @S028 */ }
            exhibit state modes {
                state s0 { doc /* construction control @S015 */ }
                state s1 { doc /* operations control @S015 */ }
            }
        }
        part onDutyOperationsLead : OnDutyOperationsLead;
        part onboardLogger : OnboardLogger {
            perform action a0 { doc /* timestamps observations @S104 */ }
            perform action a1 { doc /* retains a local history during intermittent communications @S104 */ }
        }
        part operatingOrganization : OperatingOrganization {
            perform action a0 { doc /* uses defined handoffs @S098 */ }
        }
        part operationalAndTechnicalRepresentatives : OperationalAndTechnicalRepresentatives {
            perform action a0 { doc /* Proposed revisions are checked by affected operational and technical representatives @S978 */ }
        }
        part operationalPersonnel : OperationalPersonnel {
            perform action a0 { doc /* retain authority for decisions that require procedural, safety, or engineering judgment @S073 */ }
        }
        part operationalSystem : OperationalSystem;
        part operationsRadioConsole : OperationsRadioConsole {
            perform action a0 { doc /* supports routine communications and escalation @S239 */ }
            perform action a1 { doc /* supports communications between the Shore Control Room, vessels, and offshore work teams @S627 */ }
            perform action a2 { doc /* supports voice communication with the Crew Transfer Vessel, Service Operations Vessel, and Daughter Craft @S762 */ }
            perform action a3 { doc /* provides a coordinated communications channel @S806 */ }
        }
        part operationsTeam : OperationsTeam {
            perform action a0 { doc /* relies on them for control decisions @S558 */ }
        }
        part operator : Operator {
            perform action a0 { doc /* records test results @S356 */ }
            perform action a1 { doc /* raises a defect promptly @S356 */ }
            perform action a2 { doc /* operating a breaker or isolator @S359 */ }
            perform action a3 { doc /* verifies the required clearances @S359 */ }
            perform action a4 { doc /* confirms that affected parties are informed @S359 */ }
            perform action a5 { doc /* limits further switching @S360 */ }
            perform action a6 { doc /* escalates the condition @S360 */ }
            perform action a7 { doc /* places the Offshore Substation in Substation Degraded @S361 */ }
            perform action a8 { doc /* communicates the resulting restrictions @S361 */ }
            perform action a9 { doc /* records its scope, start time, and expected review point @S376 */ }
            perform action a10 { doc /* confirms that export equipment remains within its approved operating range @S549 */ }
            perform action a11 { doc /* positions each load to avoid obstructing doors, controls, and emergency access @S878 */ }
            perform action a12 { doc /* checks the lift identification, rated capacity, and current service status before each operating period @S888 */ }
            perform action a13 { doc /* confirms that the car floor is level with the boarding landing before permitting entry or exit @S890 */ }
            perform action a14 { doc /* checks that the controls respond correctly and that the emergency stop is accessible @S892 */ }
            perform action a15 { doc /* confirms that the expected load, including tools and carried equipment, remains within the rated capacity @S895 */ }
            perform action a16 { doc /* confirms that all occupants are ready and that the doors are fully closed @S898 */ }
            perform action a17 { doc /* starting movement @S898 */ }
            perform action a18 { doc /* monitors lift movement for unusual noise, vibration, hesitation, or irregular stopping @S900 */ }
            perform action a19 { doc /* stop the lift at the nearest safe landing when practicable @S901 */ }
            perform action a20 { doc /* confirms that the car is level and stationary @S904 */ }
            perform action a21 { doc /* opening the doors @S904 */ }
            perform action a22 { doc /* checks that tools and equipment have been removed from the car @S905 */ }
            perform action a23 { doc /* periodically evaluates whether assurance arrangements provide sufficient evidence that the concept remains effective @S983 */ }
        }
        part operators : Operators {
            perform action a0 { doc /* assess the fault @S184 */ }
            perform action a1 { doc /* preserve essential services @S184 */ }
            perform action a2 { doc /* restore the normal supply @S184 */ }
            perform action a3 { doc /* verify the scanner clock and connectivity @S832 */ }
            perform action a4 { doc /* assess the scope and duration of the impairment @S935 */ }
        }
        part organization : Organization {
            perform action a0 { doc /* retains voice recordings, system logs, and work records @S782 */ }
        }
        part outgoingSupervisor : OutgoingSupervisor {
            perform action a0 { doc /* briefs the incoming supervisor on site conditions, access status, and outstanding hazards @S512 */ }
        }
        part passengers : Passengers {
            perform action a0 { doc /* distribute themselves and their equipment to avoid obstructing the doors or control panel @S896 */ }
        }
        part permitReviewers : PermitReviewers;
        part person : Person {
            perform action a0 { doc /* presents the credential at the controlled entry point @S812 */ }
            perform action a1 { doc /* waits for the scanner response @S812 */ }
        }
        part personnel : Personnel {
            perform action a0 { doc /* confirm their identity @S393 */ }
            perform action a1 { doc /* entering controlled shore access areas @S393 */ }
            perform action a2 { doc /* report any change in destination or transfer plan @S402 */ }
            perform action a3 { doc /* enter the work area @S405 */ }
            perform action a4 { doc /* report their arrival and departure at each active work location @S406 */ }
            perform action a5 { doc /* disembark at shore @S411 */ }
            perform action a6 { doc /* report suspected compromise, lost credentials, and unexplained equipment behavior @S431 */ }
            perform action a7 { doc /* approach the rotor @S451 */ }
            perform action a8 { doc /* leave the work area @S457 */ }
            perform action a9 { doc /* board a vessel @S482 */ }
            perform action a10 { doc /* use the North Access Scanner or South Access Scanner at the designated entry point @S501 */ }
            perform action a11 { doc /* Personnel movements do not resume @S585 */ }
            perform action a12 { doc /* use the approved fallback method @S771 */ }
            perform action a13 { doc /* report the outage as soon as practicable @S771 */ }
            perform action a14 { doc /* investigate a fire alarm @S802 */ }
            perform action a15 { doc /* complete post-event checks @S802 */ }
            perform action a16 { doc /* follow posted escape routes @S804 */ }
            perform action a17 { doc /* muster at the designated assembly point @S804 */ }
            perform action a18 { doc /* follow the approved contingency process @S828 */ }
            perform action a19 { doc /* use an approved alternative entry process @S856 */ }
            perform action a20 { doc /* do not attempt to open doors or climb out of a stopped car without direction from the response team @S903 */ }
            perform action a21 { doc /* receive appropriate communication or training before the change takes effect @S981 */ }
        }
        part personnelTrackingConsole : PersonnelTrackingConsole {
            perform action a0 { doc /* represents the personnel location and accountability function @S047 */ }
            perform action a1 { doc /* helps the organization maintain an accurate view of personnel assigned to offshore activities @S094 */ }
            perform action a2 { doc /* maintains the offshore personnel roster and expected return times @S234 */ }
            perform action a3 { doc /* supports confirmation that personnel assigned to the task are accounted for at the work location @S332 */ }
            perform action a4 { doc /* maintains the current accountability status @S392 */ }
            perform action a5 { doc /* maintains the operational count for active marine movements @S571 */ }
            perform action a6 { doc /* update a verified personnel total @S573 */ }
            perform action a7 { doc /* supports personnel accounting @S619 */ }
            perform action a8 { doc /* supports confirmation that all assigned personnel have returned to a safe location @S648 */ }
            perform action a9 { doc /* supports accountability checks @S805 */ }
            perform action a10 { doc /* maintain an accurate record of personnel entering and leaving the route @S874 */ }
        }
        part personsStillUnaccountedFor : PersonsStillUnaccountedFor;
        part pitchSystem : PitchSystem {
            perform action a0 { doc /* changes blade angle in response to turbine control commands and local protection logic @S130 */ }
            perform action a1 { doc /* adjusts blade angle within its operating envelope @S546 */ }
            perform action a2 { doc /* moves the blades to the defined safe position @S790 */ }
            exhibit state modes {
                state s0 { doc /* emergency shutdown @S790 */ }
            }
        }
        part portAgent : PortAgent {
            perform action a0 { doc /* supports shore-side arrangements for vessel calls, crew access, and staged cargo @S093 */ }
            perform action a1 { doc /* coordinates port services @S240 */ }
            perform action a2 { doc /* confirms that planned departures can be supported @S240 */ }
            perform action a3 { doc /* issues the Berth Slot Confirmation @S324 */ }
        }
        part portStagingAreas : PortStagingAreas;
        part portSupport : PortSupport;
        part productionLostDuringDowntime : ProductionLostDuringDowntime;
        part protectiveDevices : ProtectiveDevices;
        part qualifiedTechnician : QualifiedTechnician {
            perform action a0 { doc /* checks the device at the point of isolation @S719 */ }
        }
        part receiver : Receiver {
            perform action a0 { doc /* repeats critical details @S773 */ }
        }
        part record : Record;
        part remoteSessions : RemoteSessions;
        part repairableUnits : RepairableUnits;
        part replenishmentRequest : ReplenishmentRequest;
        part requester : Requester {
            perform action a0 { doc /* identifies the equipment affected @S152 */ }
            perform action a1 { doc /* describes the intended work @S152 */ }
        }
        part requiredQuantity : RequiredQuantity;
        part rescueCoordinator : RescueCoordinator {
            perform action a0 { doc /* maintains the response arrangements for incidents involving vessels or personnel @S244 */ }
            perform action a1 { doc /* leads rescue planning @S614 */ }
            perform action a2 { doc /* coordinates requests for external assistance @S614 */ }
            perform action a3 { doc /* revises the response plan @S634 */ }
            perform action a4 { doc /* establishes the recovery objective @S637 */ }
            perform action a5 { doc /* confirms who has authority to suspend the operation @S637 */ }
            perform action a6 { doc /* uses the load sheet to confirm that recovery baskets are secured and their contents are accounted for @S646 */ }
        }
        part responsibleAuthority : ResponsibleAuthority {
            perform action a0 { doc /* confirms that the equipment and work area are safe for subsequent activity @S657 */ }
            perform action a1 { doc /* approves restoration @S732 */ }
        }
        part responsibleManager : ResponsibleManager {
            perform action a0 { doc /* reviews record completeness after significant events @S784 */ }
            perform action a1 { doc /* assigns correction or follow-up actions where evidence is missing @S784 */ }
        }
        part responsibleOperationalAuthority : ResponsibleOperationalAuthority {
            perform action a0 { doc /* confirms that conditions permit work to proceed @S500 */ }
        }
        part responsibleOperator : ResponsibleOperator {
            perform action a0 { doc /* confirmed that the equipment is stable @S952 */ }
        }
        part responsiblePersonnel : ResponsiblePersonnel {
            perform action a0 { doc /* confirm that operations can resume safely @S086 */ }
        }
        part responsibleSupervisor : ResponsibleSupervisor {
            perform action a0 { doc /* keeps a local record @S413 */ }
            perform action a1 { doc /* reports it when service is restored @S413 */ }
        }
        part responsibleTeam : ResponsibleTeam {
            perform action a0 { doc /* reports completion status and outstanding issues @S170 */ }
            perform action a1 { doc /* verifies turbine isolation, rotor restraint, access arrangements, and rescue provisions @S450 */ }
        }
        part reviewTeams : ReviewTeams {
            perform action a0 { doc /* distinguish equipment faults from external causes such as access limitations, weather conditions, and grid restrictions @S922 */ }
        }
        part riskAssessments : RiskAssessments;
        part rotorBrakeUnit : RotorBrakeUnit {
            perform action a0 { doc /* applies braking @S791 */ }
        }
        part sCADAEngineer : SCADAEngineer {
            perform action a0 { doc /* maintains the configuration and technical integrity of supervisory interfaces @S062 */ }
            perform action a1 { doc /* use individually assigned accounts rather than shared credentials for interactive work @S423 */ }
            perform action a2 { doc /* validates restored configurations and communications @S437 */ }
            perform action a3 { doc /* investigates telemetry gaps or inconsistent measurements @S558 */ }
            perform action a4 { doc /* uses the Firmware Hash Attestation to verify the approved image @S593 */ }
            perform action a5 { doc /* loading a release @S593 */ }
            perform action a6 { doc /* investigates missing or inconsistent indications @S946 */ }
            perform action a7 { doc /* verifies that status, alarms, and command feedback are consistent across the available control views @S954 */ }
            perform action a8 { doc /* reviews monitoring and control assumptions @S968 */ }
        }
        part sCADAGateway : SCADAGateway {
            perform action a0 { doc /* provides a controlled boundary for supervisory data exchange between offshore assets and shore-based operations @S052 */ }
            perform action a1 { doc /* mediates supervisory exchanges @S059 */ }
            perform action a2 { doc /* supports consistent access to operational information @S059 */ }
            perform action a3 { doc /* remains responsible for supervisory communications within its defined control scope @S114 */ }
            perform action a4 { doc /* presents turbine status and control availability to authorized shore personnel @S133 */ }
            perform action a5 { doc /* uses the deviation notice to flag work packages that may require technical review @S159 */ }
            perform action a6 { doc /* provide current operational status to permit reviewers @S171 */ }
            perform action a7 { doc /* presents supply alarms and generator status to the Shore Control Room @S192 */ }
            perform action a8 { doc /* provides relay status and interface measurements to the farm monitoring environment @S211 */ }
            perform action a9 { doc /* produces the Session Revocation Receipt @S212 */ }
            perform action a10 { doc /* forwards time-stamped observations @S295 */ }
            perform action a11 { doc /* provides the operational measurements @S369 */ }
            perform action a12 { doc /* records security-relevant access and control events for review @S417 */ }
            perform action a13 { doc /* provides operating data @S447 */ }
            perform action a14 { doc /* presents current generation, export, and equipment status to the operations team @S540 */ }
            perform action a15 { doc /* carries operational data to the Shore Control Room @S767 */ }
            perform action a16 { doc /* preserves source timestamps @S767 */ }
            perform action a17 { doc /* supports alarm visibility at the shore operating position @S800 */ }
            perform action a18 { doc /* provides operational records used to assess turbine availability and production trends @S914 */ }
            perform action a19 { doc /* preserves available status and alarm information @S946 */ }
        }
        part sender : Sender {
            perform action a0 { doc /* confirms that the read-back is accurate @S773 */ }
        }
        part serviceOperationsVessel : ServiceOperationsVessel {
            perform action a0 { doc /* may support offshore work @S045 */ }
            perform action a1 { doc /* provides a platform for work that needs longer offshore presence or broader onboard support @S089 */ }
            perform action a2 { doc /* provides a stable offshore base @S228 */ }
            perform action a3 { doc /* provide a more stable work platform @S281 */ }
            perform action a4 { doc /* prepares the Recovery Basket Load Sheet @S461 */ }
            perform action a5 { doc /* provide accommodation, medical support, and a stable platform @S622 */ }
            perform action a6 { doc /* provides a stable working platform @S645 */ }
            perform action a7 { doc /* maintain a safe stand-off @S680 */ }
        }
        part serviceableParts : ServiceableParts;
        part shiftHandover : ShiftHandover {
            perform action a0 { doc /* records outstanding isolations, affected equipment, and any restrictions that remain in force @S730 */ }
        }
        part shiftRecords : ShiftRecords {
            perform action a0 { doc /* capture dispatch instructions, constraint decisions, measured response, and unresolved follow-up actions @S389 */ }
        }
        part shoreBasedPlanning : ShoreBasedPlanning;
        part shoreControlRoom : ShoreControlRoom {
            perform action a0 { doc /* continuous monitoring and dispatch coordination @S013 */ }
            perform action a1 { doc /* provides a shore-based operating location for authorized personnel @S040 */ }
            perform action a2 { doc /* monitoring and coordinating wind farm operations @S056 */ }
            perform action a3 { doc /* provides a shared operational context for personnel responsible for offshore assets @S064 */ }
            perform action a4 { doc /* maintains operational oversight @S097 */ }
            perform action a5 { doc /* provides a point of coordination for shore-based personnel @S097 */ }
            perform action a6 { doc /* maintains operational oversight @S099 */ }
            perform action a7 { doc /* provides a point of coordination for shore-based personnel @S099 */ }
            perform action a8 { doc /* provides a staffed location for supervisory control and operational review @S134 */ }
            perform action a9 { doc /* coordinates operational notices and control-room decisions affecting the farm interface @S214 */ }
            perform action a10 { doc /* maintains an overview of active marine operations and operational restrictions @S238 */ }
            perform action a11 { doc /* escalates an alert @S303 */ }
            perform action a12 { doc /* retains the decision record, supporting observations, and response outcome @S317 */ }
            perform action a13 { doc /* retains the permit status, isolation history, test results, and restoration decision @S339 */ }
            perform action a14 { doc /* receives concise status updates @S364 */ }
            perform action a15 { doc /* maintains the current dispatch target, ramp rate, and next review time in the shift record @S371 */ }
            perform action a16 { doc /* uses the tap snapshot to check the recorded transformer position @S374 */ }
            perform action a17 { doc /* maintains the last validated operating limit @S386 */ }
            perform action a18 { doc /* seeking clarification through the approved channel @S386 */ }
            perform action a19 { doc /* maintains an operational view of affected systems @S420 */ }
            perform action a20 { doc /* coordinates immediate protective actions @S420 */ }
            perform action a21 { doc /* monitors turbine status @S448 */ }
            perform action a22 { doc /* records any operating restrictions required during the remote survey @S448 */ }
            perform action a23 { doc /* sends the Switching Window Acknowledgment @S531 */ }
            perform action a24 { doc /* confirms that monitoring and operator procedures remain suitable for the revised configuration @S606 */ }
            perform action a25 { doc /* maintains the incident log @S613 */ }
            perform action a26 { doc /* provides a single operational point of contact for offshore teams @S613 */ }
            perform action a27 { doc /* maintains awareness of the decision and the operational restrictions @S683 */ }
            perform action a28 { doc /* coordination point for routine operational messages @S761 */ }
            perform action a29 { doc /* assesses incoming alarms @S798 */ }
            perform action a30 { doc /* confirms the affected asset @S798 */ }
            perform action a31 { doc /* initiates the response appropriate to the reported severity @S798 */ }
            perform action a32 { doc /* monitors the loss of visibility @S937 */ }
            perform action a33 { doc /* applies the approved operating concept @S963 */ }
        }
        part shorePersonnel : ShorePersonnel {
            perform action a0 { doc /* anticipate vessel arrivals @S410 */ }
        }
        part signs : Signs {
            perform action a0 { doc /* identify the permitted approach @S852 */ }
            perform action a1 { doc /* direct personnel to the controlled entry point @S852 */ }
        }
        part southAccessScanner : SouthAccessScanner {
            perform action a0 { doc /* records authorized entry at the south access point @S236 */ }
            perform action a1 { doc /* records identity checks at the south shore access point @S395 */ }
            perform action a2 { doc /* records personnel access events at the south access point @S570 */ }
            perform action a3 { doc /* checks that the authorization is active for the scheduled work period @S813 */ }
            perform action a4 { doc /* checks that the requested access area is within the person's approved scope @S814 */ }
            perform action a5 { doc /* verify a credential or retrieve the required authorization information @S816 */ }
            perform action a6 { doc /* displays a clear outcome @S831 */ }
            perform action a7 { doc /* serves the designated southern entry route to the offshore wind farm @S835 */ }
            perform action a8 { doc /* applies the same identity verification standard @S838 */ }
            perform action a9 { doc /* checks that the credential is active and belongs to the person presenting it @S840 */ }
            perform action a10 { doc /* records each successful entry and each denied attempt with a time reference @S843 */ }
            exhibit state modes {
                state s0 { doc /* unavailable @S828,S856 */ }
            }
        }
        part southernEntryRoute : SouthernEntryRoute {
            exhibit state modes {
                state s0 { doc /* in service @S853 */ }
                state s1 { doc /* out of service @S855 */ }
            }
        }
        part sparesHub : SparesHub {
            perform action a0 { doc /* provides a separate view of stock held for regional replenishment and emergency support @S689 */ }
        }
        part staleOrImplausibleValue : StaleOrImplausibleValue {
            exhibit state modes {
                state s0 { doc /* unverified @S300 */ }
            }
        }
        part startTime : StartTime;
        part stationServiceTransformers : StationServiceTransformers {
            perform action a0 { doc /* supply the facility's auxiliary electrical loads from the medium-voltage collection system @S173 */ }
        }
        part storekeeper : Storekeeper {
            perform action a0 { doc /* checks requested materials against available stock @S092 */ }
            perform action a1 { doc /* coordinates replenishment with the Spares Hub @S092 */ }
            perform action a2 { doc /* prepares requested equipment for dispatch @S242 */ }
            perform action a3 { doc /* uses the exception slip to validate an unavailable part @S262 */ }
            perform action a4 { doc /* checks repair materials and tooling against the approved repair method @S460 */ }
            perform action a5 { doc /* checks that critical spares are available and that packaging is suitable for marine transport @S479 */ }
            perform action a6 { doc /* reconciles physical counts with recorded balances @S690 */ }
            perform action a7 { doc /* records adjustments with a reason and timestamp @S690 */ }
            perform action a8 { doc /* records unavailable quantities and the expected date of the next supply @S703 */ }
            perform action a9 { doc /* confirms that equipment intended for the lift is ready and properly identified for the work party @S876 */ }
        }
        part substationOperator : SubstationOperator {
            perform action a0 { doc /* confirms that switching actions affecting the export path are within the authorized work scope @S216 */ }
            perform action a1 { doc /* confirms local operating constraints @S268 */ }
            perform action a2 { doc /* applies authorized switching actions @S326 */ }
            perform action a3 { doc /* records the resulting equipment state @S326 */ }
            perform action a4 { doc /* removes isolations only under the approved switching process @S337 */ }
            perform action a5 { doc /* records each restoration action @S337 */ }
            perform action a6 { doc /* maintains the Offshore Substation within approved operating limits @S342 */ }
            perform action a7 { doc /* follows current switching instructions @S342 */ }
            perform action a8 { doc /* reviews alarms, active restrictions, equipment status, and handover notes @S343 */ }
            perform action a9 { doc /* checks Main Transformer temperatures, cooling equipment, oil indications, and abnormal noise against established limits @S345 */ }
            perform action a10 { doc /* verifies that personnel access records are consistent with the planned work and current site occupancy @S351 */ }
            perform action a11 { doc /* confirms fuel level, starting battery condition, ventilation, and readiness of the Emergency Generator for loss of normal supply @S354 */ }
            perform action a12 { doc /* coordinates switching activity @S382 */ }
            perform action a13 { doc /* confirms that switching conditions affecting the worksite are understood by the relevant personnel @S497 */ }
            perform action a14 { doc /* verifies equipment status and switching points at the Offshore Substation @S517 */ }
            perform action a15 { doc /* accepts the instructions @S530 */ }
            perform action a16 { doc /* checking the equipment state @S530 */ }
            perform action a17 { doc /* confirming authorization with the Control Engineer @S530 */ }
            perform action a18 { doc /* uses the test trace to verify that the planned restoration checks have completed @S532 */ }
            perform action a19 { doc /* requesting the next switching step @S532 */ }
            perform action a20 { doc /* reports any substation limitation @S559 */ }
            perform action a21 { doc /* reviews the switching sequence @S741 */ }
            perform action a22 { doc /* confirms that each step can be performed within the available interval @S741 */ }
            perform action a23 { doc /* begin switching @S753 */ }
            perform action a24 { doc /* reviews responsibilities and coordination arrangements for substation activities @S971 */ }
        }
        part substitution : Substitution;
        part supplyInterfaces : SupplyInterfaces;
        part switchingOperator : SwitchingOperator {
            perform action a0 { doc /* performs each authorized action @S533 */ }
            perform action a1 { doc /* reports completion @S533 */ }
        }
        part systemPart : System {
            perform action a0 { doc /* retains successful and unsuccessful attempts @S824 */ }
            perform action a1 { doc /* measures operational performance against approved service objectives and documented fleet baselines @S908 */ }
            perform action a2 { doc /* records the affected function, the detected condition, and the time of transition @S935 */ }
            perform action a3 { doc /* retains the event record and recovery decisions @S957 */ }
            exhibit state modes {
                state s0 { doc /* degraded mode @S934 */ }
            }
        }
        part systemArchitecture : SystemArchitecture {
            perform action a0 { doc /* separates offshore equipment, operational services, and shore-based decision functions @S051 */ }
        }
        part technicalReviewers : TechnicalReviewers {
            perform action a0 { doc /* confirm that the work scope is compatible with equipment condition and the planned maintenance method @S158 */ }
        }
        part technicalTeams : TechnicalTeams {
            perform action a0 { doc /* isolate only the affected connection or service @S433 */ }
            perform action a1 { doc /* review causes, response effectiveness, and corrective actions with operations management @S439 */ }
        }
        part technicians : Technicians;
        part temporaryPersonnel : TemporaryPersonnel {
            perform action a0 { doc /* follow the same identity checks as other entrants @S849 */ }
        }
        part transaction : Transaction {
            perform action a0 { doc /* records the credential identifier, decision time, access point, and decision outcome @S821 */ }
            perform action a1 { doc /* records the authorization version and the rule that determined the outcome @S822 */ }
        }
        part transmissionSystem : TransmissionSystem;
        part turbine : Turbine {
            exhibit state modes {
                state s0 { doc /* Turbine Lockout @S657,S940 */ }
                state s1 { doc /* approved operating state @S444 */ }
            }
        }
        part turbineController : TurbineController {
            perform action a0 { doc /* performs local turbine control functions @S060 */ }
            perform action a1 { doc /* produces the Pitch Deviation Notice @S061 */ }
            perform action a2 { doc /* adjusts turbine output within approved operating limits @S127 */ }
            perform action a3 { doc /* blocks commands that conflict with active protection conditions @S127 */ }
            perform action a4 { doc /* executes authorized control actions @S129 */ }
            perform action a5 { doc /* reports its operating state through established control interfaces @S129 */ }
            perform action a6 { doc /* enters its configured safe operating mode @S191 */ }
            perform action a7 { doc /* adjusts output in accordance with validated plant commands and local equipment protections @S377 */ }
            perform action a8 { doc /* applies the accepted output target @S545 */ }
            perform action a9 { doc /* retaining its protective control functions @S545 */ }
            perform action a10 { doc /* initiates the configured shutdown response @S789 */ }
            perform action a11 { doc /* retains protective control locally @S937 */ }
            exhibit state modes {
                state s0 { doc /* safe operating mode @S191 */ }
            }
        }
        part turbineLockout : TurbineLockout {
            perform action a0 { doc /* prevents remote restart @S802 */ }
        }
        part turbineSensorBus : TurbineSensorBus {
            perform action a0 { doc /* provides operating measurements @S251 */ }
            perform action a1 { doc /* collects operating measurements @S294 */ }
            perform action a2 { doc /* carries equipment status @S788 */ }
        }
        part turbines : Turbines;
        part urgentPurchase : UrgentPurchase;
        part users : Users {
            perform action a0 { doc /* report unusual noise, vibration, door behavior, or control response immediately @S882 */ }
        }
        part vesselAISReceiver : VesselAISReceiver {
            perform action a0 { doc /* produces a Position Quality Flag @S105 */ }
            perform action a1 { doc /* collects vessel position broadcasts @S139 */ }
            perform action a2 { doc /* maintains a time-stamped view of nearby vessel movements @S140 */ }
            perform action a3 { doc /* provides vessel position information @S288 */ }
            perform action a4 { doc /* provides vessel position information @S401 */ }
        }
        part vesselCrews : VesselCrews;
        part vesselMaster : VesselMaster {
            perform action a0 { doc /* retains authority for navigation, vessel safety, and decisions about whether a transfer can proceed @S079 */ }
            perform action a1 { doc /* evaluates local conditions before departure @S085 */ }
            perform action a2 { doc /* continues to reassess them during the voyage @S085 */ }
            perform action a3 { doc /* confirms that the vessel plan can support the approved personnel and equipment transfer @S161 */ }
            perform action a4 { doc /* confirms departure readiness @S226 */ }
            perform action a5 { doc /* reports any change that could affect the passage @S226 */ }
            perform action a6 { doc /* receives the Transfer Manifest Addendum @S278 */ }
            perform action a7 { doc /* considers the approach and transfer conditions acceptable @S279 */ }
            perform action a8 { doc /* pause or abort an approach @S284 */ }
            perform action a9 { doc /* produces the Crew Count Correction @S390 */ }
            perform action a10 { doc /* confirms the departure roster @S398 */ }
            perform action a11 { doc /* records crew changes that occur during transit or between offshore locations @S403 */ }
            perform action a12 { doc /* maintains an onboard count @S409 */ }
            perform action a13 { doc /* confirms practical arrival and departure estimates against the vessel's operating limits @S476 */ }
            perform action a14 { doc /* confirms that the vessel is safely positioned and that transfer conditions remain acceptable @S498 */ }
            perform action a15 { doc /* confirms that the vessel can meet the agreed timing and maintain safe operating margins @S524 */ }
            perform action a16 { doc /* verifies the number of people physically aboard @S567 */ }
            perform action a17 { doc /* maintains a safe operating position @S577 */ }
            perform action a18 { doc /* retains authority over vessel safety, navigation, and decisions to approach or withdraw from a casualty @S616 */ }
            perform action a19 { doc /* withdraw @S634 */ }
            perform action a20 { doc /* retains authority over vessel movements @S642 */ }
            perform action a21 { doc /* decline a task that cannot be completed safely @S642 */ }
            perform action a22 { doc /* retains authority to proceed, slow, alter course, or hold position @S677 */ }
            perform action a23 { doc /* reassess the route and the suitability of continuing toward the work site @S682 */ }
            perform action a24 { doc /* confirms safety-critical instructions using the agreed read-back procedure @S763 */ }
            perform action a25 { doc /* maintains a safe position and readiness to support personnel recovery @S807 */ }
            perform action a26 { doc /* confirm that personnel and vessels can remain safely accounted for @S944 */ }
        }
        part vesselRecoverySupport : VesselRecoverySupport {
            perform action a0 { doc /* coordinates people, vessels, and handling equipment @S636 */ }
        }
        part visitors : Visitors {
            perform action a0 { doc /* follow the same identity checks as other entrants @S849 */ }
        }
        part warehouseSystem : WarehouseSystem {
            perform action a0 { doc /* records stock status @S091 */ }
            perform action a1 { doc /* supports preparation of equipment and consumables for scheduled work @S091 */ }
            perform action a2 { doc /* produces a Backorder Exception Slip @S163 */ }
            perform action a3 { doc /* records stock movements @S241 */ }
            perform action a4 { doc /* makes current inventory information available for logistics planning @S241 */ }
            perform action a5 { doc /* supports cargo preparation @S478 */ }
            perform action a6 { doc /* arrange receiving space @S655 */ }
            perform action a7 { doc /* preserve traceability for equipment returned ashore @S655 */ }
            perform action a8 { doc /* maintains the authoritative item catalogue, stock balances, and storage locations @S687 */ }
            perform action a9 { doc /* uses recurring failure and repair information to inform review of critical spares and replenishment assumptions @S928 */ }
        }
        part weatherAnalyst : WeatherAnalyst {
            perform action a0 { doc /* reviews available forecasts @S084 */ }
            perform action a1 { doc /* advises the Marine Coordinator on conditions that may affect marine operations @S084 */ }
            perform action a2 { doc /* reviews forecast limitations @S107 */ }
            perform action a3 { doc /* identifies conditions that may affect vessel access or turbine work @S107 */ }
            perform action a4 { doc /* reviews forecast changes @S232 */ }
            perform action a5 { doc /* advises the Marine Coordinator @S232 */ }
            perform action a6 { doc /* reviews forecast confidence @S256 */ }
            perform action a7 { doc /* highlights conditions that could invalidate a planned access period @S256 */ }
            perform action a8 { doc /* compares forecast data with recent observations @S272 */ }
            perform action a9 { doc /* advising on the reliability of a work window @S272 */ }
            perform action a10 { doc /* uses the Wave Burst Record to assess whether the planned access period remains suitable @S323 */ }
            perform action a11 { doc /* produces the Visibility Confidence Note @S472 */ }
            perform action a12 { doc /* summarize confidence in visibility conditions for near-term port and offshore planning @S472 */ }
            perform action a13 { doc /* reviews the forecast @S522 */ }
            perform action a14 { doc /* advises the Duty Planner if conditions could affect the planned sequence @S522 */ }
            perform action a15 { doc /* interprets forecast uncertainty @S626 */ }
            perform action a16 { doc /* communicates material changes to the Rescue Coordinator @S626 */ }
            perform action a17 { doc /* interprets forecast uncertainty @S641 */ }
            perform action a18 { doc /* identifies conditions that could affect safe vessel handling @S641 */ }
            perform action a19 { doc /* assesses forecast uncertainty @S765 */ }
            perform action a20 { doc /* communicates conditions that could affect access, lifting, or work at height @S765 */ }
            perform action a21 { doc /* support entry into Weather Hold @S939 */ }
        }
        part weatherHold : WeatherHold {
            perform action a0 { doc /* prevents mobilization @S259 */ }
        }
        part weatherService : WeatherService {
            perform action a0 { doc /* contributes environmental information to operational planning and coordination @S067 */ }
            perform action a1 { doc /* produces the Squall Window Bulletin @S083 */ }
            perform action a2 { doc /* uses validated environmental observations in forecast products for offshore planning @S106 */ }
            perform action a3 { doc /* issues forecast updates @S128 */ }
            perform action a4 { doc /* provides forecast information for marine planning @S230 */ }
            perform action a5 { doc /* supplies forecast information @S255 */ }
            perform action a6 { doc /* provides forecast conditions and confidence information @S270 */ }
            perform action a7 { doc /* provide contextual conditions @S309 */ }
            perform action a8 { doc /* provide forecasts @S443 */ }
            perform action a9 { doc /* supplies forecast conditions relevant to access and safe execution @S521 */ }
            perform action a10 { doc /* provides forecast information for planning @S624 */ }
            perform action a11 { doc /* provides current forecasts for the recovery area and the planned transit route @S640 */ }
            perform action a12 { doc /* provides context for expected changes @S664 */ }
            perform action a13 { doc /* provide inputs @S766 */ }
            perform action a14 { doc /* support entry into Weather Hold @S939 */ }
        }
        part weatherServices : WeatherServices;
        part westServiceLift : WestServiceLift {
            perform action a0 { doc /* provides vertical access along the west route between the designated service landings @S884 */ }
            exhibit state modes {
                state s0 { doc /* removed from service @S907 */ }
            }
        }
        part workParty : WorkParty {
            perform action a0 { doc /* confirms equipment identity using permanent labels and the current site designation @S720 */ }
        }
        part workPermitPortal : WorkPermitPortal {
            perform action a0 { doc /* support controlled and secure operations @S049 */ }
            perform action a1 { doc /* supports authorization processes that govern work under controlled conditions @S070 */ }
            perform action a2 { doc /* maintains the request record and its revision history @S155 */ }
            perform action a3 { doc /* records review decisions @S162 */ }
            perform action a4 { doc /* returns incomplete requests to the requester @S162 */ }
            perform action a5 { doc /* records the start, pause, resumption, and completion of authorized work against the permit record @S169 */ }
            perform action a6 { doc /* supports readiness checks for work requiring controlled access or electrical isolation @S265 */ }
            perform action a7 { doc /* block permit release @S321 */ }
            perform action a8 { doc /* produces the Isolation Boundary Sketch @S492 */ }
            perform action a9 { doc /* makes the approved boundary available to the work party and the control team @S713 */ }
            perform action a10 { doc /* retains the current approval @S728 */ }
            perform action a11 { doc /* makes superseded versions unavailable for active work @S728 */ }
            perform action a12 { doc /* retains permit decisions and associated approvals @S780 */ }
        }
        part workforceInterfaces : WorkforceInterfaces;
        flow f0 of InputItem from fieldSupervisor to dutyPlanner { doc /* @S076 */ }
        flow f1 of InputItem from maintenancePlanningEngine to dutyPlanner { doc /* @S076 */ }
        flow f2 of SharedViewOfVesselAssignmentsPlannedMovementsAndDispatchStatusItem from fleetDispatchConsole to marineCoordinator { doc /* @S081 */ }
        flow f4 of AdviceOnConditionsItem from weatherAnalyst to marineCoordinator { doc /* @S084 */ }
        flow f5 of ChangesToWorkProgressItem from fieldSupervisor to dutyPlanner { doc /* @S096 */ }
        flow f6 of EnvironmentalObservationsItem from metoceanBuoy to weatherService { doc /* @S106 */ }
        flow f7 of TurbineStatusAndControlAvailabilityItem from sCADAGateway to authorizedShorePersonnel { doc /* @S133 */ }
        flow f8 of TrafficPictureItem from vesselAISReceiver to marineCoordinator { doc /* @S141 */ }
        flow f9 of RemoteObservationsItem from bladeInspectionDrone to fieldSupervisor { doc /* @S145 */ }
        flow f10 of PitchDeviationNoticeItem from turbineController to sCADAGateway { doc /* @S159 */ }
        flow f11 of IncompleteRequestsItem from workPermitPortal to requester { doc /* @S162 */ }
        flow f12 of CurrentOperationalStatusItem from sCADAGateway to permitReviewers { doc /* @S171 */ }
        flow f13 of EmergencyPowerItem from emergencyGenerator to emergencyDistributionBus { doc /* @S180 */ }
        flow f14 of SupplyAlarmsAndGeneratorStatusItem from sCADAGateway to shoreControlRoom { doc /* @S192 */ }
        flow f15 of ElectricalPowerItem from farm to designatedGridConnectionPoint { doc /* @S199 */ }
        flow f16 of AuthorizedOperatingSignalsItem from gridInterfaceRelay to transmissionSystem { doc /* @S201 */ }
        flow f17 of RelayStatusAndInterfaceMeasurementsItem from sCADAGateway to farmMonitoringEnvironment { doc /* @S211 */ }
        flow f18 of SquallWindowBulletinItem from weatherService to maintenancePlanningEngine { doc /* @S213 */ }
        flow f19 of PositionQualityFlagItem from vesselAISReceiver to fleetDispatchConsole { doc /* @S225 */ }
        flow f20 of ForecastUpdatesItem from weatherService to weatherAnalyst { doc /* @S232 */ }
        flow f22 of UpdateItem from marineCoordinator to affectedTeams { doc /* @S245 */ }
        flow f23 of ResourceChangesItem from marineCoordinator to vesselMaster { doc /* @S261 */ }
        flow f24 of BackorderExceptionSlipItem from warehouseSystem to storekeeper { doc /* @S262 */ }
        flow f25 of ResultingPlanItem from dutyPlanner to affectedTeams { doc /* @S269 */ }
        flow f26 of ForecastDataItem from weatherService to weatherAnalyst { doc /* @S272 */ }
        flow f27 of OperatingMeasurementsItem from turbineController to turbineSensorBus { doc /* @S294 */ }
        flow f28 of OperatingMeasurementsItem from pitchSystem to turbineSensorBus { doc /* @S294 */ }
        flow f29 of OperatingMeasurementsItem from converterCabinet to turbineSensorBus { doc /* @S294 */ }
        flow f30 of OperatingMeasurementsItem from nacelleConditionMonitor to turbineSensorBus { doc /* @S294 */ }
        flow f31 of TimeStampedObservationsItem from sCADAGateway to shoreControlRoom { doc /* @S295 */ }
        flow f32 of IndependentSignalsItem from turbineController to controlEngineer { doc /* @S299 */ }
        flow f33 of IndependentSignalsItem from nacelleConditionMonitor to controlEngineer { doc /* @S299 */ }
        flow f34 of HarnessAuditCardItem from hSEOfficer to crewTransferVessel { doc /* @S312 */ }
        flow f35 of AlertItem from shoreControlRoom to controlEngineer { doc /* @S316 */ }
        flow f36 of WaveBurstRecordItem from metoceanBuoy to weatherAnalyst { doc /* @S323 */ }
        flow f37 of PermitLimitsIsolationBoundariesCommunicationsAndConditionsRequiringWorkToStopItem from fieldSupervisor to crew { doc /* @S330 */ }
        flow f38 of ActivePowerTargetsAndRampInstructionsItem from gridDispatcher to controlEngineer { doc /* @S368 */ }
        flow f39 of TransformerTapSnapshotItem from offshoreSubstation to shoreControlRoom { doc /* @S374 */ }
        flow f40 of ChangeInDestinationOrTransferPlanItem from personnel to vesselMaster { doc /* @S402 */ }
        flow f41 of UnexplainedAbsenceOrOverdueCheckInItem from fieldSupervisor to marineCoordinator { doc /* @S412 */ }
        flow f42 of AlertItem from shoreControlRoom to cybersecurityAnalyst { doc /* @S419 */ }
        flow f43 of UrgentConcernsItem from cybersecurityAnalyst to onDutyOperationsLead { doc /* @S419 */ }
        flow f44 of DeferredTaskRationaleItem from maintenancePlanningEngine to fieldSupervisor { doc /* @S430 */ }
        flow f45 of LeadingEdgeTileImageItem from bladeInspectionDrone to bladeSpecialist { doc /* @S445 */ }
        flow f46 of TurbineStatusAndControlAvailabilityItem from sCADAGateway to shoreControlRoom { doc /* @S448 */ }
        flow f47 of TaskDurationResourceDemandAndDependencyStatusItem from maintenancePlanningEngine to dutyPlanner { doc /* @S470 */ }
        flow f48 of BerthSlotConfirmationItem from portAgent to marineCoordinator { doc /* @S473 */ }
        flow f49 of SiteConditionsAccessStatusAndOutstandingHazardsItem from outgoingSupervisor to incomingSupervisor { doc /* @S512 */ }
        flow f50 of ForecastConditionsItem from weatherService to weatherAnalyst { doc /* @S522 */ }
        flow f51 of WeatherAdviceItem from weatherAnalyst to dutyPlanner { doc /* @S522 */ }
        flow f52 of SwitchingInstructionsItem from controlEngineer to substationOperator { doc /* @S530 */ }
        flow f53 of StartTestTraceItem from emergencyGenerator to substationOperator { doc /* @S532 */ }
        flow f54 of CurrentGenerationExportAndEquipmentStatusItem from sCADAGateway to operationsTeam { doc /* @S540 */ }
        flow f55 of ExportLimitAdvisoryItem from gridInterfaceRelay to gridDispatcher { doc /* @S541 */ }
        flow f56 of CrewCountCorrectionItem from vesselMaster to personnelTrackingConsole { doc /* @S573 */ }
        flow f57 of DiscrepancyAndTheImmediateControlActionsItem from marineCoordinator to shoreControlRoom { doc /* @S578 */ }
        flow f58 of UnresolvedDiscrepancyItem from marineCoordinator to dutyPlanner { doc /* @S583 */ }
        flow f59 of UnresolvedDiscrepancyItem from marineCoordinator to shiftHandover { doc /* @S586 */ }
        flow f60 of FirmwareHashAttestationItem from cybersecurityAnalyst to sCADAEngineer { doc /* @S593 */ }
        flow f61 of MaterialChangesItem from weatherAnalyst to rescueCoordinator { doc /* @S626 */ }
        flow f62 of ForecastsItem from weatherService to weatherAnalyst { doc /* @S641 */ }
        flow f63 of VisibilityConfidenceNoteItem from weatherAnalyst to dutyPlanner { doc /* @S669 */ }
        flow f64 of ApprovedBoundaryItem from workPermitPortal to workParty { doc /* @S713 */ }
        flow f65 of ApprovedBoundaryItem from workPermitPortal to controlTeam { doc /* @S713 */ }
        flow f66 of IsolationBoundarySketchItem from workPermitPortal to electricalTechnician { doc /* @S716 */ }
        flow f67 of BoundaryAccessRestrictionsAndConditionsThatRequireWorkToStopItem from fieldSupervisor to crew { doc /* @S717 */ }
        flow f68 of RemainingOperationalLimitationItem from controlEngineer to personnel { doc /* @S734 */ }
        flow f69 of PlannedWorkPeriodItem from maintenancePlanningEngine to dutyPlanner { doc /* @S737 */ }
        flow f70 of SwitchingWindowAcknowledgmentItem from shoreControlRoom to offshoreSubstation { doc /* @S752 */ }
        flow f71 of RelevantMarineAndWeatherInformationItem from marineCoordinator to dutyPlanner { doc /* @S764 */ }
        flow f72 of OperationalDataItem from sCADAGateway to shoreControlRoom { doc /* @S767 */ }
        flow f73 of ExternalOperatingRequirementsItem from gridDispatcher to gridInterfaceRelay { doc /* @S769 */ }
        flow f74 of AlarmsWithLocationAndFaultInformationItem from fireDetectionPanel to shoreControlRoom { doc /* @S798 */ }
        flow f75 of UnresolvedPersonnelOrAccessConcernsItem from fieldSupervisor to shoreControlRoom { doc /* @S809 */ }
        flow f76 of CredentialItem from person to southAccessScanner { doc /* @S812 */ }
        flow f78 of InspectionResultAndObservedDefectsItem from fieldSupervisor to maintenanceSystem { doc /* @S869 */ }
        flow f79 of ReleaseStatusItem from fieldSupervisor to workParty { doc /* @S881 */ }
        flow f80 of OperationalRestrictionsItem from fleetDispatchConsole to dutyPlanner { doc /* @S947 */ }
        flow f81 of TheTransferManifestAddendumItem from dutyPlanner to vesselMaster { doc /* joined @S126,S278 */ }
        flow f82 of TheSessionRevocationReceiptItem from sCADAGateway to cybersecurityGateway { doc /* joined @S212,S357 */ }
        flow f83 of TheRecoveryBasketLoadSheetItem from serviceOperationsVessel to rescueCoordinator { doc /* joined @S461,S646 */ }
    }
    requirement def R0 { doc /* Safety objectives require work to be authorized, hazards to be controlled, and personnel and vessels to be accounted for throughout each operation. @S011 */ subject s : OffshoreWindFarm; }
    requirement def R1 { doc /* Juniper Vale shall provide current operational status to permit reviewers when requested as part of the authorization check. @S171 */ subject s : SCADAGateway; }
    requirement def R2 { doc /* Where a turbine response is required, the Control Engineer follows the approved operating procedure and confirms the resulting state through available indications. @S305 */ subject s : ControlEngineer; }
    requirement def R3 { doc /* Larkspur shall repeat a close-range pass when image coverage is insufficient to assess the suspected surface condition. @S314 */ subject s : BladeInspectionDrone; }
    requirement def R4 { doc /* Redoubt shall block permit release until required risk reviews and isolation references are complete. @S321 */ subject s : WorkPermitPortal; }
    requirement def R5 { doc /* A change in equipment condition, task scope, or operating constraint requires the Field Supervisor to pause work and reassess the authorization. @S333 */ subject s : FieldSupervisor; }
    requirement def R6 { doc /* Remote sessions require approved connection paths, strong authentication, and active supervision when they can affect live operations. @S427 */ subject s : RemoteSessions; }
    requirement def R7 { doc /* Port staging areas are reserved for equipment that must be inspected, secured, or transferred before sailing. @S477 */ subject s : PortStagingAreas; }
    requirement def R8 { doc /* A Grid Constraint requires the Duty Planner to reassess the sequence and obtain revised authorization before work proceeds. @S519 */ subject s : DutyPlanner; }
    requirement def R9 { doc /* Electrical recovery work requires qualified personnel, verified isolation, and a safe means of access before hands-on activity begins. @S631 */ subject s : ElectricalRecoveryWork; }
    requirement def R10 { doc /* A Daughter Craft operation requires particular caution where reduced visibility could compromise separation from other vessels or structures. @S679 */ subject s : DaughterCraft; }
    requirement def R11 { doc /* Substitutions require engineering acceptance and confirmation that the alternative meets the required interface and operating limits. @S704 */ subject s : Substitution; }
    requirement def R12 { doc /* Urgent purchases require documented authorization and retain the same traceability and inspection controls as routine receipts. @S707 */ subject s : UrgentPurchase; }
    requirement def R13 { doc /* equipment and energy sources must be made safe before field work begins @S711 */ subject s : IsolationBoundary; }
    requirement def R14 { doc /* adjacent equipment must remain energized or available for service @S715 */ subject s : AdjacentEquipment; }
    requirement def R15 { doc /* The Substation Operator does not begin switching until the window is active and operational authority has been confirmed. @S753 */ subject s : SubstationOperator; }
    requirement def R16 { doc /* requires a named approver and a recorded reason for any temporary access decision @S829 */ subject s : ContingencyProcess; }
    requirement def R17 { doc /* Personnel must not hold the barrier open for another entrant. @S847 */ subject s : Personnel; }
    requirement def R18 { doc /* Lighting inside the car and at each landing must be adequate for safe movement and inspection. @S891 */ subject s : Lighting; }
    requirement def R19 { doc /* Door interlocks and other protective devices must be functional before the lift is placed in service. @S893 */ subject s : DoorInterlocks; }
    requirement def R20 { doc /* Protective devices must not be bypassed to maintain access or avoid delay. @S894 */ subject s : ProtectiveDevices; }
    requirement def R21 { doc /* Any unexpected movement or control response requires the operator to stop the lift at the nearest safe landing when practicable. @S901 */ subject s : Operator; }
}
