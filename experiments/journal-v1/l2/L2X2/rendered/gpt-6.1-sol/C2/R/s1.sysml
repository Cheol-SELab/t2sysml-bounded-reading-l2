package L2Model {
    item def AccessRestrictionsItem { doc /* @S717 */ }
    item def AccessStatusItem { doc /* @S512 */ }
    item def ActiveFaultIndicationItem { doc /* @S867 */ }
    item def ActivePowerTargetsItem { doc /* @S367 */ }
    item def AlarmIndicationsItem { doc /* @S629 */ }
    item def AlarmsItem { doc /* @S297 */ }
    item def AuthorizedOperatingSignalsItem { doc /* @S201 */ }
    item def BackorderExceptionSlipItem { doc /* @S262 */ }
    item def BerthSlotConfirmationItem { doc /* @S473 */ }
    item def ChangeInDestinationOrTransferPlanItem { doc /* @S402 */ }
    item def ChangesToWorkProgressItem { doc /* @S096 */ }
    item def CompletionItem { doc /* @S533 */ }
    item def ConciseStatusUpdatesItem { doc /* @S364 */ }
    item def ConditionsThatMayAffectMarineOperationsItem { doc /* @S084 */ }
    item def ConditionsThatRequireWorkToStopItem { doc /* @S717 */ }
    item def ConfidenceInformationItem { doc /* @S270,S289 */ }
    item def ContextForExpectedChangesItem { doc /* @S664 */ }
    item def ContextualConditionsItem { doc /* @S309 */ }
    item def ControlAvailabilityItem { doc /* @S133 */ }
    item def CriticalDetailsItem { doc /* @S773 */ }
    item def CurrentGenerationItem { doc /* @S540 */ }
    item def CurrentOperationalStatusItem { doc /* @S171 */ }
    item def DeferredTaskRationaleItem { doc /* @S430 */ }
    item def DependencyStatusItem { doc /* @S470 */ }
    item def DirectReportsItem { doc /* @S629 */ }
    item def DiscrepanciesItem { doc /* @S578,S583 */ }
    item def ElectricalPowerItem { doc /* @S199 */ }
    item def EquipmentStatusItem { doc /* @S540,S788 */ }
    item def ExportItem { doc /* @S540 */ }
    item def ExternalOperatingRequirementsItem { doc /* @S769 */ }
    item def ForecastConditionsItem { doc /* @S270,S521,S522 */ }
    item def ForecastDataItem { doc /* @S272 */ }
    item def GeneratorStatusItem { doc /* @S192 */ }
    item def HarnessAuditCardItem { doc /* @S312 */ }
    item def ImmediateControlActionsItem { doc /* @S578 */ }
    item def IncomingAlarmsItem { doc /* @S798 */ }
    item def IncompleteRequestsItem { doc /* @S162 */ }
    item def IndependentSignalsItem { doc /* @S299 */ }
    item def InputItem { doc /* @S076 */ }
    item def InterfaceMeasurementsItem { doc /* @S211 */ }
    item def IsolationBoundaryItem { doc /* @S713,S717 */ }
    item def IsolationBoundarySketchItem { doc /* @S716 */ }
    item def LeadingEdgeTileImageItem { doc /* @S445 */ }
    item def LocalReferenceItem { doc /* @S665 */ }
    item def MaterialChangesItem { doc /* @S626 */ }
    item def NextInstructionItem { doc /* @S533 */ }
    item def ObservationsItem { doc /* @S104,S271,S272,S280 */ }
    item def OperatingMeasurementsItem { doc /* @S294 */ }
    item def OperationalDataItem { doc /* @S767 */ }
    item def OperationalRestrictionsItem { doc /* @S947 */ }
    item def OutstandingHazardsItem { doc /* @S512 */ }
    item def OverdueCheckInItem { doc /* @S412 */ }
    item def PitchDeviationNoticeItem { doc /* @S159 */ }
    item def PlannedWorkPeriodItem { doc /* @S520 */ }
    item def PositionQualityFlagItem { doc /* @S225 */ }
    item def RampInstructionsItem { doc /* @S367 */ }
    item def RecoveryBasketLoadSheetItem { doc /* @S646 */ }
    item def RelayStatusItem { doc /* @S211 */ }
    item def ReleaseStatusItem { doc /* @S881 */ }
    item def RelevantMarineAndWeatherInformationItem { doc /* @S764 */ }
    item def RemainingHazardsItem { doc /* @S660 */ }
    item def RemainingOperationalLimitationItem { doc /* @S734 */ }
    item def ResourceDemandItem { doc /* @S470 */ }
    item def ResultingPlanItem { doc /* @S269 */ }
    item def SessionRevocationReceiptItem { doc /* @S357 */ }
    item def SharedViewOfVesselAssignmentsPlannedMovementsAndDispatchStatusItem { doc /* @S081,S082 */ }
    item def SiteConditionsItem { doc /* @S512 */ }
    item def SquallWindowBulletinItem { doc /* @S213 */ }
    item def StartTestTraceItem { doc /* @S532 */ }
    item def SupplyAlarmsItem { doc /* @S192 */ }
    item def SwitchingInstructionsItem { doc /* @S530 */ }
    item def SwitchingWindowAcknowledgmentItem { doc /* @S531,S752 */ }
    item def TaskDurationItem { doc /* @S470 */ }
    item def TechnicalGuidanceItem { doc /* @S658 */ }
    item def TimeStampedObservationsItem { doc /* @S295 */ }
    item def TimelyClearAndTraceableInformationItem { doc /* @S760 */ }
    item def TransferManifestAddendumItem { doc /* @S278 */ }
    item def TransformerTapSnapshotItem { doc /* @S374 */ }
    item def TurbineControlCommandsItem { doc /* @S130 */ }
    item def TurbineStatusItem { doc /* @S133 */ }
    item def UnexplainedAbsenceItem { doc /* @S412 */ }
    item def UnresolvedPersonnelOrAccessConcernsItem { doc /* @S809 */ }
    item def UpdateItem { doc /* @S245 */ }
    item def UrgentConcernsItem { doc /* @S419 */ }
    item def ValidatedEnvironmentalObservationsItem { doc /* @S106 */ }
    item def VisibilityItem { doc /* @S662 */ }
    item def WaveBurstRecordItem { doc /* @S323 */ }
    part def AbnormalCondition { doc /* @S768 */ }
    part def AccessConditions { doc /* @S224 */ }
    part def AccessRecords { doc /* @S825 */ }
    part def AccountabilityRecords { doc /* @S414 */ }
    part def AccountableOwner { doc /* @S959 */ }
    part def ActionsTaken { doc /* @S584 */ }
    part def ActiveRestrictions { doc /* @S871 */ }
    part def Activity { doc /* @S751 */ }
    part def ActualConditions { doc /* @S509,S755 */ }
    part def AdjacentEquipment { doc /* @S715 */ }
    part def AdministrativeAccess { doc /* @S115 */ }
    part def AffectedActivity { doc /* @S579 */ }
    part def AffectedEquipment { doc /* @S740,S953 */ }
    part def AffectedPersonnel { doc /* @S734 */ }
    part def AffectedServices { doc /* @S122 */ }
    part def AffectedTeams { doc /* @S245,S269 */ }
    part def Alarm { doc /* @S797 */ }
    part def AlarmPriorities { doc /* @S796 */ }
    part def AlarmThresholds { doc /* @S108 */ }
    part def Alternative { doc /* @S704 */ }
    part def AlternativeAccessMethod { doc /* @S292 */ }
    part def ApplicableHandlingRequirements { doc /* @S699 */ }
    part def Approval { doc /* @S714,S715 */ }
    part def ApprovedContingencyProcess { doc /* @S829 */ }
    part def ApprovedElectricalConfiguration { doc /* @S387 */ }
    part def ApprovedHandlingArrangement { doc /* @S877 */ }
    part def ApprovedProcedures { doc /* @S972 */ }
    part def ApprovedSwitchingWindow { doc /* @S753 */ }
    part def ApprovedWindow { doc /* @S740 */ }
    part def ApprovedWork { doc /* @S519 */ }
    part def Architecture { doc /* @S072 */ }
    part def Area { doc /* @S801 */ }
    part def AreasIdentifiedByTheSiteFireRiskAssessment { doc /* @S787 */ }
    part def AssetOperator { doc /* @S959 */ }
    part def AssuranceArrangements { doc /* @S983 */ }
    part def AssuranceEvidence { doc /* @S972 */ }
    part def Attempt { doc /* @S820 */ }
    part def AuditFindings { doc /* @S972 */ }
    part def AuditRecord { doc /* @S823 */ }
    part def Authority { doc /* @S122 */ }
    part def Authorization { doc /* @S813,S815,S823 */ }
    part def AuthorizationLifecycle { doc /* @S151 */ }
    part def AuthorizationProcesses { doc /* @S070 */ }
    part def AuthorizedPersonnel { doc /* @S358 */ }
    part def AuthorizedShorePersonnel { doc /* @S133 */ }
    part def AutomaticControls { doc /* @S177 */ }
    part def AuxiliaryElectricalLoads { doc /* @S173 */ }
    part def BackupPower { doc /* @S025 */ }
    part def BarrierControls { doc /* @S854 */ }
    part def BladeCondition { doc /* @S440 */ }
    part def BladeInspectionDrone { doc /* @S142,S254,S313,S314,S445 */ }
    part def BladeSpecialist { doc /* @S143,S315,S445,S452,S455,S463,S651 */ }
    part def Blades { doc /* @S790 */ }
    part def Cancellation { doc /* @S292 */ }
    part def Car { doc /* @S863,S902,S904 */ }
    part def CarFloor { doc /* @S862 */ }
    part def CarriedEquipment { doc /* @S895 */ }
    part def Change { doc /* @S981 */ }
    part def ChangeToTheWorkScope { doc /* @S510 */ }
    part def Changes { doc /* @S969 */ }
    part def ChangesToAccessRules { doc /* @S833,S834 */ }
    part def ChangesToOperatingAssumptionsResponsibilitiesInterfacesOrDecisionAuthority { doc /* @S960 */ }
    part def CommunicationChannel { doc /* @S771 */ }
    part def Communications { doc /* @S025,S413,S535,S630 */ }
    part def CompetenceRecords { doc /* @S972 */ }
    part def CompletionOfRequiredControls { doc /* @S912 */ }
    part def Concept { doc /* @S001,S005,S006,S014,S019 */ }
    part def Condition { doc /* @S907 */ }
    part def ConditionData { doc /* @S250 */ }
    part def ConditionInformation { doc /* @S793 */ }
    part def Conditions { doc /* @S107,S232,S381,S455,S535,S634,S641,S765 */ }
    part def ConditionsThatRequireWorkToStop { doc /* @S717 */ }
    part def Confidence { doc /* @S105 */ }
    part def ConfiguredIdentityAndAuthorizationChecks { doc /* @S819 */ }
    part def ConfirmedFaults { doc /* @S248 */ }
    part def ConfirmedFireCondition { doc /* @S789 */ }
    part def ContextualConditions { doc /* @S309 */ }
    part def ContinuedResponse { doc /* @S633 */ }
    part def ControlEngineer { doc /* @S063,S135,S193,S217,S297,S299,S302,S305,S310,S316,S338,S349,S367,S368,S375,S384,S423,S434,S516,S528,S530,S533,S534,S535,S542,S544,S552,S560,S562,S594,S630,S658,S718,S734,S742,S768,S799,S920,S938,S951,S964 */ }
    part def ControlFunctions { doc /* @S002 */ }
    part def ControlInterface { doc /* @S020 */ }
    part def ControlRoomDecisions { doc /* @S214 */ }
    part def ControlRoomStaff { doc /* @S729 */ }
    part def ControlTeam { doc /* @S713 */ }
    part def ControlledBoundary { doc /* @S112,S118 */ }
    part def ControlledLifecycle { doc /* @S587 */ }
    part def Controls { doc /* @S892 */ }
    part def ConverterCabinet { doc /* @S005,S035,S131,S294,S547 */ }
    part def Corrections { doc /* @S777 */ }
    part def Credential { doc /* @S840 */ }
    part def CredentialReaders { doc /* @S854 */ }
    part def Crew { doc /* @S167,S495,S504,S506,S511,S671,S678,S717,S721 */ }
    part def CrewAccountability { doc /* @S391 */ }
    part def CrewChanges { doc /* @S403 */ }
    part def CrewMember { doc /* @S726 */ }
    part def CrewTransferVessel { doc /* @S021,S045,S087,S215,S279,S312,S568,S643,S678 */ }
    part def CurrentAuthorization { doc /* @S168 */ }
    part def CurrentStatus { doc /* @S584 */ }
    part def Cybersecurity { doc /* @S025 */ }
    part def CybersecurityAnalyst { doc /* @S117,S419,S428,S435,S781,S929,S969 */ }
    part def CybersecurityControls { doc /* @S929 */ }
    part def CybersecurityGateway { doc /* @S049,S071,S110,S111,S287,S357,S416 */ }
    part def CybersecurityOperations { doc /* @S415 */ }
    part def CybersecurityRelatedWorkItem { doc /* @S430 */ }
    part def DamagedOrContaminatedItems { doc /* @S653 */ }
    part def DaughterCraft { doc /* @S021,S045,S088,S568,S621,S679 */ }
    part def DecisionRecords { doc /* @S293 */ }
    part def DefectAffectingSafeOperation { doc /* @S870 */ }
    part def DefectRecords { doc /* @S453 */ }
    part def DeferredTaskRationale { doc /* @S286 */ }
    part def Delay { doc /* @S292,S754 */ }
    part def DeliveredEnergy { doc /* @S910 */ }
    part def DeliveryLocation { doc /* @S699 */ }
    part def Denial { doc /* @S817 */ }
    part def Deployment { doc /* @S608 */ }
    part def DesignatedApprover { doc /* @S979 */ }
    part def DesignatedAuthorizingRole { doc /* @S165 */ }
    part def DesignatedEmergencyDistributionBus { doc /* @S180 */ }
    part def DesignatedGridConnectionPoint { doc /* @S199 */ }
    part def DetectionCoverage { doc /* @S787 */ }
    part def DetectorSignal { doc /* @S797 */ }
    part def DifferenceBetweenTheExpectedAndObservedCount { doc /* @S575 */ }
    part def DispatchRecord { doc /* @S708 */ }
    part def DocumentOwner { doc /* @S976 */ }
    part def DocumentedConfigurationBaseline { doc /* @S589 */ }
    part def DocumentedImpactAssessment { doc /* @S961 */ }
    part def Door { doc /* @S863 */ }
    part def DoorInterlocks { doc /* @S893 */ }
    part def Doors { doc /* @S898 */ }
    part def DurationOfGridRelatedRestrictions { doc /* @S910 */ }
    part def DutyPlanner { doc /* @S065,S076,S096,S126,S153,S164,S224,S247,S258,S260,S263,S269,S274,S278,S292,S304,S319,S334,S340,S388,S396,S442,S459,S464,S469,S470,S491,S515,S519,S520,S527,S536,S537,S539,S553,S561,S583,S639,S662,S664,S668,S669,S670,S672,S673,S675,S695,S702,S737,S758,S764,S779,S872,S925,S947,S955,S965 */ }
    part def EastServiceLift { doc /* @S859 */ }
    part def ElectricalAbsenceOfVoltageChecks { doc /* @S724 */ }
    part def ElectricalBoundary { doc /* @S004 */ }
    part def ElectricalEnclosures { doc /* @S787 */ }
    part def ElectricalRecoveryWork { doc /* @S631 */ }
    part def ElectricalTechnician { doc /* @S185,S325,S327,S331,S336,S363,S434,S496,S529,S650,S716,S750,S801,S867 */ }
    part def EmergencyArrangements { doc /* @S612 */ }
    part def EmergencyEgress { doc /* @S857 */ }
    part def EmergencyGenerator { doc /* @S180,S183,S186,S353,S356,S532,S803 */ }
    part def EmergencyResponseOrganizations { doc /* @S024 */ }
    part def EndTime { doc /* @S740 */ }
    part def EnergyProductionMeasures { doc /* @S910 */ }
    part def EnergySources { doc /* @S711 */ }
    part def Entrant { doc /* @S839,S840 */ }
    part def Entries { doc /* @S775 */ }
    part def EntryBarrier { doc /* @S846 */ }
    part def EnvironmentalLimits { doc /* @S233 */ }
    part def Equipment { doc /* @S341,S477,S535,S657,S711 */ }
    part def EquipmentStatus { doc /* @S630 */ }
    part def EstimatedVisibility { doc /* @S667 */ }
    part def Event { doc /* @S307 */ }
    part def EventInvestigations { doc /* @S972 */ }
    part def Evidence { doc /* @S303 */ }
    part def ExpectedLoad { doc /* @S895 */ }
    part def ExpectedPersonnelCount { doc /* @S584 */ }
    part def ExportCableMonitor { doc /* @S006,S200,S252,S346 */ }
    part def ExportEquipment { doc /* @S549 */ }
    part def ExportRestriction { doc /* @S538,S553 */ }
    part def ExternalConnectivity { doc /* @S113 */ }
    part def ExternalInterfaces { doc /* @S024 */ }
    part def ExternalOrganizations { doc /* @S027 */ }
    part def ExternalTransmissionSystem { doc /* @S201 */ }
    part def ExternalWork { doc /* @S748 */ }
    part def FailureAnalyses { doc /* @S923 */ }
    part def FarmMonitoringEnvironment { doc /* @S211 */ }
    part def FaultOnTheExternalSystem { doc /* @S208 */ }
    part def FieldSupervisor { doc /* @S076,S096,S145,S167,S253,S320,S329,S330,S333,S335,S340,S405,S412,S429,S430,S457,S493,S503,S509,S536,S615,S649,S658,S660,S717,S726,S778,S809,S826,S860,S869,S879,S881,S886,S887,S906,S927,S970 */ }
    part def FieldTeam { doc /* @S729 */ }
    part def FieldWork { doc /* @S711 */ }
    part def FinalWindow { doc /* @S747 */ }
    part def Fire { doc /* @S792 */ }
    part def FireDetectionPanel { doc /* @S629,S786 */ }
    part def FireProtection { doc /* @S025,S785 */ }
    part def FleetDispatchConsole { doc /* @S041,S069,S081,S082,S203,S225,S260,S370,S385,S543,S917,S947 */ }
    part def FleetDispatchConsoleSchedules { doc /* @S485 */ }
    part def FogBanks { doc /* @S662 */ }
    part def ForecastConditions { doc /* @S522 */ }
    part def ForecastOrObservedConditions { doc /* @S259 */ }
    part def ForecastUpdates { doc /* @S128 */ }
    part def Gate { doc /* @S816 */ }
    part def GoOrNoGoDecision { doc /* @S674 */ }
    part def GridConstraint { doc /* @S210,S519,S746 */ }
    part def GridDispatch { doc /* @S024 */ }
    part def GridDispatcher { doc /* @S202,S362,S367,S518,S541,S739,S769,S942 */ }
    part def GridInterfaceRelay { doc /* @S004,S190,S197,S201,S221,S372,S373,S551,S743,S769,S942 */ }
    part def HSEOfficer { doc /* @S095,S157,S237,S266,S312,S322,S408,S451,S481,S505,S526,S579,S617,S647,S808,S827,S949,S967 */ }
    part def HandsOnActivity { doc /* @S631 */ }
    part def HandsOnWork { doc /* @S725,S727 */ }
    part def Hazards { doc /* @S011 */ }
    part def Helideck { doc /* @S021 */ }
    part def IncidentLead { doc /* @S432,S436,S619 */ }
    part def IncomingSupervisor { doc /* @S512 */ }
    part def IncomingTeam { doc /* @S731 */ }
    part def Indicators { doc /* @S854 */ }
    part def Inspection { doc /* @S861 */ }
    part def InspectionRecord { doc /* @S456 */ }
    part def Inspector { doc /* @S862,S865,S868 */ }
    part def InstallationTeam { doc /* @S853 */ }
    part def Instructions { doc /* @S770 */ }
    part def InventoryRecord { doc /* @S686 */ }
    part def Isolation { doc /* @S732 */ }
    part def IsolationBoundary { doc /* @S711 */ }
    part def IsolationDevice { doc /* @S722 */ }
    part def Items { doc /* @S701 */ }
    part def LandingThresholds { doc /* @S862 */ }
    part def LaterReviewers { doc /* @S775 */ }
    part def LessonsLearned { doc /* @S933 */ }
    part def LiftSupply { doc /* @S867 */ }
    part def LightingInsideTheCarAndAtEachLanding { doc /* @S891 */ }
    part def LocalConditions { doc /* @S664 */ }
    part def LocalProtectionFunctions { doc /* @S137 */ }
    part def LocalReference { doc /* @S665 */ }
    part def LocalSystems { doc /* @S221 */ }
    part def LocalVisualIndicator { doc /* @S845 */ }
    part def LongOrUnstableLoads { doc /* @S877 */ }
    part def LossOfCommunications { doc /* @S209 */ }
    part def LowCloud { doc /* @S662 */ }
    part def LowConfidence { doc /* @S676 */ }
    part def LowStockAlerts { doc /* @S701 */ }
    part def MachinerySpaces { doc /* @S787 */ }
    part def MainTransformer { doc /* @S006,S038 */ }
    part def Maintenance { doc /* @S490 */ }
    part def MaintenanceActivities { doc /* @S002 */ }
    part def MaintenancePlanningEngine { doc /* @S042,S054,S058,S066,S076,S148,S154,S188,S195,S213,S246,S285,S308,S430,S441,S458,S470,S520,S670,S694,S738,S918,S948 */ }
    part def MaintenanceRecords { doc /* @S972 */ }
    part def MarineAccess { doc /* @S748 */ }
    part def MarineCoordination { doc /* @S021,S222 */ }
    part def MarineCoordinator { doc /* @S068,S077,S081,S082,S084,S141,S160,S223,S245,S257,S261,S277,S283,S290,S397,S400,S410,S412,S466,S473,S483,S488,S499,S523,S565,S576,S578,S583,S585,S618,S638,S658,S659,S660,S676,S682,S749,S764,S944,S966 */ }
    part def MarkedLimits { doc /* @S495 */ }
    part def MeasuredConditions { doc /* @S291 */ }
    part def MeasuredDelivery { doc /* @S383 */ }
    part def MeasuredExport { doc /* @S544 */ }
    part def MeasurementIntervals { doc /* @S108 */ }
    part def Measurements { doc /* @S200 */ }
    part def MetoceanBuoy { doc /* @S101,S102,S104,S106,S194,S231,S271,S272,S280,S309,S323,S443,S625,S665,S766 */ }
    part def MetoceanObservations { doc /* @S024 */ }
    part def MismatchBetweenTheFieldLabelAndTheApprovedRecord { doc /* @S721 */ }
    part def MonitoringAndControlAssumptions { doc /* @S968 */ }
    part def MonitoringAndControlFunctions { doc /* @S006 */ }
    part def MonitoringProcess { doc /* @S296 */ }
    part def MonitoringRules { doc /* @S418 */ }
    part def NacelleConditionMonitor { doc /* @S005,S035,S132,S250,S294,S299,S793,S915 */ }
    part def NeedDate { doc /* @S699 */ }
    part def NetworkSegmentation { doc /* @S120 */ }
    part def NewCondition { doc /* @S883 */ }
    part def NormalMonitoringResponsibilities { doc /* @S437 */ }
    part def NormalSupply { doc /* @S174 */ }
    part def NormalWork { doc /* @S635 */ }
    part def NorthAccessScanner { doc /* @S235,S394,S569,S810,S811 */ }
    part def Observation { doc /* @S306 */ }
    part def Observations { doc /* @S271 */ }
    part def ObservedCount { doc /* @S584 */ }
    part def Occupants { doc /* @S898,S899,S902,S905 */ }
    part def OffshoreEnvironmentalObservations { doc /* @S100 */ }
    part def OffshoreFarm { doc /* @S199,S205 */ }
    part def OffshoreGenerationAssets { doc /* @S027 */ }
    part def OffshorePersonnel { doc /* @S804 */ }
    part def OffshoreRecovery { doc /* @S636 */ }
    part def OffshoreRecoveryPlans { doc /* @S633 */ }
    part def OffshoreSubstation { doc /* @S003,S037,S038,S189,S267,S361,S374,S752,S941 */ }
    part def OffshoreSupportFacilities { doc /* @S002 */ }
    part def OffshoreWindFarm { doc /* @S014,S015,S016,S019,S028 */ }
    part def OffshoreWindFarmOperationsAndMaintenanceSystem { doc /* @S025,S027 */ }
    part def OnDutyOperationsLead { doc /* @S419 */ }
    part def OnboardLogger { doc /* @S104 */ }
    part def OperatingConcept { doc /* @S983 */ }
    part def OperatingData { doc /* @S447 */ }
    part def OperatingOrganization { doc /* @S075,S094,S098 */ }
    part def OperatingPersonnel { doc /* @S341,S349 */ }
    part def OperatingPlan { doc /* @S088 */ }
    part def OperatingRestrictions { doc /* @S448 */ }
    part def OperationalAssessment { doc /* @S667 */ }
    part def OperationalBoundary { doc /* @S002 */ }
    part def OperationalCommunications { doc /* @S760 */ }
    part def OperationalDecisions { doc /* @S624 */ }
    part def OperationalHandoverRecords { doc /* @S611 */ }
    part def OperationalMonitoring { doc /* @S788 */ }
    part def OperationalNotices { doc /* @S214 */ }
    part def OperationalPersonnel { doc /* @S027,S073,S074 */ }
    part def OperationalProcedures { doc /* @S122 */ }
    part def OperationalRecords { doc /* @S774,S776 */ }
    part def OperationalReports { doc /* @S440 */ }
    part def OperationalSystem { doc /* @S058 */ }
    part def OperationsRadioConsole { doc /* @S239,S627,S762,S806 */ }
    part def OperationsTeam { doc /* @S540 */ }
    part def Operator { doc /* @S356,S359,S360,S361,S376,S878,S888,S890,S892,S895,S898,S900,S901,S904,S905,S983 */ }
    part def Operators { doc /* @S184,S832,S935 */ }
    part def Organization { doc /* @S782 */ }
    part def OutgoingSupervisor { doc /* @S512 */ }
    part def Overheating { doc /* @S792 */ }
    part def PartsSupportingScheduledMaintenance { doc /* @S697 */ }
    part def Passengers { doc /* @S896 */ }
    part def People { doc /* @S502 */ }
    part def PeopleResponsibleForOffshoreWork { doc /* @S760 */ }
    part def PerformanceDefinitions { doc /* @S913 */ }
    part def Permit { doc /* @S329 */ }
    part def PermitControls { doc /* @S318 */ }
    part def PermitReviewers { doc /* @S171 */ }
    part def Permits { doc /* @S525 */ }
    part def Person { doc /* @S425,S812,S817 */ }
    part def PersonIssuingTheInstruction { doc /* @S772 */ }
    part def PersonMakingTheChange { doc /* @S777 */ }
    part def PersonRemovingEachControl { doc /* @S733 */ }
    part def PersonResponsibleForApplyingTheControl { doc /* @S714 */ }
    part def PersonSLocation { doc /* @S580 */ }
    part def PersonalProtection { doc /* @S723 */ }
    part def Personnel { doc /* @S011,S243,S393,S402,S405,S406,S411,S431,S451,S457,S482,S501,S525,S629,S648,S649,S771,S802,S828,S836,S847,S856,S873,S874,S903 */ }
    part def PersonnelAffectedByARevision { doc /* @S981 */ }
    part def PersonnelMovements { doc /* @S585 */ }
    part def PersonnelTrackingConsole { doc /* @S094,S234,S332,S392,S571,S573,S619,S648,S805,S874 */ }
    part def PersonsStillUnaccountedFor { doc /* @S584 */ }
    part def PhysicalBoundary { doc /* @S003 */ }
    part def PitchSystem { doc /* @S005,S034,S130,S294,S546,S601,S790 */ }
    part def PlannedCrewAssignments { doc /* @S396 */ }
    part def PlannedOutage { doc /* @S745 */ }
    part def PlannedRestorationChecks { doc /* @S532 */ }
    part def PlannedVesselMovements { doc /* @S681 */ }
    part def PlannedWork { doc /* @S872 */ }
    part def Planners { doc /* @S252 */ }
    part def PortAgent { doc /* @S093,S240,S324,S473 */ }
    part def PortAndBerthCoordination { doc /* @S465 */ }
    part def PortConditions { doc /* @S471 */ }
    part def PortSupport { doc /* @S024 */ }
    part def PositionIntegrityChecks { doc /* @S105 */ }
    part def PrivilegedSessions { doc /* @S116 */ }
    part def ProductionLostDuringDowntime { doc /* @S910 */ }
    part def ProposedControls { doc /* @S266 */ }
    part def ProposedReliabilityImprovements { doc /* @S932 */ }
    part def ProposedSequence { doc /* @S516,S535 */ }
    part def ProposedWorkaround { doc /* @S949 */ }
    part def ProtectedOperationalNetworks { doc /* @S100 */ }
    part def ProtectionActions { doc /* @S799 */ }
    part def ProtectionCoordination { doc /* @S208 */ }
    part def ProtectiveDevices { doc /* @S867,S893,S894 */ }
    part def ProtectiveFunctions { doc /* @S788 */ }
    part def QualifiedPersonnel { doc /* @S607 */ }
    part def QualifiedTechnician { doc /* @S719 */ }
    part def Rain { doc /* @S662 */ }
    part def Receiver { doc /* @S773 */ }
    part def Record { doc /* @S584,S844 */ }
    part def RecoveredComponents { doc /* @S656 */ }
    part def Recovery { doc /* @S436,S952 */ }
    part def RecoveryTask { doc /* @S639 */ }
    part def ReleasedRevisions { doc /* @S980 */ }
    part def ReliabilityReviews { doc /* @S921 */ }
    part def RemoteAdministrativeFunctions { doc /* @S118 */ }
    part def RemoteEvidence { doc /* @S310 */ }
    part def RemoteIndications { doc /* @S718 */ }
    part def RemoteObservations { doc /* @S147 */ }
    part def RemoteOperation { doc /* @S138 */ }
    part def RemoteSessions { doc /* @S427 */ }
    part def RemoteSurveys { doc /* @S444 */ }
    part def RepairPlans { doc /* @S462 */ }
    part def ReplenishmentRequests { doc /* @S699 */ }
    part def ReportedEvents { doc /* @S912 */ }
    part def ReportedStateChange { doc /* @S534 */ }
    part def Requester { doc /* @S152,S162 */ }
    part def RequiredQuantity { doc /* @S699 */ }
    part def RescueCoordinator { doc /* @S244,S580,S614,S626,S634,S637,S646 */ }
    part def Reservations { doc /* @S693 */ }
    part def ResourceAvailability { doc /* @S224 */ }
    part def Responders { doc /* @S629 */ }
    part def Response { doc /* @S306,S645 */ }
    part def ResponsibleAuthority { doc /* @S657,S732 */ }
    part def ResponsibleControlPersonnel { doc /* @S769 */ }
    part def ResponsibleManager { doc /* @S784 */ }
    part def ResponsibleOperationalAuthority { doc /* @S500 */ }
    part def ResponsibleOperationsStaff { doc /* @S754 */ }
    part def ResponsibleOperator { doc /* @S952 */ }
    part def ResponsibleOrganization { doc /* @S019 */ }
    part def ResponsiblePersonnel { doc /* @S086 */ }
    part def ResponsibleSupervisor { doc /* @S413 */ }
    part def ResponsibleTeam { doc /* @S170,S450 */ }
    part def Review { doc /* @S156 */ }
    part def ReviewTeams { doc /* @S922 */ }
    part def Reviewers { doc /* @S596 */ }
    part def Reviews { doc /* @S974 */ }
    part def RiskAssessments { doc /* @S972 */ }
    part def RotorBrakeUnit { doc /* @S005,S034,S791 */ }
    part def Route { doc /* @S842,S853,S855 */ }
    part def RoutineChecks { doc /* @S854 */ }
    part def RoutineRounds { doc /* @S344 */ }
    part def Rule { doc /* @S822 */ }
    part def SCADAEngineer { doc /* @S062,S423,S437,S558,S593,S946,S954,S968 */ }
    part def SCADAGateway { doc /* @S006,S052,S058,S059,S133,S159,S171,S192,S211,S212,S295,S297,S357,S364,S369,S417,S447,S540,S767,S798,S800,S914,S946 */ }
    part def SafetyFunctions { doc /* @S936 */ }
    part def SafetyPerformanceMeasures { doc /* @S912,S933 */ }
    part def ScheduledExercising { doc /* @S186 */ }
    part def ScheduledSurveillance { doc /* @S440 */ }
    part def SeaConditions { doc /* @S620 */ }
    part def SeaOrWeatherConditions { doc /* @S499 */ }
    part def SecurityEvents { doc /* @S119 */ }
    part def Sender { doc /* @S773 */ }
    part def SensorHealth { doc /* @S109 */ }
    part def Sensors { doc /* @S103 */ }
    part def SerialControlledParts { doc /* @S692 */ }
    part def ServiceOperationsVessel { doc /* @S021,S045,S089,S228,S281,S461,S622,S645,S646,S680 */ }
    part def ShiftHandover { doc /* @S730 */ }
    part def ShiftRecords { doc /* @S365,S389 */ }
    part def ShoreControlRoom { doc /* @S013,S040,S058,S064,S097,S099,S134,S192,S214,S238,S295,S303,S317,S339,S364,S371,S374,S386,S420,S448,S531,S578,S606,S613,S683,S752,S767,S798,S809,S937,S963 */ }
    part def ShorePersonnel { doc /* @S410 */ }
    part def Shortage { doc /* @S702 */ }
    part def Signs { doc /* @S852 */ }
    part def SiteMeasurements { doc /* @S625 */ }
    part def SiteSpecificDetectionAndTripSettings { doc /* @S795 */ }
    part def SoftwareChanges { doc /* @S597,S603 */ }
    part def SouthAccessScanner { doc /* @S236,S395,S570,S835,S838 */ }
    part def SparesHub { doc /* @S689 */ }
    part def Spray { doc /* @S662 */ }
    part def StaleOrImplausibleValue { doc /* @S300 */ }
    part def StartTime { doc /* @S740 */ }
    part def StationServiceTransformers { doc /* @S173 */ }
    part def StatusIndications { doc /* @S190 */ }
    part def StockVisibility { doc /* @S688 */ }
    part def Storekeeper { doc /* @S092,S242,S262,S460,S479,S690,S703,S876 */ }
    part def SubstationOperator { doc /* @S216,S268,S326,S337,S342,S343,S345,S351,S354,S382,S497,S517,S530,S531,S532,S549,S559,S741,S753,S971 */ }
    part def Substitutions { doc /* @S704 */ }
    part def SuccessfulResponseAtOneLevel { doc /* @S956 */ }
    part def SupervisoryFaults { doc /* @S796 */ }
    part def SupportingMarineAndShoreFacilities { doc /* @S027 */ }
    part def SwitchingActions { doc /* @S216 */ }
    part def SwitchingActivity { doc /* @S382 */ }
    part def SwitchingConditions { doc /* @S497 */ }
    part def SwitchingOperator { doc /* @S533 */ }
    part def System { doc /* @S183,S824,S908,S935,S957 */ }
    part def SystemArchitecture { doc /* @S051 */ }
    part def Task { doc /* @S157,S737 */ }
    part def TaskSelection { doc /* @S671 */ }
    part def Tasks { doc /* @S948 */ }
    part def Team { doc /* @S270,S271,S280,S289,S558,S684 */ }
    part def TechnicalReviewers { doc /* @S158,S309 */ }
    part def TechnicalTeams { doc /* @S433,S439 */ }
    part def Technicians { doc /* @S429 */ }
    part def TemporaryPersonnel { doc /* @S849 */ }
    part def TestRequirements { doc /* @S750 */ }
    part def TimeSynchronization { doc /* @S109 */ }
    part def TimelyClosureOfCorrectiveActions { doc /* @S912 */ }
    part def Tools { doc /* @S895 */ }
    part def Transaction { doc /* @S821,S822 */ }
    part def Transfer { doc /* @S565 */ }
    part def TransferArrangement { doc /* @S179 */ }
    part def TransferArrangements { doc /* @S620 */ }
    part def Transfers { doc /* @S227 */ }
    part def Turbine { doc /* @S034,S035,S444,S940 */ }
    part def TurbineAlarms { doc /* @S440 */ }
    part def TurbineController { doc /* @S005,S060,S061,S127,S129,S130,S159,S191,S294,S299,S377,S545,S789,S937 */ }
    part def TurbineLockout { doc /* @S657,S802 */ }
    part def TurbineResponse { doc /* @S305 */ }
    part def TurbineSensorBus { doc /* @S005,S251,S294,S788 */ }
    part def Turbines { doc /* @S003 */ }
    part def UnplannedMaintenance { doc /* @S018 */ }
    part def UrgentMessages { doc /* @S772 */ }
    part def UrgentPurchases { doc /* @S707 */ }
    part def Users { doc /* @S882 */ }
    part def ValidationChecks { doc /* @S298 */ }
    part def VerbalRequest { doc /* @S818 */ }
    part def Verification { doc /* @S609 */ }
    part def VerifiedHeadcount { doc /* @S390 */ }
    part def Vessel { doc /* @S398,S399,S582,S763 */ }
    part def VesselAISReceiver { doc /* @S105,S139,S140,S225,S288,S401 */ }
    part def VesselMaster { doc /* @S079,S085,S161,S226,S278,S279,S284,S390,S398,S402,S403,S409,S476,S498,S524,S525,S567,S577,S616,S634,S642,S659,S677,S682,S763,S807,S944 */ }
    part def VesselOperatingProcedures { doc /* @S021 */ }
    part def VesselPersonnel { doc /* @S764 */ }
    part def VesselPlan { doc /* @S161 */ }
    part def VesselRecoverySupport { doc /* @S636 */ }
    part def Vessels { doc /* @S011 */ }
    part def Visibility { doc /* @S620,S662,S673 */ }
    part def VisibilityAssessments { doc /* @S663 */ }
    part def Visitors { doc /* @S508,S849 */ }
    part def WarehouseSystem { doc /* @S091,S163,S241,S262,S478,S655,S687,S928 */ }
    part def WeatherAnalyst { doc /* @S084,S107,S232,S256,S270,S272,S323,S472,S521,S522,S626,S641,S765,S939 */ }
    part def WeatherHold { doc /* @S086,S259 */ }
    part def WeatherService { doc /* @S067,S083,S106,S128,S213,S230,S255,S270,S272,S289,S309,S443,S521,S522,S624,S640,S662,S665,S666,S748,S766,S939 */ }
    part def WeatherServiceForecast { doc /* @S664 */ }
    part def WeatherServiceForecasts { doc /* @S471 */ }
    part def WeatherServices { doc /* @S024 */ }
    part def WestRouteLandingDoors { doc /* @S889 */ }
    part def WestServiceLift { doc /* @S883,S884,S885,S893 */ }
    part def WindFarmAssets { doc /* @S002 */ }
    part def Work { doc /* @S011,S156,S329,S330,S388,S426,S581,S672,S685,S717 */ }
    part def WorkArrangements { doc /* @S095 */ }
    part def WorkParty { doc /* @S405,S713,S720,S881 */ }
    part def WorkPermitPortal { doc /* @S049,S070,S149,S155,S162,S169,S265,S321,S492,S713,S716,S728,S751,S780 */ }
    part def WorkPlan { doc /* @S228 */ }
    part def WorkScope { doc /* @S750 */ }
    part system {
        part abnormalCondition : AbnormalCondition {
            perform action a0 { doc /* may require intervention @S768 */ }
        }
        part accessConditions : AccessConditions {
            perform action a0 { doc /* change @S224 */ }
        }
        part accessRecords : AccessRecords {
            exhibit state modes {
                state s0 { doc /* available @S825 */ }
            }
        }
        part accountabilityRecords : AccountabilityRecords {
            perform action a0 { doc /* retain the time, location, responsible role, and disposition of each material movement @S414 */ }
        }
        part accountableOwner : AccountableOwner {
            perform action a0 { doc /* maintain the document @S959 */ }
            perform action a1 { doc /* coordinate its approval @S959 */ }
        }
        part actionsTaken : ActionsTaken;
        part activeRestrictions : ActiveRestrictions {
            perform action a0 { doc /* could conflict with lift operation @S871 */ }
        }
        part activity : Activity {
            perform action a0 { doc /* begins @S751 */ }
        }
        part actualConditions : ActualConditions {
            perform action a0 { doc /* differ from the approved method or the marked worksite boundaries @S509 */ }
            perform action a1 { doc /* make the planned sequence unsafe or incompatible with grid requirements @S755 */ }
        }
        part adjacentEquipment : AdjacentEquipment {
            perform action a0 { doc /* must remain energized or available for service @S715 */ }
            exhibit state modes {
                state s0 { doc /* available for service @S715 */ }
                state s1 { doc /* energized @S715 */ }
            }
        }
        part administrativeAccess : AdministrativeAccess {
            perform action a0 { doc /* requires authenticated individual accounts and role-based authorization @S115 */ }
        }
        part affectedActivity : AffectedActivity {
            perform action a0 { doc /* can continue @S579 */ }
        }
        part affectedEquipment : AffectedEquipment;
        part affectedPersonnel : AffectedPersonnel;
        part affectedServices : AffectedServices {
            exhibit state modes {
                state s0 { doc /* normal operation @S122 */ }
            }
        }
        part affectedTeams : AffectedTeams {
            perform action a0 { doc /* receive the update @S245 */ }
        }
        part alarm : Alarm;
        part alarmPriorities : AlarmPriorities {
            perform action a0 { doc /* distinguish immediate danger from supervisory faults that require assessment but do not indicate an active fire @S796 */ }
        }
        part alarmThresholds : AlarmThresholds {
            perform action a0 { doc /* are configured to support both trend analysis and timely operational decisions @S108 */ }
            perform action a1 { doc /* support both trend analysis and timely operational decisions @S108 */ }
        }
        part alternative : Alternative {
            perform action a0 { doc /* meets the required interface and operating limits @S704 */ }
        }
        part alternativeAccessMethod : AlternativeAccessMethod {
            perform action a0 { doc /* changes resource demand @S292 */ }
        }
        part applicableHandlingRequirements : ApplicableHandlingRequirements;
        part approval : Approval {
            perform action a0 { doc /* identifies each isolation point, the required device position, and the person responsible for applying the control @S714 */ }
            perform action a1 { doc /* also records any adjacent equipment that must remain energized or available for service @S715 */ }
        }
        part approvedContingencyProcess : ApprovedContingencyProcess {
            perform action a0 { doc /* requires a named approver and a recorded reason for any temporary access decision @S829 */ }
        }
        part approvedElectricalConfiguration : ApprovedElectricalConfiguration {
            perform action a0 { doc /* explicitly supports it @S387 */ }
        }
        part approvedHandlingArrangement : ApprovedHandlingArrangement {
            perform action a0 { doc /* keeps the load contained within the car @S877 */ }
        }
        part approvedProcedures : ApprovedProcedures;
        part approvedSwitchingWindow : ApprovedSwitchingWindow {
            exhibit state modes {
                state s0 { doc /* active @S753 */ }
            }
        }
        part approvedWindow : ApprovedWindow;
        part approvedWork : ApprovedWork {
            perform action a0 { doc /* proceeds @S519 */ }
        }
        part architecture : Architecture {
            perform action a0 { doc /* assigns defined responsibilities to interfaces @S072 */ }
        }
        part area : Area {
            exhibit state modes {
                state s0 { doc /* safe @S801 */ }
            }
        }
        part areasIdentifiedByTheSiteFireRiskAssessment : AreasIdentifiedByTheSiteFireRiskAssessment;
        part assetOperator : AssetOperator {
            perform action a0 { doc /* assigns an accountable owner to maintain the document and coordinate its approval @S959 */ }
        }
        part assuranceArrangements : AssuranceArrangements {
            perform action a0 { doc /* provide sufficient evidence that the concept remains effective @S983 */ }
        }
        part assuranceEvidence : AssuranceEvidence;
        part attempt : Attempt {
            perform action a0 { doc /* receives a unique transaction identifier for later reference @S820 */ }
        }
        part auditFindings : AuditFindings;
        part auditRecord : AuditRecord {
            perform action a0 { doc /* distinguishes a rejected credential from an authorization that lacks the required scope @S823 */ }
        }
        part authority : Authority {
            perform action a0 { doc /* approving access @S122 */ }
            perform action a1 { doc /* responding to alarms @S122 */ }
            perform action a2 { doc /* returning affected services to normal operation @S122 */ }
        }
        part authorization : Authorization {
            perform action a0 { doc /* results in a denied entry decision @S815 */ }
            perform action a1 { doc /* lacks the required scope @S823 */ }
            exhibit state modes {
                state s0 { doc /* active @S813 */ }
                state s1 { doc /* expired @S815 */ }
                state s2 { doc /* incomplete @S815 */ }
                state s3 { doc /* suspended @S815 */ }
            }
        }
        part authorizationLifecycle : AuthorizationLifecycle {
            perform action a0 { doc /* begins when a work request is entered with its location, scope, planned duration, and responsible team @S151 */ }
        }
        part authorizationProcesses : AuthorizationProcesses {
            perform action a0 { doc /* govern work under controlled conditions @S070 */ }
        }
        part authorizedPersonnel : AuthorizedPersonnel {
            perform action a0 { doc /* using approved instructions and positive confirmation of equipment identity @S358 */ }
        }
        part authorizedShorePersonnel : AuthorizedShorePersonnel;
        part automaticControls : AutomaticControls {
            perform action a0 { doc /* initiate the Emergency Generator start sequence @S177 */ }
        }
        part auxiliaryElectricalLoads : AuxiliaryElectricalLoads;
        part backupPower : BackupPower;
        part barrierControls : BarrierControls {
            perform action a0 { doc /* operate as intended @S854 */ }
        }
        part bladeCondition : BladeCondition;
        part bladeInspectionDrone : BladeInspectionDrone {
            perform action a0 { doc /* captures close-range visual observations of accessible blade surfaces @S142 */ }
            perform action a1 { doc /* can support inspection planning @S254 */ }
            perform action a2 { doc /* produces the Leading Edge Tile Image @S313 */ }
            perform action a3 { doc /* repeat a close-range pass @S314 */ }
        }
        part bladeSpecialist : BladeSpecialist {
            perform action a0 { doc /* plans inspection passes @S143 */ }
            perform action a1 { doc /* provide consistent coverage of areas selected for examination @S143 */ }
            perform action a2 { doc /* reviews available inspection evidence @S315 */ }
            perform action a3 { doc /* reports whether further examination is warranted @S315 */ }
            perform action a4 { doc /* reviews the tile image @S445 */ }
            perform action a5 { doc /* classify visible damage @S445 */ }
            perform action a6 { doc /* identify areas requiring closer assessment @S445 */ }
            perform action a7 { doc /* examines the affected surface using suitable lighting, measurement tools, and nondestructive inspection methods @S452 */ }
            perform action a8 { doc /* using suitable lighting, measurement tools, and nondestructive inspection methods @S452 */ }
            perform action a9 { doc /* distinguishes cosmetic damage from conditions that could affect structural integrity or safe turbine operation @S455 */ }
            perform action a10 { doc /* records the completed work @S463 */ }
            perform action a11 { doc /* verifies that the repaired area meets the applicable acceptance criteria @S463 */ }
            perform action a12 { doc /* identifies fragile blade components @S651 */ }
            perform action a13 { doc /* specifies padding or restraints @S651 */ }
            perform action a14 { doc /* prevent handling damage @S651 */ }
        }
        part blades : Blades {
            exhibit state modes {
                state s0 { doc /* defined safe position @S790 */ }
            }
        }
        part cancellation : Cancellation {
            perform action a0 { doc /* changes resource demand @S292 */ }
        }
        part car : Car {
            perform action a0 { doc /* cannot move while a door is open @S863 */ }
            perform action a1 { doc /* stops between landings @S902 */ }
            exhibit state modes {
                state s0 { doc /* level and stationary @S904 */ }
            }
        }
        part carFloor : CarFloor {
            exhibit state modes {
                state s0 { doc /* clear of loose material and standing water @S862 */ }
            }
        }
        part carriedEquipment : CarriedEquipment;
        part change : Change {
            perform action a0 { doc /* takes effect @S981 */ }
        }
        part changeToTheWorkScope : ChangeToTheWorkScope;
        part changes : Changes {
            perform action a0 { doc /* could affect access, communications, or the integrity of operational records @S969 */ }
        }
        part changesToAccessRules : ChangesToAccessRules {
            perform action a0 { doc /* become effective at the entry point @S833 */ }
            perform action a1 { doc /* provides a consistent basis for admitting authorized personnel and explaining each access decision @S834 */ }
        }
        part changesToOperatingAssumptionsResponsibilitiesInterfacesOrDecisionAuthority : ChangesToOperatingAssumptionsResponsibilitiesInterfacesOrDecisionAuthority {
            perform action a0 { doc /* require documented impact assessment before approval @S960 */ }
        }
        part communicationChannel : CommunicationChannel {
            exhibit state modes {
                state s0 { doc /* unavailable @S771 */ }
            }
        }
        part communications : Communications {
            perform action a0 { doc /* fail @S535 */ }
            perform action a1 { doc /* allow safe intervention @S630 */ }
            exhibit state modes {
                state s0 { doc /* unavailable @S413 */ }
            }
        }
        part competenceRecords : CompetenceRecords;
        part completionOfRequiredControls : CompletionOfRequiredControls;
        part concept : Concept {
            perform action a0 { doc /* defines the operational scope and principal interfaces for operating and maintaining the offshore wind farm @S001 */ }
            perform action a1 { doc /* includes the Turbine Controller, Pitch System, Converter Cabinet, Nacelle Condition Monitor, Rotor Brake Unit, and Turbine Sensor Bus as representative turbine systems @S005 */ }
            perform action a2 { doc /* also includes the Main Transformer, Export Cable Monitor, SCADA Gateway, and associated monitoring and control functions @S006 */ }
            perform action a3 { doc /* applies from commissioning and acceptance through routine operation, major refurbishment, and eventual decommissioning @S014 */ }
            perform action a4 { doc /* supports safe isolation, removal planning, and transfer of residual operational records to the responsible organization @S019 */ }
        }
        part condition : Condition {
            perform action a0 { doc /* could compromise safe movement @S907 */ }
        }
        part conditionData : ConditionData {
            perform action a0 { doc /* helps distinguish developing degradation from transient alarms @S250 */ }
        }
        part conditionInformation : ConditionInformation {
            perform action a0 { doc /* can help distinguish a developing equipment fault from a confirmed fire alarm @S793 */ }
        }
        part conditions : Conditions {
            perform action a0 { doc /* may affect vessel access or turbine work @S107 */ }
            perform action a1 { doc /* may affect the plan @S232 */ }
            perform action a2 { doc /* require a reduced transfer level @S381 */ }
            perform action a3 { doc /* could affect structural integrity or safe turbine operation @S455 */ }
            perform action a4 { doc /* differ from the plan @S535 */ }
            perform action a5 { doc /* exceed the approved operating envelope @S634 */ }
            perform action a6 { doc /* could affect safe vessel handling @S641 */ }
            perform action a7 { doc /* could affect access, lifting, or work at height @S765 */ }
        }
        part conditionsThatRequireWorkToStop : ConditionsThatRequireWorkToStop {
            perform action a0 { doc /* require work to stop @S717 */ }
        }
        part confidence : Confidence {
            perform action a0 { doc /* falls below its configured threshold @S105 */ }
        }
        part configuredIdentityAndAuthorizationChecks : ConfiguredIdentityAndAuthorizationChecks {
            perform action a0 { doc /* pass @S819 */ }
        }
        part confirmedFaults : ConfirmedFaults {
            perform action a0 { doc /* threaten personnel safety @S248 */ }
            perform action a1 { doc /* cause substantial generation loss @S248 */ }
            perform action a2 { doc /* receive priority over routine inspections @S248 */ }
        }
        part confirmedFireCondition : ConfirmedFireCondition {
            perform action a0 { doc /* requires turbine protection @S789 */ }
        }
        part contextualConditions : ContextualConditions {
            perform action a0 { doc /* help reviewers distinguish environmental effects from equipment deterioration @S309 */ }
        }
        part continuedResponse : ContinuedResponse {
            perform action a0 { doc /* would expose rescuers to unacceptable risk @S633 */ }
        }
        part controlEngineer : ControlEngineer {
            perform action a0 { doc /* uses the shore-based operational picture @S063 */ }
            perform action a1 { doc /* assess equipment status @S063 */ }
            perform action a2 { doc /* coordinate response @S063 */ }
            perform action a3 { doc /* reviews alarms and operating conditions @S135 */ }
            perform action a4 { doc /* issuing a remote command @S135 */ }
            perform action a5 { doc /* reviews persistent alarms @S193 */ }
            perform action a6 { doc /* coordinates electrical support with the Substation Operator @S193 */ }
            perform action a7 { doc /* verifies that dispatch changes are reflected in the applicable control settings before implementation @S217 */ }
            perform action a8 { doc /* reviews alarms alongside recent operating trends @S297 */ }
            perform action a9 { doc /* rather than treating an isolated threshold crossing as a confirmed fault @S297 */ }
            perform action a10 { doc /* compares disputed readings with independent signals from the Turbine Controller and Nacelle Condition Monitor where available @S299 */ }
            perform action a11 { doc /* records the evidence considered and the basis for accepting, rejecting, or continuing to monitor an alert @S302 */ }
            perform action a12 { doc /* accepting @S302 */ }
            perform action a13 { doc /* rejecting @S302 */ }
            perform action a14 { doc /* continuing to monitor an alert @S302 */ }
            perform action a15 { doc /* follows the approved operating procedure @S305 */ }
            perform action a16 { doc /* confirms the resulting state through available indications @S305 */ }
            perform action a17 { doc /* requests an on-site inspection when remote evidence cannot resolve a material uncertainty @S310 */ }
            perform action a18 { doc /* reassesses the alert @S316 */ }
            perform action a19 { doc /* reviews the restored equipment state @S338 */ }
            perform action a20 { doc /* confirms that required operational checks are complete @S338 */ }
            perform action a21 { doc /* investigates unexplained discrepancies @S349 */ }
            perform action a22 { doc /* reviews each instruction for consistency with current plant status @S368 */ }
            perform action a23 { doc /* applying it @S368 */ }
            perform action a24 { doc /* confirms that the control response follows the instruction and remains within the permitted ramp rate @S375 */ }
            perform action a25 { doc /* records the reason for any temporary deviation from the requested output and the action taken @S384 */ }
            perform action a26 { doc /* use individually assigned accounts rather than shared credentials for interactive work @S423 */ }
            perform action a27 { doc /* coordinate any operational changes with the relevant duty role before implementation @S434 */ }
            perform action a28 { doc /* checks the current network configuration @S516 */ }
            perform action a29 { doc /* confirms that the proposed sequence supports the approved work @S516 */ }
            perform action a30 { doc /* prepares clear switching instructions with one action per step and an explicit hold point where needed @S528 */ }
            perform action a31 { doc /* is issued @S533 */ }
            perform action a32 { doc /* monitors available indications @S534 */ }
            perform action a33 { doc /* confirms that each reported state change matches the approved sequence @S534 */ }
            perform action a34 { doc /* is paused @S535 */ }
            perform action a35 { doc /* is left in a safe state @S535 */ }
            perform action a36 { doc /* verifies the permitted level, its effective time, and any required ramp rate @S542 */ }
            perform action a37 { doc /* changing operating targets @S542 */ }
            perform action a38 { doc /* reduces active power in controlled steps @S544 */ }
            perform action a39 { doc /* checks that measured export follows the revised target @S544 */ }
            perform action a40 { doc /* compares actual export with the permitted level @S552 */ }
            perform action a41 { doc /* investigates any persistent mismatch @S552 */ }
            perform action a42 { doc /* escalates any condition that threatens equipment limits, protection coordination, or safe operation @S560 */ }
            perform action a43 { doc /* confirms authorization @S562 */ }
            perform action a44 { doc /* restores output gradually @S562 */ }
            perform action a45 { doc /* monitoring equipment response @S562 */ }
            perform action a46 { doc /* confirms that proposed changes have a clear operational purpose and defined scope @S594 */ }
            perform action a47 { doc /* supports remote shutdown actions @S630 */ }
            perform action a48 { doc /* provides technical guidance @S658 */ }
            perform action a49 { doc /* checks that remote indications agree with the approved switching state @S718 */ }
            perform action a50 { doc /* authorizing access @S718 */ }
            perform action a51 { doc /* verifies the restoration state @S734 */ }
            perform action a52 { doc /* communicates any remaining operational limitation to affected personnel @S734 */ }
            perform action a53 { doc /* checks that turbine operations can be managed safely while the substation work is in progress @S742 */ }
            perform action a54 { doc /* reviews alarms and operating trends with the SCADA Engineer @S768 */ }
            perform action a55 { doc /* verifies the equipment state @S799 */ }
            perform action a56 { doc /* checks that protection actions have completed @S799 */ }
            perform action a57 { doc /* authorizing any further operational action @S799 */ }
            perform action a58 { doc /* examines significant operational deviations @S920 */ }
            perform action a59 { doc /* records the technical findings for review @S920 */ }
            perform action a60 { doc /* suspends those commands @S938 */ }
            perform action a61 { doc /* uses approved local procedures until reliable control is restored @S938 */ }
            perform action a62 { doc /* coordinates technical recovery with the relevant field and shore roles @S951 */ }
            perform action a63 { doc /* reviews control-room practices @S964 */ }
            perform action a64 { doc /* confirms that operational procedures remain consistent with the concept @S964 */ }
        }
        part controlFunctions : ControlFunctions;
        part controlInterface : ControlInterface {
            perform action a0 { doc /* includes operational coordination with the Fleet Dispatch Console and Maintenance Planning Engine @S020 */ }
        }
        part controlRoomDecisions : ControlRoomDecisions {
            perform action a0 { doc /* affecting the farm interface @S214 */ }
        }
        part controlRoomStaff : ControlRoomStaff {
            perform action a0 { doc /* use the same revision @S729 */ }
            perform action a1 { doc /* confirming isolation status @S729 */ }
        }
        part controlTeam : ControlTeam;
        part controlledBoundary : ControlledBoundary {
            perform action a0 { doc /* permits only approved protocols, destinations, and service accounts @S112 */ }
            perform action a1 { doc /* places remote administrative functions in a restricted state without bypassing local protective controls @S118 */ }
        }
        part controlledLifecycle : ControlledLifecycle {
            perform action a0 { doc /* protects the integrity and availability of operational systems @S587 */ }
        }
        part controls : Controls {
            perform action a0 { doc /* respond correctly @S892 */ }
        }
        part converterCabinet : ConverterCabinet {
            perform action a0 { doc /* manages electrical conversion @S131 */ }
            perform action a1 { doc /* observing equipment limits and protective interlocks @S131 */ }
            perform action a2 { doc /* remains within its electrical and thermal ratings throughout the reduction @S547 */ }
        }
        part corrections : Corrections {
            perform action a0 { doc /* preserve the original entry @S777 */ }
            perform action a1 { doc /* identify the person making the change @S777 */ }
            perform action a2 { doc /* state the reason for the correction @S777 */ }
        }
        part credential : Credential {
            exhibit state modes {
                state s0 { doc /* active @S840 */ }
            }
        }
        part credentialReaders : CredentialReaders {
            perform action a0 { doc /* operate as intended @S854 */ }
        }
        part crew : Crew {
            perform action a0 { doc /* starts work @S167 */ }
            perform action a1 { doc /* confirms that the marked limits match the current isolation points and the approved maintenance scope @S495 */ }
            perform action a2 { doc /* starting @S504 */ }
            perform action a3 { doc /* inspects personal protective equipment, communications equipment, and rescue equipment for serviceability @S504 */ }
            perform action a4 { doc /* tests the required radio channel with the Operations Radio Console @S506 */ }
            perform action a5 { doc /* separating into work teams @S506 */ }
            perform action a6 { doc /* maintains clear access to fire equipment, escape routes, and lifting areas throughout the task @S511 */ }
            perform action a7 { doc /* can be performed safely under the assessed conditions @S671 */ }
            perform action a8 { doc /* relying on precise visual identification or close-range observation @S671 */ }
            perform action a9 { doc /* can maintain adequate visual awareness @S678 */ }
            perform action a10 { doc /* proceeding @S721 */ }
        }
        part crewAccountability : CrewAccountability {
            perform action a0 { doc /* covers personnel movement between shore facilities, vessels, offshore structures, and the return journey @S391 */ }
        }
        part crewChanges : CrewChanges {
            perform action a0 { doc /* occur during transit or between offshore locations @S403 */ }
        }
        part crewMember : CrewMember {
            perform action a0 { doc /* understands the limits of the approved work area @S726 */ }
        }
        part crewTransferVessel : CrewTransferVessel {
            perform action a0 { doc /* may support offshore work @S045 */ }
            perform action a1 { doc /* transports authorized personnel and routine tools between shore and offshore work locations @S087 */ }
            perform action a2 { doc /* reports its approach and departure status in accordance with the approved marine coordination procedure @S215 */ }
            perform action a3 { doc /* proceeds only when the Vessel Master considers the approach and transfer conditions acceptable @S279 */ }
            perform action a4 { doc /* uses the Harness Audit Card @S312 */ }
            perform action a5 { doc /* verify the applicable equipment checks @S312 */ }
            perform action a6 { doc /* operate in the same transfer sequence @S568 */ }
            perform action a7 { doc /* transports personnel and small equipment only when sea conditions and transfer arrangements are acceptable @S643 */ }
            perform action a8 { doc /* remain clear of a transfer location @S678 */ }
            perform action a9 { doc /* can maintain adequate visual awareness @S678 */ }
        }
        part currentAuthorization : CurrentAuthorization;
        part currentStatus : CurrentStatus;
        part cybersecurity : Cybersecurity;
        part cybersecurityAnalyst : CybersecurityAnalyst {
            perform action a0 { doc /* monitors gateway events for unusual access patterns and configuration changes @S117 */ }
            perform action a1 { doc /* reviews alerts @S419 */ }
            perform action a2 { doc /* assesses their operational significance @S419 */ }
            perform action a3 { doc /* escalates urgent concerns to the on-duty operations lead @S419 */ }
            perform action a4 { doc /* produces the Firmware Hash Attestation for controlled software releases @S428 */ }
            perform action a5 { doc /* preserves relevant logs and technical evidence @S435 */ }
            perform action a6 { doc /* limiting access to personnel assigned to the investigation @S435 */ }
            perform action a7 { doc /* protects access logs and communication records against unauthorized alteration or disclosure @S781 */ }
            perform action a8 { doc /* reviews performance records for evidence that cybersecurity controls affect operational availability or recovery @S929 */ }
            perform action a9 { doc /* assesses changes that could affect access, communications, or the integrity of operational records @S969 */ }
        }
        part cybersecurityControls : CybersecurityControls {
            perform action a0 { doc /* affect operational availability or recovery @S929 */ }
        }
        part cybersecurityGateway : CybersecurityGateway {
            perform action a0 { doc /* support controlled and secure operations @S049 */ }
            perform action a1 { doc /* provides a security boundary for connected operational services @S071 */ }
            perform action a2 { doc /* is designated Quiet Harbor for operational reference @S110 */ }
            perform action a3 { doc /* establishes a controlled boundary between authorized shore-side services and offshore operational networks @S111 */ }
            perform action a4 { doc /* blocks a route change when the required authorization is incomplete @S287 */ }
            perform action a5 { doc /* uses the revocation receipt @S357 */ }
            perform action a6 { doc /* support access control during routine account and session reviews @S357 */ }
            perform action a7 { doc /* monitors traffic between operational networks and approved external connections @S416 */ }
        }
        part cybersecurityOperations : CybersecurityOperations {
            perform action a0 { doc /* protect the wind farm control environment @S415 */ }
            perform action a1 { doc /* supporting safe and reliable production @S415 */ }
        }
        part cybersecurityRelatedWorkItem : CybersecurityRelatedWorkItem;
        part damagedOrContaminatedItems : DamagedOrContaminatedItems {
            perform action a0 { doc /* cannot create hazards for personnel or other cargo @S653 */ }
        }
        part daughterCraft : DaughterCraft {
            perform action a0 { doc /* may support offshore work @S045 */ }
            perform action a1 { doc /* can support short-range transfers @S088 */ }
            perform action a2 { doc /* operate in the same transfer sequence @S568 */ }
            perform action a3 { doc /* may support a local response @S621 */ }
        }
        part decisionRecords : DecisionRecords {
            perform action a0 { doc /* capture the forecast basis, applicable limits, observed conditions, and the reason for proceeding, holding, or returning to port @S293 */ }
        }
        part defectAffectingSafeOperation : DefectAffectingSafeOperation {
            perform action a0 { doc /* prevents release until the required repair and verification are complete @S870 */ }
        }
        part defectRecords : DefectRecords {
            perform action a0 { doc /* describe location, dimensions, orientation, suspected cause, confidence, and any change from earlier observations @S453 */ }
        }
        part deferredTaskRationale : DeferredTaskRationale {
            perform action a0 { doc /* supports later reprioritization @S286 */ }
            perform action a1 { doc /* implying that the task is safe under the current conditions @S286 */ }
        }
        part delay : Delay {
            perform action a0 { doc /* changes resource demand @S292 */ }
            perform action a1 { doc /* threatens the agreed end time @S754 */ }
        }
        part deliveredEnergy : DeliveredEnergy;
        part deliveryLocation : DeliveryLocation;
        part denial : Denial {
            perform action a0 { doc /* directs the person to contact the Field Supervisor or the HSE Officer for review @S817 */ }
        }
        part deployment : Deployment {
            perform action a0 { doc /* begins @S608 */ }
        }
        part designatedApprover : DesignatedApprover {
            perform action a0 { doc /* confirms that comments are resolved or explicitly accepted @S979 */ }
        }
        part designatedAuthorizingRole : DesignatedAuthorizingRole {
            perform action a0 { doc /* grants permission only after required reviews and controls are recorded in the portal @S165 */ }
        }
        part designatedEmergencyDistributionBus : DesignatedEmergencyDistributionBus;
        part designatedGridConnectionPoint : DesignatedGridConnectionPoint;
        part detectionCoverage : DetectionCoverage;
        part detectorSignal : DetectorSignal {
            perform action a0 { doc /* has returned to normal @S797 */ }
            exhibit state modes {
                state s0 { doc /* normal @S797 */ }
            }
        }
        part differenceBetweenTheExpectedAndObservedCount : DifferenceBetweenTheExpectedAndObservedCount {
            exhibit state modes {
                state s0 { doc /* unresolved @S575 */ }
            }
        }
        part dispatchRecord : DispatchRecord {
            perform action a0 { doc /* identifies the quantity, destination, handling conditions, and responsible receiving location @S708 */ }
        }
        part documentOwner : DocumentOwner {
            perform action a0 { doc /* schedules periodic review @S976 */ }
            perform action a1 { doc /* initiates an additional review after material operational, technical, or regulatory change @S976 */ }
        }
        part documentedConfigurationBaseline : DocumentedConfigurationBaseline {
            perform action a0 { doc /* records software versions, configuration parameters, dependencies, and applicable hardware revisions @S589 */ }
        }
        part documentedImpactAssessment : DocumentedImpactAssessment {
            perform action a0 { doc /* considers effects on personnel safety, marine coordination, electrical safety, availability, cybersecurity, and regulatory obligations @S961 */ }
        }
        part door : Door {
            exhibit state modes {
                state s0 { doc /* open @S863 */ }
            }
        }
        part doorInterlocks : DoorInterlocks;
        part doors : Doors {
            exhibit state modes {
                state s0 { doc /* fully closed @S898 */ }
            }
        }
        part durationOfGridRelatedRestrictions : DurationOfGridRelatedRestrictions;
        part dutyPlanner : DutyPlanner {
            perform action a0 { doc /* uses the Maintenance Planning Engine @S065 */ }
            perform action a1 { doc /* prepare maintenance activities @S065 */ }
            perform action a2 { doc /* review maintenance activities @S065 */ }
            perform action a3 { doc /* develops daily work priorities with input from the Field Supervisor and the Maintenance Planning Engine @S076 */ }
            perform action a4 { doc /* prepares the Transfer Manifest Addendum @S126 */ }
            perform action a5 { doc /* capture approved vessel deployment changes @S126 */ }
            perform action a6 { doc /* reviews the request for completeness @S153 */ }
            perform action a7 { doc /* assigns it to the appropriate planning queue @S153 */ }
            perform action a8 { doc /* resolves outstanding supply and scheduling issues @S164 */ }
            perform action a9 { doc /* submitting the request for authorization @S164 */ }
            perform action a10 { doc /* updates work priorities when access conditions or resource availability change @S224 */ }
            perform action a11 { doc /* reviews the ranked queue @S247 */ }
            perform action a12 { doc /* confirms that urgent work has a clear technical basis and a feasible execution path @S247 */ }
            perform action a13 { doc /* considers Crew Transfer Vessel, Daughter Craft, Service Operations Vessel, and Helideck access @S258 */ }
            perform action a14 { doc /* selecting a mobilization method @S258 */ }
            perform action a15 { doc /* confirms the operating priority @S260 */ }
            perform action a16 { doc /* accounts for part availability, technician competence, and estimated task duration @S263 */ }
            perform action a17 { doc /* committing a work window @S263 */ }
            perform action a18 { doc /* revises priorities @S269 */ }
            perform action a19 { doc /* communicates the resulting plan to affected teams @S269 */ }
            perform action a20 { doc /* checks that the expected conditions remain within the limits for the task, transfer method, and vessel @S274 */ }
            perform action a21 { doc /* adjusts the executable plan when a delay, cancellation, or alternative access method changes resource demand @S292 */ }
            perform action a22 { doc /* reviews accepted alerts for immediate response needs and for effects on the executable maintenance plan @S304 */ }
            perform action a23 { doc /* submits a defined task scope, work location, crew, and requested operating window for review @S319 */ }
            perform action a24 { doc /* coordinates any revised work window with the relevant operational roles @S334 */ }
            perform action a25 { doc /* closes the work authorization @S340 */ }
            perform action a26 { doc /* considers active dispatch constraints when scheduling work that would reduce generation or access to export equipment @S388 */ }
            perform action a27 { doc /* scheduling work that would reduce generation or access to export equipment @S388 */ }
            perform action a28 { doc /* verifies that planned crew assignments match the approved work schedule before mobilization @S396 */ }
            perform action a29 { doc /* confirms the inspection priority @S442 */ }
            perform action a30 { doc /* coordinates access with the Marine Coordinator or the Field Supervisor @S442 */ }
            perform action a31 { doc /* assigns a target repair window @S459 */ }
            perform action a32 { doc /* coordinates required personnel, equipment, and vessel capacity @S459 */ }
            perform action a33 { doc /* updates the maintenance record @S464 */ }
            perform action a34 { doc /* schedules follow-up inspection when residual uncertainty or defect history warrants it @S464 */ }
            perform action a35 { doc /* compares task readiness with the expected departure window @S469 */ }
            perform action a36 { doc /* committing crews and equipment to a marine campaign @S469 */ }
            perform action a37 { doc /* checks that the planned task matches the approved work authorization and that required personnel and equipment are available @S491 */ }
            perform action a38 { doc /* develops the proposed sequence with the Control Engineer @S515 */ }
            perform action a39 { doc /* identifies affected equipment and operating limits @S515 */ }
            perform action a40 { doc /* reassess the sequence @S519 */ }
            perform action a41 { doc /* obtain revised authorization @S519 */ }
            perform action a42 { doc /* records the proposed sequence, required approvals, execution roles, and planned communications in the operating record @S527 */ }
            perform action a43 { doc /* authorizes restoration or release of the work area @S536 */ }
            perform action a44 { doc /* records the final equipment state, approvals, deviations, and handover information for the incoming shift @S537 */ }
            perform action a45 { doc /* treats a confirmed restriction as a Grid Constraint until the applicable limit is clarified or withdrawn @S539 */ }
            perform action a46 { doc /* records the revised operating basis @S553 */ }
            perform action a47 { doc /* coordinates updated targets @S553 */ }
            perform action a48 { doc /* maintains a clear record of the restriction, response actions, approvals, and outstanding checks for shift handover @S561 */ }
            perform action a49 { doc /* confirms that the recovery task does not conflict with other offshore work @S639 */ }
            perform action a50 { doc /* is treated as an operational constraint @S668 */ }
            perform action a51 { doc /* uses the Visibility Confidence Note @S669 */ }
            perform action a52 { doc /* considering task readiness and the conditions that would require a decision to pause or defer work @S669 */ }
            perform action a53 { doc /* pause @S669 */ }
            perform action a54 { doc /* defer work @S669 */ }
            perform action a55 { doc /* may be rescheduled @S670 */ }
            perform action a56 { doc /* is given a more conservative assessment @S672 */ }
            perform action a57 { doc /* is deferred @S673 */ }
            perform action a58 { doc /* authorize a task @S675 */ }
            perform action a59 { doc /* reviews forecast demand against current stock @S695 */ }
            perform action a60 { doc /* confirming work readiness @S695 */ }
            perform action a61 { doc /* consolidates proposed work periods @S737 */ }
            perform action a62 { doc /* identifies tasks that require a change to substation configuration @S737 */ }
            perform action a63 { doc /* records actual start and finish times @S758 */ }
            perform action a64 { doc /* improve future estimates and coordination @S758 */ }
            perform action a65 { doc /* links relevant communications and work records to the applicable work package and operating plan @S779 */ }
            perform action a66 { doc /* confirms that the planned work can proceed within the lift capacity and operating limits @S872 */ }
            perform action a67 { doc /* uses reliability findings @S925 */ }
            perform action a68 { doc /* adjust work priorities and planned maintenance intervals when justified @S925 */ }
            perform action a69 { doc /* can prioritize urgent safety work and maintainable generation capacity @S947 */ }
            perform action a70 { doc /* updates operating priorities and deferred work @S955 */ }
            perform action a71 { doc /* checks that maintenance priorities, resource plans, and operational constraints are reflected in planned work @S965 */ }
        }
        part eastServiceLift : EastServiceLift {
            perform action a0 { doc /* runs a door-interlock and overload check @S859 */ }
            perform action a1 { doc /* accepting a movement request @S859 */ }
        }
        part electricalAbsenceOfVoltageChecks : ElectricalAbsenceOfVoltageChecks {
            perform action a0 { doc /* are performed at the work location using suitable, tested equipment @S724 */ }
        }
        part electricalBoundary : ElectricalBoundary {
            perform action a0 { doc /* extends through the farm’s export connection to the point where the Grid Interface Relay represents the interface with the external grid @S004 */ }
        }
        part electricalEnclosures : ElectricalEnclosures;
        part electricalRecoveryWork : ElectricalRecoveryWork;
        part electricalTechnician : ElectricalTechnician {
            perform action a0 { doc /* verifies protective device settings and transfer interlocks during planned maintenance @S185 */ }
            perform action a1 { doc /* identifies the electrical sources, isolation points, and verification steps required by the approved scope @S325 */ }
            perform action a2 { doc /* verifies the relevant local isolation @S327 */ }
            perform action a3 { doc /* secures the equipment against unintended energization @S327 */ }
            perform action a4 { doc /* proves the test instrument @S331 */ }
            perform action a5 { doc /* tests for absence of voltage @S331 */ }
            perform action a6 { doc /* proves the instrument again @S331 */ }
            perform action a7 { doc /* checks that the work area is ready for restoration @S336 */ }
            perform action a8 { doc /* reports any outstanding defects or restrictions @S336 */ }
            perform action a9 { doc /* supports fault diagnosis and maintenance under the applicable work authorization and isolation controls @S363 */ }
            perform action a10 { doc /* coordinate any operational changes with the relevant duty role before implementation @S434 */ }
            perform action a11 { doc /* verifies electrical isolation at the work location @S496 */ }
            perform action a12 { doc /* verifies equipment labels @S529 */ }
            perform action a13 { doc /* confirms the intended switching points @S529 */ }
            perform action a14 { doc /* isolates @S650 */ }
            perform action a15 { doc /* protects recovered electrical equipment @S650 */ }
            perform action a16 { doc /* uses the boundary sketch to identify the approved isolation points before starting the work @S716 */ }
            perform action a17 { doc /* identify the approved isolation points @S716 */ }
            perform action a18 { doc /* starting the work @S716 */ }
            perform action a19 { doc /* confirms that the work scope and test requirements fit the approved duration @S750 */ }
            perform action a20 { doc /* performs local inspection @S801 */ }
            perform action a21 { doc /* verifies that the lift supply and protective devices show no active fault indication @S867 */ }
        }
        part emergencyArrangements : EmergencyArrangements {
            perform action a0 { doc /* define who may direct an incident, who supports rescue, and who may authorize a return to work @S612 */ }
        }
        part emergencyEgress : EmergencyEgress {
            perform action a0 { doc /* without requiring an access credential from the inside of the route @S857 */ }
            exhibit state modes {
                state s0 { doc /* available @S857 */ }
            }
        }
        part emergencyGenerator : EmergencyGenerator {
            perform action a0 { doc /* supplies the designated emergency distribution bus @S180 */ }
            perform action a1 { doc /* is not intended to support turbine export production @S180 */ }
            perform action a2 { doc /* does not start or stabilize @S183 */ }
            perform action a3 { doc /* can start @S186 */ }
            perform action a4 { doc /* accept its expected load @S186 */ }
            perform action a5 { doc /* operate for the required test duration @S186 */ }
            perform action a6 { doc /* produces the Start Test Trace during its scheduled functional test @S353 */ }
            perform action a7 { doc /* fails to start or sustain its required load @S356 */ }
            perform action a8 { doc /* start @S356 */ }
            perform action a9 { doc /* sustain its required load @S356 */ }
            perform action a10 { doc /* supports essential functions @S803 */ }
        }
        part emergencyResponseOrganizations : EmergencyResponseOrganizations;
        part endTime : EndTime;
        part energyProductionMeasures : EnergyProductionMeasures;
        part energySources : EnergySources {
            exhibit state modes {
                state s0 { doc /* safe @S711 */ }
            }
        }
        part entrant : Entrant {
            perform action a0 { doc /* presents an individually assigned credential for validation @S839 */ }
            perform action a1 { doc /* presenting it @S840 */ }
        }
        part entries : Entries {
            perform action a0 { doc /* distinguish observed facts from estimates, assumptions, and recommendations @S775 */ }
        }
        part entryBarrier : EntryBarrier {
            exhibit state modes {
                state s0 { doc /* closed @S846 */ }
            }
        }
        part environmentalLimits : EnvironmentalLimits {
            perform action a0 { doc /* make a planned movement or transfer unsafe @S233 */ }
        }
        part equipment : Equipment {
            perform action a0 { doc /* returns to service @S341 */ }
            exhibit state modes {
                state s0 { doc /* Turbine Lockout @S657 */ }
                state s1 { doc /* safe @S711 */ }
                state s2 { doc /* safe state @S535 */ }
                state s3 { doc /* service @S341 */ }
            }
        }
        part equipmentStatus : EquipmentStatus {
            perform action a0 { doc /* allow safe intervention @S630 */ }
        }
        part estimatedVisibility : EstimatedVisibility {
            perform action a0 { doc /* represents conditions at the intended work location @S667 */ }
        }
        part eventPart : Event {
            perform action a0 { doc /* may affect electrical operation @S307 */ }
            perform action a1 { doc /* require coordination beyond the turbine @S307 */ }
        }
        part eventInvestigations : EventInvestigations;
        part evidence : Evidence {
            perform action a0 { doc /* indicates a developing hazard @S303 */ }
        }
        part expectedLoad : ExpectedLoad;
        part expectedPersonnelCount : ExpectedPersonnelCount;
        part exportCableMonitor : ExportCableMonitor {
            perform action a0 { doc /* provides measurements that support assessment of the export path @S200 */ }
            perform action a1 { doc /* helps planners assess whether cable condition warrants inspection or corrective intervention @S252 */ }
        }
        part exportEquipment : ExportEquipment {
            perform action a0 { doc /* remains within its approved operating range @S549 */ }
        }
        part exportRestriction : ExportRestriction {
            perform action a0 { doc /* may arise from a grid instruction, a cable condition, or a substation operating limit @S538 */ }
            perform action a1 { doc /* changes @S553 */ }
        }
        part externalConnectivity : ExternalConnectivity {
            perform action a0 { doc /* is denied by default @S113 */ }
            perform action a1 { doc /* enabled only for documented operational needs @S113 */ }
        }
        part externalInterfaces : ExternalInterfaces;
        part externalOrganizations : ExternalOrganizations;
        part externalTransmissionSystem : ExternalTransmissionSystem;
        part externalWork : ExternalWork {
            perform action a0 { doc /* affects the achievable start time @S748 */ }
        }
        part failureAnalyses : FailureAnalyses {
            perform action a0 { doc /* use available operating history, inspection findings, and maintenance records @S923 */ }
            perform action a1 { doc /* identify credible causes @S923 */ }
        }
        part farmMonitoringEnvironment : FarmMonitoringEnvironment;
        part faultOnTheExternalSystem : FaultOnTheExternalSystem {
            perform action a0 { doc /* causing unnecessary disconnection of healthy farm equipment @S208 */ }
        }
        part fieldSupervisor : FieldSupervisor {
            perform action a0 { doc /* coordinates task execution offshore @S096 */ }
            perform action a1 { doc /* keeps the Duty Planner informed of changes to work progress @S096 */ }
            perform action a2 { doc /* considers remote observations alongside site conditions @S145 */ }
            perform action a3 { doc /* recommending follow-up work @S145 */ }
            perform action a4 { doc /* verifies that the approved conditions remain valid @S167 */ }
            perform action a5 { doc /* checks reported faults against available evidence @S253 */ }
            perform action a6 { doc /* identifies work that requires an offshore visit @S253 */ }
            perform action a7 { doc /* confirms that the proposed method, access arrangements, and work party are suitable for the task @S320 */ }
            perform action a8 { doc /* confirms that the permit is active and the required isolations have been independently verified @S329 */ }
            perform action a9 { doc /* briefs the crew on the permit limits, isolation boundaries, communications, and conditions requiring work to stop @S330 */ }
            perform action a10 { doc /* pause work @S333 */ }
            perform action a11 { doc /* reassess the authorization @S333 */ }
            perform action a12 { doc /* confirms that tools, temporary connections, and personnel are clear @S335 */ }
            perform action a13 { doc /* requesting isolation removal @S335 */ }
            perform action a14 { doc /* confirms completion @S340 */ }
            perform action a15 { doc /* formally records any remaining work @S340 */ }
            perform action a16 { doc /* confirms the work party is complete @S405 */ }
            perform action a17 { doc /* escalates any unexplained absence or overdue check-in to Marine Coordinator without delay @S412 */ }
            perform action a18 { doc /* checks that cybersecurity requirements are included in the work briefing @S429 */ }
            perform action a19 { doc /* uses the Deferred Task Rationale @S430 */ }
            perform action a20 { doc /* confirms that close-access findings are documented before personnel leave the work area @S457 */ }
            perform action a21 { doc /* reviews the worksite limits with the crew @S493 */ }
            perform action a22 { doc /* verifies each worker's authorization, competence, and fitness for the assigned task @S503 */ }
            perform action a23 { doc /* pauses the job @S509 */ }
            perform action a24 { doc /* confirms personnel are clear of affected equipment @S536 */ }
            perform action a25 { doc /* directs personnel at the affected work site @S615 */ }
            perform action a26 { doc /* maintains control of the work area @S649 */ }
            perform action a27 { doc /* stops handling @S649 */ }
            perform action a28 { doc /* could affect turbine systems or restart readiness @S658 */ }
            perform action a29 { doc /* reports remaining hazards @S660 */ }
            perform action a30 { doc /* confirms that temporary securing arrangements are adequate for transit @S660 */ }
            perform action a31 { doc /* briefs the crew on the boundary, access restrictions, and conditions that require work to stop @S717 */ }
            perform action a32 { doc /* confirms that every crew member understands the limits of the approved work area @S726 */ }
            perform action a33 { doc /* ensures that field observations and work outcomes are entered promptly while the details remain verifiable @S778 */ }
            perform action a34 { doc /* confirms work party status @S809 */ }
            perform action a35 { doc /* reports unresolved personnel or access concerns to the Shore Control Room @S809 */ }
            perform action a36 { doc /* reviews unusual denial patterns and unresolved access exceptions during the work shift @S826 */ }
            perform action a37 { doc /* coordinates the inspection before the first planned movement of each operating shift @S860 */ }
            perform action a38 { doc /* records the inspection result and any observed defects in the maintenance system @S869 */ }
            perform action a39 { doc /* confirms that no person is exposed to a suspended or shifting load during movement @S879 */ }
            perform action a40 { doc /* communicates the release status to the work party @S881 */ }
            perform action a41 { doc /* records the time that service is authorized @S881 */ }
            perform action a42 { doc /* confirms that the work authorization covers the intended landing and task @S886 */ }
            perform action a43 { doc /* verifies that the landing is accessible and that the route is clear of obstructions @S887 */ }
            perform action a44 { doc /* ensures that the lift is left secure and that any irregularity is reported through the established site process @S906 */ }
            perform action a45 { doc /* provides feedback on whether revised procedures and controls are practical during offshore work @S927 */ }
            perform action a46 { doc /* confirms that field execution practices and escalation routes are workable for offshore personnel @S970 */ }
        }
        part fieldTeam : FieldTeam {
            perform action a0 { doc /* use the same revision @S729 */ }
            perform action a1 { doc /* confirming isolation status @S729 */ }
        }
        part fieldWork : FieldWork {
            perform action a0 { doc /* begins @S711 */ }
        }
        part finalWindow : FinalWindow {
            perform action a0 { doc /* allows time for switching, work execution, testing, and restoration @S747 */ }
        }
        part fire : Fire {
            perform action a0 { doc /* threatens electrical equipment or personnel @S792 */ }
        }
        part fireDetectionPanel : FireDetectionPanel {
            perform action a0 { doc /* provides alarm indications @S629 */ }
            perform action a1 { doc /* supervises detection circuits @S786 */ }
            perform action a2 { doc /* annunciates alarms with location and fault information @S786 */ }
        }
        part fireProtection : FireProtection {
            perform action a0 { doc /* detect smoke, heat, and flame @S785 */ }
            perform action a1 { doc /* support automatic equipment protection and a controlled personnel response @S785 */ }
        }
        part fleetDispatchConsole : FleetDispatchConsole {
            perform action a0 { doc /* supports the coordination of operational resources across the farm @S041 */ }
            perform action a1 { doc /* provides a fleet-level view of dispatch activity for operational coordination @S069 */ }
            perform action a2 { doc /* gives the Marine Coordinator a shared view of vessel assignments, planned movements, and dispatch status @S081 */ }
            perform action a3 { doc /* allocates requested farm output among available generating units @S203 */ }
            perform action a4 { doc /* uses the quality flag to support movement planning @S225 */ }
            perform action a5 { doc /* support movement planning @S225 */ }
            perform action a6 { doc /* assigns vessel and crew resources to approved work packages @S260 */ }
            perform action a7 { doc /* compares the requested output with available turbine capability and known operating restrictions @S370 */ }
            perform action a8 { doc /* retains the instruction history and the corresponding plant response for later review @S385 */ }
            perform action a9 { doc /* supports coordinated adjustment of turbine output across the affected operating area @S543 */ }
            perform action a10 { doc /* provides a fleet-level view of operating status and response to emerging constraints @S917 */ }
            perform action a11 { doc /* presents operational restrictions @S947 */ }
        }
        part fleetDispatchConsoleSchedules : FleetDispatchConsoleSchedules {
            perform action a0 { doc /* reflect confirmed changes to vessel availability and offshore task timing @S485 */ }
        }
        part fogBanks : FogBanks {
            perform action a0 { doc /* move through the area @S662 */ }
        }
        part forecastConditions : ForecastConditions {
            perform action a0 { doc /* could affect the planned sequence @S522 */ }
        }
        part forecastOrObservedConditions : ForecastOrObservedConditions {
            perform action a0 { doc /* exceed the approved operating limits @S259 */ }
        }
        part forecastUpdates : ForecastUpdates {
            perform action a0 { doc /* support timing decisions for remote observation and field work @S128 */ }
        }
        part gate : Gate {
            exhibit state modes {
                state s0 { doc /* secured @S816 */ }
            }
        }
        part goOrNoGoDecision : GoOrNoGoDecision {
            perform action a0 { doc /* considers the task method, crew competence, vessel capability, and the confidence in the visibility assessment @S674 */ }
        }
        part gridConstraint : GridConstraint {
            perform action a0 { doc /* may require reduced export, revised dispatch, or temporary disconnection @S210 */ }
            perform action a1 { doc /* requires the Duty Planner to reassess the sequence and obtain revised authorization before work proceeds @S519 */ }
            perform action a2 { doc /* may require the requested window to be shortened, moved, or divided into separate periods @S746 */ }
        }
        part gridDispatch : GridDispatch;
        part gridDispatcher : GridDispatcher {
            perform action a0 { doc /* sets external dispatch requirements within the applicable connection agreement @S202 */ }
            perform action a1 { doc /* issues active-power targets and ramp instructions through the established dispatch channel @S367 */ }
            perform action a2 { doc /* confirms applicable grid requirements and any restrictions on changing the connection state @S518 */ }
            perform action a3 { doc /* changing the connection state @S518 */ }
            perform action a4 { doc /* receives the Export Limit Advisory @S541 */ }
            perform action a5 { doc /* uses it to set the permitted export level @S541 */ }
            perform action a6 { doc /* set the permitted export level @S541 */ }
            perform action a7 { doc /* confirms that the requested period is compatible with export requirements and network operating limits @S739 */ }
            perform action a8 { doc /* communicates external operating requirements to the Grid Interface Relay and the responsible control personnel @S769 */ }
        }
        part gridInterfaceRelay : GridInterfaceRelay {
            perform action a0 { doc /* represents the interface with the external grid @S004 */ }
            perform action a1 { doc /* provides status indications that support assessment of the normal supply and its protective state @S190 */ }
            perform action a2 { doc /* defines the operational boundary between the offshore farm and the external transmission system @S197 */ }
            perform action a3 { doc /* exchanges authorized operating signals with the transmission system at the agreed interface @S201 */ }
            perform action a4 { doc /* maintains the farm's dispatch boundary @S221 */ }
            perform action a5 { doc /* allowing local systems to manage turbine-level operation @S221 */ }
            perform action a6 { doc /* produces an Export Limit Advisory @S372 */ }
            perform action a7 { doc /* applies the accepted export ceiling to control outputs @S373 */ }
            perform action a8 { doc /* records its effective time for audit @S373 */ }
            perform action a9 { doc /* retains its protection settings unless an authorized switching plan requires a controlled change @S551 */ }
            perform action a10 { doc /* remains available for the required protection and control functions throughout the planned work @S743 */ }
            perform action a11 { doc /* applies the configured response to a Grid Constraint @S942 */ }
        }
        part hSEOfficer : HSEOfficer {
            perform action a0 { doc /* verifies that work arrangements account for applicable safety controls and personnel responsibilities @S095 */ }
            perform action a1 { doc /* reviews the proposed controls when the task presents a material personnel or environmental risk @S157 */ }
            perform action a2 { doc /* produces the Harness Audit Card before the applicable transfer activity @S237 */ }
            perform action a3 { doc /* reviews hazards @S266 */ }
            perform action a4 { doc /* confirms that proposed controls match the task scope and site conditions @S266 */ }
            perform action a5 { doc /* reviews task hazards @S322 */ }
            perform action a6 { doc /* confirms that required controls are assigned @S322 */ }
            perform action a7 { doc /* verifies that personnel expected at the work site are accounted for during scheduled checks @S408 */ }
            perform action a8 { doc /* reviews the work method, exposure controls, and emergency arrangements @S451 */ }
            perform action a9 { doc /* checks that access controls, emergency arrangements, and handling precautions are suitable for the planned activity @S481 */ }
            perform action a10 { doc /* checks that emergency routes, muster points, and rescue arrangements are understood by everyone at the worksite @S505 */ }
            perform action a11 { doc /* reviews task hazards @S526 */ }
            perform action a12 { doc /* confirms that required controls are in place @S526 */ }
            perform action a13 { doc /* is authorized @S526 */ }
            perform action a14 { doc /* assesses any safety implications @S579 */ }
            perform action a15 { doc /* advises whether the affected activity can continue @S579 */ }
            perform action a16 { doc /* advises on personnel hazards, rescue procedures, and the use of emergency equipment @S617 */ }
            perform action a17 { doc /* reviews the handling method, lifting points, and exclusion zones @S647 */ }
            perform action a18 { doc /* advises on exposure, evacuation, and re-entry criteria in coordination with the incident response team @S808 */ }
            perform action a19 { doc /* can use the recorded entry history to support personnel accountability during an incident @S827 */ }
            perform action a20 { doc /* support personnel accountability during an incident @S827 */ }
            perform action a21 { doc /* reviews any proposed workaround that changes established access, isolation, or personnel-control arrangements @S949 */ }
            perform action a22 { doc /* evaluates safety controls, emergency arrangements, and lessons from reported events @S967 */ }
        }
        part handsOnActivity : HandsOnActivity {
            perform action a0 { doc /* begins @S631 */ }
        }
        part handsOnWork : HandsOnWork {
            perform action a0 { doc /* begins @S725 */ }
            perform action a1 { doc /* continues @S727 */ }
        }
        part hazards : Hazards;
        part helideck : Helideck;
        part incidentLead : IncidentLead {
            perform action a0 { doc /* classifies each report @S432 */ }
            perform action a1 { doc /* assigns an owner @S432 */ }
            perform action a2 { doc /* records its time, scope, and current status @S432 */ }
            perform action a3 { doc /* confirms that the threat is contained and the affected system is suitable for return to service @S436 */ }
            perform action a4 { doc /* verifies headcounts with the teams involved @S619 */ }
        }
        part incomingSupervisor : IncomingSupervisor;
        part incomingTeam : IncomingTeam {
            perform action a0 { doc /* independently checks the boundary status @S731 */ }
            perform action a1 { doc /* accepting responsibility for ongoing work @S731 */ }
        }
        part indicators : Indicators {
            perform action a0 { doc /* operate as intended @S854 */ }
        }
        part inspection : Inspection {
            perform action a0 { doc /* begins with a visual check of the car, landing doors, guide surfaces, and access barriers @S861 */ }
        }
        part inspectionRecord : InspectionRecord {
            perform action a0 { doc /* identifies the uncertainty @S456 */ }
            perform action a1 { doc /* specifies additional measurements or imagery needed @S456 */ }
        }
        part inspector : Inspector {
            perform action a0 { doc /* confirms that the car floor and landing thresholds are clear of loose material and standing water @S862 */ }
            perform action a1 { doc /* checks the operating controls for damage, legibility, and secure mounting @S865 */ }
            perform action a2 { doc /* confirms that the rated capacity and operating instructions remain legible at the car entrance @S868 */ }
        }
        part installationTeam : InstallationTeam {
            perform action a0 { doc /* verifies the scanner, barrier, and communications @S853 */ }
        }
        part instructions : Instructions {
            perform action a0 { doc /* affect electrical safety @S770 */ }
        }
        part inventoryRecord : InventoryRecord {
            perform action a0 { doc /* covers serviceable parts, consumables, repairable units, and their locations across shore and offshore stores @S686 */ }
        }
        part isolation : Isolation;
        part isolationBoundary : IsolationBoundary {
            perform action a0 { doc /* defines the equipment and energy sources that must be made safe before field work begins @S711 */ }
        }
        part isolationDevice : IsolationDevice {
            perform action a0 { doc /* is secured against unintended operation using the site-approved locking and tagging method @S722 */ }
        }
        part items : Items {
            perform action a0 { doc /* approaching their reorder point @S701 */ }
        }
        part landingThresholds : LandingThresholds {
            exhibit state modes {
                state s0 { doc /* clear of loose material and standing water @S862 */ }
            }
        }
        part laterReviewers : LaterReviewers {
            perform action a0 { doc /* can assess their basis @S775 */ }
        }
        part lessonsLearned : LessonsLearned {
            perform action a0 { doc /* continue to reflect actual operating experience @S933 */ }
        }
        part liftSupply : LiftSupply {
            perform action a0 { doc /* show no active fault indication @S867 */ }
        }
        part lightingInsideTheCarAndAtEachLanding : LightingInsideTheCarAndAtEachLanding;
        part localConditions : LocalConditions {
            perform action a0 { doc /* may develop sooner or differently than forecast @S664 */ }
        }
        part localProtectionFunctions : LocalProtectionFunctions {
            perform action a0 { doc /* retain priority when remote requests conflict with safe operating limits @S137 */ }
        }
        part localReference : LocalReference {
            perform action a0 { doc /* can help identify differences between forecast conditions and conditions at sea @S665 */ }
        }
        part localSystems : LocalSystems {
            perform action a0 { doc /* manage turbine-level operation @S221 */ }
        }
        part localVisualIndicator : LocalVisualIndicator {
            perform action a0 { doc /* communicates whether entry is permitted or denied @S845 */ }
        }
        part longOrUnstableLoads : LongOrUnstableLoads;
        part lossOfCommunications : LossOfCommunications {
            perform action a0 { doc /* does not remove local electrical protection or equipment interlocks @S209 */ }
        }
        part lowCloud : LowCloud {
            perform action a0 { doc /* move through the area @S662 */ }
        }
        part lowConfidence : LowConfidence {
            perform action a0 { doc /* affects the planned transit, transfer location, and available alternatives @S676 */ }
        }
        part lowStockAlerts : LowStockAlerts {
            perform action a0 { doc /* identify items approaching their reorder point @S701 */ }
            perform action a1 { doc /* show open purchase commitments @S701 */ }
        }
        part machinerySpaces : MachinerySpaces;
        part mainTransformer : MainTransformer;
        part maintenance : Maintenance {
            perform action a0 { doc /* begins @S490 */ }
        }
        part maintenanceActivities : MaintenanceActivities;
        part maintenancePlanningEngine : MaintenancePlanningEngine {
            perform action a0 { doc /* supports the preparation and sequencing of maintenance activities @S042 */ }
            perform action a1 { doc /* supports work preparation @S054 */ }
            perform action a2 { doc /* organizing maintenance needs, resource considerations, and planning constraints @S054 */ }
            perform action a3 { doc /* supports planning decisions @S066 */ }
            perform action a4 { doc /* can use reviewed condition information @S148 */ }
            perform action a5 { doc /* prioritizing future maintenance activities @S148 */ }
            perform action a6 { doc /* can use reviewed condition information @S154 */ }
            perform action a7 { doc /* prioritizing future maintenance activities @S154 */ }
            perform action a8 { doc /* schedules inspections and corrective work using equipment condition and operating history @S188 */ }
            perform action a9 { doc /* using equipment condition and operating history @S188 */ }
            perform action a10 { doc /* schedules periodic reviews of standby electrical maintenance requirements and outstanding corrective work @S195 */ }
            perform action a11 { doc /* uses the Squall Window Bulletin when reviewing the timing of planned work @S213 */ }
            perform action a12 { doc /* reviewing the timing of planned work @S213 */ }
            perform action a13 { doc /* ranks planned and corrective work using asset condition, safety exposure, production impact, access feasibility, and resource availability @S246 */ }
            perform action a14 { doc /* using asset condition, safety exposure, production impact, access feasibility, and resource availability @S246 */ }
            perform action a15 { doc /* produces the Deferred Task Rationale @S285 */ }
            perform action a16 { doc /* receives validated condition information for prioritization and scheduling of follow-up work @S308 */ }
            perform action a17 { doc /* combines inspection intervals, prior defect history, and turbine availability @S441 */ }
            perform action a18 { doc /* propose survey dates @S441 */ }
            perform action a19 { doc /* uses the assessed severity, defect growth rate, weather exposure, and production impact to support repair prioritization @S458 */ }
            perform action a20 { doc /* support repair prioritization @S458 */ }
            perform action a21 { doc /* supports this review by presenting task duration, resource demand, and dependency status @S470 */ }
            perform action a22 { doc /* presenting task duration, resource demand, and dependency status @S470 */ }
            perform action a23 { doc /* provides the planned work period @S520 */ }
            perform action a24 { doc /* identifies dependencies with other scheduled tasks @S520 */ }
            perform action a25 { doc /* can help identify tasks that may be rescheduled when visibility is uncertain @S670 */ }
            perform action a26 { doc /* uses planned work demand and part criticality to support replenishment forecasts @S694 */ }
            perform action a27 { doc /* support replenishment forecasts @S694 */ }
            perform action a28 { doc /* checks task durations, dependencies, and resource assumptions @S738 */ }
            perform action a29 { doc /* supports review of planned work, resource demand, and maintenance completion performance @S918 */ }
            perform action a30 { doc /* separates safety-critical work from tasks that can safely wait until normal access and support are available @S948 */ }
        }
        part maintenanceRecords : MaintenanceRecords;
        part marineAccess : MarineAccess {
            perform action a0 { doc /* affects the achievable start time @S748 */ }
        }
        part marineCoordination : MarineCoordination {
            perform action a0 { doc /* aligns vessel movements, personnel transfers, and shore-side support with the approved work schedule @S222 */ }
        }
        part marineCoordinator : MarineCoordinator {
            perform action a0 { doc /* considers offshore conditions and vessel availability @S068 */ }
            perform action a1 { doc /* coordinating access to work sites @S068 */ }
            perform action a2 { doc /* aligns vessel availability with crew readiness, port access, and the planned work locations @S077 */ }
            perform action a3 { doc /* uses that view @S082 */ }
            perform action a4 { doc /* coordinate the Crew Transfer Vessel, the Service Operations Vessel, and the Daughter Craft @S082 */ }
            perform action a5 { doc /* uses the available traffic picture @S141 */ }
            perform action a6 { doc /* support coordination of offshore movements @S141 */ }
            perform action a7 { doc /* checks that the planned access method and timing are practical for the work location @S160 */ }
            perform action a8 { doc /* maintains the daily marine plan @S223 */ }
            perform action a9 { doc /* resolves conflicts between planned activities @S223 */ }
            perform action a10 { doc /* records changes to the movement plan @S245 */ }
            perform action a11 { doc /* ensures that affected teams receive the update @S245 */ }
            perform action a12 { doc /* compares expected access conditions with vessel capability, transit time, and worksite limits @S257 */ }
            perform action a13 { doc /* coordinates resource changes with the Vessel Master and affected work teams @S261 */ }
            perform action a14 { doc /* reviews access options and vessel availability @S277 */ }
            perform action a15 { doc /* reassesses the route @S283 */ }
            perform action a16 { doc /* seeks an updated forecast @S290 */ }
            perform action a17 { doc /* confirming a departure or transfer plan @S290 */ }
            perform action a18 { doc /* reviews the intended crew movement against vessel capacity and operating conditions @S397 */ }
            perform action a19 { doc /* monitors reported vessel movements during transit to offshore locations @S400 */ }
            perform action a20 { doc /* reviews return movements @S410 */ }
            perform action a21 { doc /* maintains a rolling view of berth occupancy, planned arrivals, departure estimates, and vessel service requirements @S466 */ }
            perform action a22 { doc /* uses the Berth Slot Confirmation @S473 */ }
            perform action a23 { doc /* align an approved vessel arrival with the assigned berth window @S473 */ }
            perform action a24 { doc /* resolves competing berth requests @S483 */ }
            perform action a25 { doc /* considering task urgency, vessel compatibility, and the consequences of delay @S483 */ }
            perform action a26 { doc /* reviews safe alternatives such as a later slot, a different suitable berth, or vessel standby @S488 */ }
            perform action a27 { doc /* suspends access @S499 */ }
            perform action a28 { doc /* aligns vessel movements with the approved access plan and operational constraints @S523 */ }
            perform action a29 { doc /* establishes the expected personnel count and destination for each movement @S565 */ }
            perform action a30 { doc /* pauses further personnel transfers @S576 */ }
            perform action a31 { doc /* informs the Shore Control Room of the discrepancy and the immediate control actions @S578 */ }
            perform action a32 { doc /* escalates any unresolved discrepancy to the Duty Planner @S583 */ }
            perform action a33 { doc /* records the time of escalation @S583 */ }
            perform action a34 { doc /* confirms that the count is reconciled or an authorized response is in place @S585 */ }
            perform action a35 { doc /* maintains awareness of vessel locations, access constraints, and available marine support @S618 */ }
            perform action a36 { doc /* assigns suitable vessels @S638 */ }
            perform action a37 { doc /* maintains a common plan for their approach and departure @S638 */ }
            perform action a38 { doc /* pauses the recovery @S659 */ }
            perform action a39 { doc /* agrees a safe holding position with the Vessel Master @S659 */ }
            perform action a40 { doc /* reviews how uncertainty affects the planned transit, transfer location, and available alternatives @S676 */ }
            perform action a41 { doc /* reassess the route and the suitability of continuing toward the work site @S682 */ }
            perform action a42 { doc /* checks vessel movements and crew transfer timing against the proposed period @S749 */ }
            perform action a43 { doc /* shares relevant marine and weather information with vessel personnel and the Duty Planner @S764 */ }
            perform action a44 { doc /* confirm that personnel and vessels can remain safely accounted for during an extended interruption @S944 */ }
            perform action a45 { doc /* reviews vessel coordination arrangements @S966 */ }
            perform action a46 { doc /* verifies that marine responsibilities are understood @S966 */ }
        }
        part markedLimits : MarkedLimits {
            perform action a0 { doc /* match the current isolation points and the approved maintenance scope @S495 */ }
        }
        part measuredConditions : MeasuredConditions {
            perform action a0 { doc /* approach a limit @S291 */ }
        }
        part measuredDelivery : MeasuredDelivery {
            perform action a0 { doc /* differs materially from the instructed target @S383 */ }
        }
        part measuredExport : MeasuredExport {
            perform action a0 { doc /* follows the revised target @S544 */ }
        }
        part measurementIntervals : MeasurementIntervals {
            perform action a0 { doc /* are configured to support both trend analysis and timely operational decisions @S108 */ }
            perform action a1 { doc /* support both trend analysis and timely operational decisions @S108 */ }
        }
        part measurements : Measurements {
            perform action a0 { doc /* support assessment of the export path @S200 */ }
        }
        part metoceanBuoy : MetoceanBuoy {
            perform action a0 { doc /* is designated Copper Finch for operational reference @S101 */ }
            perform action a1 { doc /* measures wind speed and direction, wave height and period, current, air temperature, and barometric pressure @S102 */ }
            perform action a2 { doc /* produces the Wave Burst Record at the configured sampling interval @S194 */ }
            perform action a3 { doc /* reports local sea conditions for use in access planning @S231 */ }
            perform action a4 { doc /* provide contextual conditions that help reviewers distinguish environmental effects from equipment deterioration @S309 */ }
            perform action a5 { doc /* provide forecasts and measured conditions @S443 */ }
            perform action a6 { doc /* provides site measurements @S625 */ }
            perform action a7 { doc /* provides a local reference @S665 */ }
            perform action a8 { doc /* provide inputs @S766 */ }
        }
        part metoceanObservations : MetoceanObservations;
        part mismatchBetweenTheFieldLabelAndTheApprovedRecord : MismatchBetweenTheFieldLabelAndTheApprovedRecord {
            perform action a0 { doc /* prevents the crew from proceeding until it is resolved @S721 */ }
        }
        part monitoringAndControlAssumptions : MonitoringAndControlAssumptions {
            perform action a0 { doc /* affect operational decisions @S968 */ }
        }
        part monitoringAndControlFunctions : MonitoringAndControlFunctions;
        part monitoringProcess : MonitoringProcess {
            perform action a0 { doc /* retains the source, timestamp, and turbine identifier for each observation @S296 */ }
        }
        part monitoringRules : MonitoringRules {
            perform action a0 { doc /* identify unusual login patterns, unexpected configuration changes, and communications outside approved operating windows @S418 */ }
        }
        part nacelleConditionMonitor : NacelleConditionMonitor {
            perform action a0 { doc /* provides equipment measurements for ongoing assessment of turbine health @S132 */ }
            perform action a1 { doc /* provides condition data that helps distinguish developing degradation from transient alarms @S250 */ }
            perform action a2 { doc /* provides condition information @S793 */ }
            perform action a3 { doc /* supports assessment of equipment condition and emerging degradation @S915 */ }
        }
        part needDate : NeedDate;
        part networkSegmentation : NetworkSegmentation {
            perform action a0 { doc /* limits the effect of a compromised endpoint @S120 */ }
            perform action a1 { doc /* supports controlled restoration of service @S120 */ }
        }
        part newCondition : NewCondition {
            perform action a0 { doc /* could compromise safe movement @S883 */ }
        }
        part normalMonitoringResponsibilities : NormalMonitoringResponsibilities {
            perform action a0 { doc /* resume @S437 */ }
        }
        part normalSupply : NormalSupply {
            perform action a0 { doc /* serves control systems, lighting, ventilation, communications, and equipment required for safe switching and maintenance @S174 */ }
        }
        part normalWork : NormalWork {
            perform action a0 { doc /* resumes @S635 */ }
        }
        part northAccessScanner : NorthAccessScanner {
            perform action a0 { doc /* records authorized entry at the north access point @S235 */ }
            perform action a1 { doc /* records identity checks at the north shore access point @S394 */ }
            perform action a2 { doc /* records personnel access events at the north access point @S569 */ }
            perform action a3 { doc /* validates each presented credential against current access authorization @S810 */ }
            perform action a4 { doc /* enabling controlled entry @S810 */ }
            perform action a5 { doc /* accepts only credentials that can be read reliably and associated with an identifiable person @S811 */ }
        }
        part observation : Observation {
            perform action a0 { doc /* suggests a risk to personnel or equipment @S306 */ }
        }
        part observations : Observations {
            perform action a0 { doc /* give the team a local reference for checking forecast trends and current sea state @S271 */ }
        }
        part observedCount : ObservedCount;
        part occupants : Occupants {
            perform action a0 { doc /* remain inside the car @S899 */ }
            perform action a1 { doc /* avoid interfering with the controls or doors @S899 */ }
            perform action a2 { doc /* use the designated alarm or communication method @S902 */ }
            perform action a3 { doc /* remain inside the car @S902 */ }
            perform action a4 { doc /* exit without crowding @S905 */ }
            exhibit state modes {
                state s0 { doc /* ready @S898 */ }
            }
        }
        part offshoreEnvironmentalObservations : OffshoreEnvironmentalObservations {
            perform action a0 { doc /* support safe farm operations @S100 */ }
        }
        part offshoreFarm : OffshoreFarm {
            perform action a0 { doc /* exports electrical power through the Offshore Substation, Main Transformer, and export cable to the designated grid connection point @S199 */ }
            perform action a1 { doc /* reports measured active power at the grid boundary for operational monitoring and settlement processes @S205 */ }
        }
        part offshoreGenerationAssets : OffshoreGenerationAssets;
        part offshorePersonnel : OffshorePersonnel {
            perform action a0 { doc /* follow posted escape routes @S804 */ }
            perform action a1 { doc /* muster at the designated assembly point @S804 */ }
        }
        part offshoreRecovery : OffshoreRecovery {
            perform action a0 { doc /* begins @S636 */ }
        }
        part offshoreRecoveryPlans : OffshoreRecoveryPlans {
            perform action a0 { doc /* identify the point at which continued response would expose rescuers to unacceptable risk @S633 */ }
        }
        part offshoreSubstation : OffshoreSubstation {
            perform action a0 { doc /* provides the farm's offshore electrical collection and switching environment @S037 */ }
            perform action a1 { doc /* maintains the designated emergency distribution bus within its approved operating limits @S189 */ }
            perform action a2 { doc /* sends a Transformer Tap Snapshot @S267 */ }
            perform action a3 { doc /* uses the Switching Window Acknowledgment @S752 */ }
            perform action a4 { doc /* confirm that the approved switching window is available for the planned work @S752 */ }
            perform action a5 { doc /* enters Substation Degraded when a protection, auxiliary supply, or monitoring impairment limits safe switching or export capability @S941 */ }
            exhibit state modes {
                state s0 { doc /* Substation Degraded @S361,S941 */ }
            }
        }
        part offshoreSupportFacilities : OffshoreSupportFacilities;
        part offshoreWindFarm : OffshoreWindFarm {
            perform action a0 { doc /* transition from construction control to operations control through documented handover and verification @S015 */ }
            perform action a1 { doc /* operates in a variable marine environment @S028 */ }
            exhibit state modes {
                state s0 { doc /* acceptance @S014 */ }
                state s1 { doc /* commissioning @S014 */ }
                state s2 { doc /* construction control @S015 */ }
                state s3 { doc /* decommissioning @S014 */ }
                state s4 { doc /* end of life @S019 */ }
                state s5 { doc /* major refurbishment @S014 */ }
                state s6 { doc /* normal service @S016 */ }
                state s7 { doc /* operations control @S015 */ }
                state s8 { doc /* routine operation @S014 */ }
            }
        }
        part offshoreWindFarmOperationsAndMaintenanceSystem : OffshoreWindFarmOperationsAndMaintenanceSystem;
        part onDutyOperationsLead : OnDutyOperationsLead;
        part onboardLogger : OnboardLogger {
            perform action a0 { doc /* timestamps observations @S104 */ }
            perform action a1 { doc /* retains a local history during intermittent communications @S104 */ }
        }
        part operatingConcept : OperatingConcept {
            exhibit state modes {
                state s0 { doc /* effective @S983 */ }
            }
        }
        part operatingData : OperatingData {
            perform action a0 { doc /* helps distinguish persistent defects from transient changes in blade appearance @S447 */ }
        }
        part operatingOrganization : OperatingOrganization {
            perform action a0 { doc /* combines shore-based planning, marine coordination, vessel crews, and technicians assigned to offshore work @S075 */ }
            perform action a1 { doc /* maintain an accurate view of personnel assigned to offshore activities @S094 */ }
            perform action a2 { doc /* uses defined handoffs @S098 */ }
        }
        part operatingPersonnel : OperatingPersonnel {
            perform action a0 { doc /* accept the restored condition @S341 */ }
            perform action a1 { doc /* rely on remote indications @S349 */ }
        }
        part operatingPlan : OperatingPlan {
            perform action a0 { doc /* permit its use @S088 */ }
        }
        part operatingRestrictions : OperatingRestrictions;
        part operationalAssessment : OperationalAssessment {
            perform action a0 { doc /* records both the estimated visibility and the confidence that the estimate represents conditions at the intended work location @S667 */ }
        }
        part operationalBoundary : OperationalBoundary {
            perform action a0 { doc /* covers the wind farm assets, offshore support facilities, control functions, and maintenance activities required to deliver safe electrical generation @S002 */ }
        }
        part operationalCommunications : OperationalCommunications {
            perform action a0 { doc /* support safe decisions @S760 */ }
            perform action a1 { doc /* providing timely, clear, and traceable information to the people responsible for offshore work @S760 */ }
        }
        part operationalDecisions : OperationalDecisions {
            perform action a0 { doc /* account for observed local conditions @S624 */ }
        }
        part operationalHandoverRecords : OperationalHandoverRecords {
            perform action a0 { doc /* identify the deployed change, any outstanding limitations, and the responsible technical contact @S611 */ }
        }
        part operationalMonitoring : OperationalMonitoring;
        part operationalNotices : OperationalNotices {
            perform action a0 { doc /* affecting the farm interface @S214 */ }
        }
        part operationalPersonnel : OperationalPersonnel {
            perform action a0 { doc /* retain authority for decisions that require procedural, safety, or engineering judgment @S073 */ }
            perform action a1 { doc /* supports maintainable operations @S074 */ }
            perform action a2 { doc /* keeping supervisory functions distinct from planning and human coordination @S074 */ }
        }
        part operationalProcedures : OperationalProcedures {
            perform action a0 { doc /* identify the authority for approving access, responding to alarms, and returning affected services to normal operation @S122 */ }
        }
        part operationalRecords : OperationalRecords {
            perform action a0 { doc /* identify the originator, recipient, event time, recording time, relevant asset, and decision or action taken @S774 */ }
            perform action a1 { doc /* use synchronized time sources where available @S776 */ }
        }
        part operationalReports : OperationalReports {
            perform action a0 { doc /* indicate that blade condition requires review @S440 */ }
        }
        part operationalSystem : OperationalSystem;
        part operationsRadioConsole : OperationsRadioConsole {
            perform action a0 { doc /* supports routine communications and escalation during offshore activity @S239 */ }
            perform action a1 { doc /* supports communications between the Shore Control Room, vessels, and offshore work teams @S627 */ }
            perform action a2 { doc /* supports voice communication with the Crew Transfer Vessel, Service Operations Vessel, and Daughter Craft @S762 */ }
            perform action a3 { doc /* provides a coordinated communications channel for response instructions and status reports @S806 */ }
        }
        part operationsTeam : OperationsTeam;
        part operator : Operator {
            perform action a0 { doc /* records test results @S356 */ }
            perform action a1 { doc /* raises a defect promptly @S356 */ }
            perform action a2 { doc /* operating a breaker or isolator @S359 */ }
            perform action a3 { doc /* verifies the required clearances @S359 */ }
            perform action a4 { doc /* confirms that affected parties are informed @S359 */ }
            perform action a5 { doc /* limits further switching @S360 */ }
            perform action a6 { doc /* escalates the condition @S360 */ }
            perform action a7 { doc /* places the Offshore Substation in Substation Degraded when required by operating procedures @S361 */ }
            perform action a8 { doc /* communicates the resulting restrictions @S361 */ }
            perform action a9 { doc /* records its scope, start time, and expected review point @S376 */ }
            perform action a10 { doc /* positions each load @S878 */ }
            perform action a11 { doc /* avoid obstructing doors, controls, and emergency access @S878 */ }
            perform action a12 { doc /* checks the lift identification, rated capacity, and current service status before each operating period @S888 */ }
            perform action a13 { doc /* confirms that the car floor is level with the boarding landing @S890 */ }
            perform action a14 { doc /* permitting entry or exit @S890 */ }
            perform action a15 { doc /* checks that the controls respond correctly and that the emergency stop is accessible @S892 */ }
            perform action a16 { doc /* confirms that the expected load, including tools and carried equipment, remains within the rated capacity @S895 */ }
            perform action a17 { doc /* confirms that all occupants are ready and that the doors are fully closed @S898 */ }
            perform action a18 { doc /* starting movement @S898 */ }
            perform action a19 { doc /* monitors lift movement for unusual noise, vibration, hesitation, or irregular stopping @S900 */ }
            perform action a20 { doc /* stop the lift at the nearest safe landing when practicable @S901 */ }
            perform action a21 { doc /* confirms that the car is level and stationary @S904 */ }
            perform action a22 { doc /* opening the doors @S904 */ }
            perform action a23 { doc /* checks that tools and equipment have been removed from the car @S905 */ }
            perform action a24 { doc /* periodically evaluates whether assurance arrangements provide sufficient evidence that the concept remains effective @S983 */ }
        }
        part operators : Operators {
            perform action a0 { doc /* use the approved recovery procedure @S184 */ }
            perform action a1 { doc /* assess the fault @S184 */ }
            perform action a2 { doc /* preserve essential services @S184 */ }
            perform action a3 { doc /* restore the normal supply when it is safe to do so @S184 */ }
            perform action a4 { doc /* verify the scanner clock and connectivity during routine readiness checks @S832 */ }
            perform action a5 { doc /* can assess the scope and duration of the impairment @S935 */ }
        }
        part organization : Organization {
            perform action a0 { doc /* retains voice recordings, system logs, and work records according to the approved retention schedule and applicable legal obligations @S782 */ }
        }
        part outgoingSupervisor : OutgoingSupervisor {
            perform action a0 { doc /* briefs the incoming supervisor on site conditions, access status, and outstanding hazards @S512 */ }
        }
        part overheating : Overheating {
            perform action a0 { doc /* threatens electrical equipment or personnel @S792 */ }
        }
        part partsSupportingScheduledMaintenance : PartsSupportingScheduledMaintenance {
            perform action a0 { doc /* supporting scheduled maintenance @S697 */ }
            perform action a1 { doc /* receive priority @S697 */ }
        }
        part passengers : Passengers {
            perform action a0 { doc /* distribute themselves and their equipment @S896 */ }
            perform action a1 { doc /* avoid obstructing the doors or control panel @S896 */ }
        }
        part people : People {
            perform action a0 { doc /* entering @S502 */ }
            perform action a1 { doc /* leaving the site @S502 */ }
        }
        part peopleResponsibleForOffshoreWork : PeopleResponsibleForOffshoreWork;
        part performanceDefinitions : PerformanceDefinitions {
            perform action a0 { doc /* identify the source data, calculation method, reporting interval, and accountable owner for each measure @S913 */ }
        }
        part permit : Permit {
            exhibit state modes {
                state s0 { doc /* active @S329 */ }
            }
        }
        part permitControls : PermitControls {
            perform action a0 { doc /* coordinate approved work scope, electrical isolation, field execution, and return to service @S318 */ }
            perform action a1 { doc /* without treating authorization as proof of a safe electrical state @S318 */ }
        }
        part permitReviewers : PermitReviewers;
        part permits : Permits {
            exhibit state modes {
                state s0 { doc /* ready @S525 */ }
            }
        }
        part person : Person {
            perform action a0 { doc /* changes duties @S425 */ }
            perform action a1 { doc /* leaves the operation @S425 */ }
            perform action a2 { doc /* presents the credential at the controlled entry point @S812 */ }
            perform action a3 { doc /* waits for the scanner response @S812 */ }
            perform action a4 { doc /* contact the Field Supervisor or the HSE Officer for review @S817 */ }
        }
        part personIssuingTheInstruction : PersonIssuingTheInstruction {
            perform action a0 { doc /* issuing the instruction @S772 */ }
        }
        part personMakingTheChange : PersonMakingTheChange {
            perform action a0 { doc /* making the change @S777 */ }
        }
        part personRemovingEachControl : PersonRemovingEachControl {
            perform action a0 { doc /* removing each control @S733 */ }
            perform action a1 { doc /* confirms that the associated work party is clear of the hazard area @S733 */ }
        }
        part personResponsibleForApplyingTheControl : PersonResponsibleForApplyingTheControl {
            perform action a0 { doc /* applying the control @S714 */ }
        }
        part personSLocation : PersonSLocation {
            exhibit state modes {
                state s0 { doc /* uncertain @S580 */ }
            }
        }
        part personalProtection : PersonalProtection {
            perform action a0 { doc /* is applied in accordance with the permit and local electrical safety rules @S723 */ }
        }
        part personnel : Personnel {
            perform action a0 { doc /* perform controlled work offshore @S243 */ }
            perform action a1 { doc /* confirm their identity @S393 */ }
            perform action a2 { doc /* entering controlled shore access areas @S393 */ }
            perform action a3 { doc /* report any change in destination or transfer plan to the Vessel Master as soon as practicable @S402 */ }
            perform action a4 { doc /* enter the work area @S405 */ }
            perform action a5 { doc /* report their arrival and departure at each active work location using the approved site process @S406 */ }
            perform action a6 { doc /* using the approved site process @S406 */ }
            perform action a7 { doc /* disembark at shore @S411 */ }
            perform action a8 { doc /* report suspected compromise, lost credentials, and unexplained equipment behavior promptly through the established operations channel @S431 */ }
            perform action a9 { doc /* approach the rotor @S451 */ }
            perform action a10 { doc /* leave the work area @S457 */ }
            perform action a11 { doc /* board a vessel @S482 */ }
            perform action a12 { doc /* use the North Access Scanner or South Access Scanner at the designated entry point @S501 */ }
            perform action a13 { doc /* have returned to a safe location @S648 */ }
            perform action a14 { doc /* enter a restricted zone @S649 */ }
            perform action a15 { doc /* use the approved fallback method @S771 */ }
            perform action a16 { doc /* report the outage as soon as practicable @S771 */ }
            perform action a17 { doc /* investigate a fire alarm @S802 */ }
            perform action a18 { doc /* complete post-event checks @S802 */ }
            perform action a19 { doc /* follow the approved contingency process rather than bypassing the gate @S828 */ }
            perform action a20 { doc /* bypassing the gate @S828 */ }
            perform action a21 { doc /* arriving through the south-side access point @S836 */ }
            perform action a22 { doc /* must not hold the barrier open for another entrant @S847 */ }
            perform action a23 { doc /* use an approved alternative entry process rather than an uncontrolled bypass @S856 */ }
            perform action a24 { doc /* boarding @S873 */ }
            perform action a25 { doc /* entering the route @S874 */ }
            perform action a26 { doc /* leaving the route @S874 */ }
            perform action a27 { doc /* do not attempt to open doors or climb out of a stopped car without direction from the response team @S903 */ }
            perform action a28 { doc /* open doors @S903 */ }
            perform action a29 { doc /* climb out of a stopped car @S903 */ }
            exhibit state modes {
                state s0 { doc /* ready @S525 */ }
            }
        }
        part personnelAffectedByARevision : PersonnelAffectedByARevision {
            perform action a0 { doc /* receive appropriate communication or training @S981 */ }
        }
        part personnelMovements : PersonnelMovements {
            perform action a0 { doc /* do not resume until the Marine Coordinator confirms that the count is reconciled or an authorized response is in place @S585 */ }
        }
        part personnelTrackingConsole : PersonnelTrackingConsole {
            perform action a0 { doc /* helps the organization maintain an accurate view of personnel assigned to offshore activities @S094 */ }
            perform action a1 { doc /* maintains the offshore personnel roster and expected return times @S234 */ }
            perform action a2 { doc /* supports confirmation that personnel assigned to the task are accounted for at the work location @S332 */ }
            perform action a3 { doc /* maintains the current accountability status for personnel assigned to offshore work @S392 */ }
            perform action a4 { doc /* maintains the operational count for active marine movements @S571 */ }
            perform action a5 { doc /* update a verified personnel total @S573 */ }
            perform action a6 { doc /* supports personnel accounting @S619 */ }
            perform action a7 { doc /* supports confirmation that all assigned personnel have returned to a safe location @S648 */ }
            perform action a8 { doc /* supports accountability checks for personnel assigned to the affected work area @S805 */ }
            perform action a9 { doc /* maintain an accurate record of personnel entering and leaving the route @S874 */ }
        }
        part personsStillUnaccountedFor : PersonsStillUnaccountedFor;
        part physicalBoundary : PhysicalBoundary {
            perform action a0 { doc /* begins at the turbine structures @S003 */ }
            perform action a1 { doc /* includes the array of turbines and the Offshore Substation @S003 */ }
        }
        part pitchSystem : PitchSystem {
            perform action a0 { doc /* changes blade angle in response to turbine control commands and local protection logic @S130 */ }
            perform action a1 { doc /* adjusts blade angle within its operating envelope @S546 */ }
            perform action a2 { doc /* does not override local protection limits @S546 */ }
            perform action a3 { doc /* retain its approved control behavior @S601 */ }
            perform action a4 { doc /* moves the blades to the defined safe position @S790 */ }
        }
        part plannedCrewAssignments : PlannedCrewAssignments {
            perform action a0 { doc /* match the approved work schedule @S396 */ }
        }
        part plannedOutage : PlannedOutage {
            perform action a0 { doc /* could restrict power transfer @S745 */ }
        }
        part plannedRestorationChecks : PlannedRestorationChecks {
            perform action a0 { doc /* have completed @S532 */ }
        }
        part plannedVesselMovements : PlannedVesselMovements {
            perform action a0 { doc /* account for reduced speed, increased separation, and the possibility of returning to a safe holding area @S681 */ }
        }
        part plannedWork : PlannedWork {
            perform action a0 { doc /* can proceed within the lift capacity and operating limits @S872 */ }
        }
        part planners : Planners {
            perform action a0 { doc /* assess whether cable condition warrants inspection or corrective intervention @S252 */ }
        }
        part portAgent : PortAgent {
            perform action a0 { doc /* supports shore-side arrangements for vessel calls, crew access, and staged cargo @S093 */ }
            perform action a1 { doc /* coordinates port services @S240 */ }
            perform action a2 { doc /* confirms that planned departures can be supported @S240 */ }
            perform action a3 { doc /* issues the Berth Slot Confirmation for the planned work period @S324 */ }
        }
        part portAndBerthCoordination : PortAndBerthCoordination {
            perform action a0 { doc /* aligns vessel access with the readiness of offshore work, people, equipment, and permits @S465 */ }
        }
        part portConditions : PortConditions {
            perform action a0 { doc /* can delay loading @S471 */ }
            perform action a1 { doc /* restrict vessel movement @S471 */ }
        }
        part portSupport : PortSupport;
        part positionIntegrityChecks : PositionIntegrityChecks {
            perform action a0 { doc /* fail @S105 */ }
        }
        part privilegedSessions : PrivilegedSessions {
            perform action a0 { doc /* are time limited @S116 */ }
            perform action a1 { doc /* logged @S116 */ }
            perform action a2 { doc /* reviewed against approved maintenance activity @S116 */ }
        }
        part productionLostDuringDowntime : ProductionLostDuringDowntime;
        part proposedControls : ProposedControls {
            perform action a0 { doc /* match the task scope and site conditions @S266 */ }
        }
        part proposedReliabilityImprovements : ProposedReliabilityImprovements {
            perform action a0 { doc /* deliver the intended result @S932 */ }
            perform action a1 { doc /* do not introduce adverse effects @S932 */ }
        }
        part proposedSequence : ProposedSequence {
            perform action a0 { doc /* supports the approved work @S516 */ }
            exhibit state modes {
                state s0 { doc /* paused @S535 */ }
            }
        }
        part proposedWorkaround : ProposedWorkaround {
            perform action a0 { doc /* changes established access, isolation, or personnel-control arrangements @S949 */ }
        }
        part protectedOperationalNetworks : ProtectedOperationalNetworks {
            perform action a0 { doc /* support safe farm operations @S100 */ }
        }
        part protectionActions : ProtectionActions {
            perform action a0 { doc /* have completed @S799 */ }
        }
        part protectionCoordination : ProtectionCoordination {
            perform action a0 { doc /* prevents a fault on the external system from causing unnecessary disconnection of healthy farm equipment @S208 */ }
        }
        part protectiveDevices : ProtectiveDevices {
            perform action a0 { doc /* show no active fault indication @S867 */ }
            perform action a1 { doc /* must not be bypassed @S894 */ }
        }
        part protectiveFunctions : ProtectiveFunctions;
        part qualifiedPersonnel : QualifiedPersonnel {
            perform action a0 { doc /* supervise the work @S607 */ }
        }
        part qualifiedTechnician : QualifiedTechnician {
            perform action a0 { doc /* checks the device at the point of isolation @S719 */ }
        }
        part rain : Rain {
            perform action a0 { doc /* move through the area @S662 */ }
        }
        part receiver : Receiver {
            perform action a0 { doc /* repeats critical details @S773 */ }
        }
        part record : Record {
            perform action a0 { doc /* supports routine review of access activity and investigation of anomalies @S844 */ }
        }
        part recoveredComponents : RecoveredComponents {
            perform action a0 { doc /* support repair planning @S656 */ }
        }
        part recovery : Recovery {
            perform action a0 { doc /* begins @S436 */ }
            perform action a1 { doc /* begins only after the initiating condition has been corrected or bounded and the responsible operator has confirmed that the equipment is stable @S952 */ }
        }
        part recoveryTask : RecoveryTask {
            perform action a0 { doc /* does not conflict with other offshore work @S639 */ }
        }
        part releasedRevisions : ReleasedRevisions {
            perform action a0 { doc /* identify the change, rationale, approval, effective date, and superseded baseline @S980 */ }
        }
        part reliabilityReviews : ReliabilityReviews {
            perform action a0 { doc /* consider failure frequency, failure duration, recurrence, and the operational consequences of each event @S921 */ }
        }
        part remoteAdministrativeFunctions : RemoteAdministrativeFunctions {
            exhibit state modes {
                state s0 { doc /* restricted state @S118 */ }
            }
        }
        part remoteEvidence : RemoteEvidence {
            perform action a0 { doc /* cannot resolve a material uncertainty @S310 */ }
        }
        part remoteIndications : RemoteIndications {
            perform action a0 { doc /* agree with the approved switching state @S718 */ }
        }
        part remoteObservations : RemoteObservations {
            perform action a0 { doc /* supplement field assessment @S147 */ }
            perform action a1 { doc /* do not replace required physical inspections @S147 */ }
        }
        part remoteOperation : RemoteOperation {
            perform action a0 { doc /* begins @S138 */ }
        }
        part remoteSessions : RemoteSessions {
            perform action a0 { doc /* require approved connection paths, strong authentication, and active supervision when they can affect live operations @S427 */ }
            perform action a1 { doc /* can affect live operations @S427 */ }
        }
        part remoteSurveys : RemoteSurveys {
            perform action a0 { doc /* use the Blade Inspection Drone @S444 */ }
            perform action a1 { doc /* capture repeatable views of blade surfaces @S444 */ }
        }
        part repairPlans : RepairPlans {
            perform action a0 { doc /* identify surface preparation, material application, cure requirements, inspection hold points, and acceptance criteria @S462 */ }
        }
        part replenishmentRequests : ReplenishmentRequests {
            perform action a0 { doc /* include the required quantity, need date, delivery location, and applicable handling requirements @S699 */ }
        }
        part reportedEvents : ReportedEvents;
        part reportedStateChange : ReportedStateChange {
            perform action a0 { doc /* matches the approved sequence @S534 */ }
        }
        part requester : Requester {
            perform action a0 { doc /* identifies the equipment affected @S152 */ }
            perform action a1 { doc /* describes the intended work in terms that can be checked against operating constraints @S152 */ }
        }
        part requiredQuantity : RequiredQuantity;
        part rescueCoordinator : RescueCoordinator {
            perform action a0 { doc /* maintains the response arrangements for incidents involving vessels or personnel @S244 */ }
            perform action a1 { doc /* leads rescue planning @S614 */ }
            perform action a2 { doc /* coordinates requests for external assistance @S614 */ }
            perform action a3 { doc /* revises the response plan @S634 */ }
            perform action a4 { doc /* establishes the recovery objective @S637 */ }
            perform action a5 { doc /* confirms who has authority to suspend the operation @S637 */ }
            perform action a6 { doc /* uses the load sheet @S646 */ }
            perform action a7 { doc /* confirm that recovery baskets are secured and their contents are accounted for before transfer @S646 */ }
        }
        part reservations : Reservations {
            perform action a0 { doc /* prevent the same available quantity from being assigned to multiple work packages @S693 */ }
        }
        part resourceAvailability : ResourceAvailability {
            perform action a0 { doc /* change @S224 */ }
        }
        part responders : Responders {
            perform action a0 { doc /* use alongside direct reports from personnel on site @S629 */ }
        }
        part response : Response {
            perform action a0 { doc /* prioritizes safe operation @S306 */ }
            perform action a1 { doc /* restricts work until the condition is understood @S306 */ }
            perform action a2 { doc /* requires additional deck space or lifting capability @S645 */ }
        }
        part responsibleAuthority : ResponsibleAuthority {
            perform action a0 { doc /* confirms that the equipment and work area are safe for subsequent activity @S657 */ }
            perform action a1 { doc /* approves restoration @S732 */ }
        }
        part responsibleControlPersonnel : ResponsibleControlPersonnel;
        part responsibleManager : ResponsibleManager {
            perform action a0 { doc /* reviews record completeness after significant events @S784 */ }
            perform action a1 { doc /* assigns correction or follow-up actions where evidence is missing @S784 */ }
        }
        part responsibleOperationalAuthority : ResponsibleOperationalAuthority {
            perform action a0 { doc /* confirms that conditions permit work to proceed @S500 */ }
        }
        part responsibleOperationsStaff : ResponsibleOperationsStaff;
        part responsibleOperator : ResponsibleOperator {
            perform action a0 { doc /* has confirmed that the equipment is stable @S952 */ }
        }
        part responsibleOrganization : ResponsibleOrganization;
        part responsiblePersonnel : ResponsiblePersonnel {
            perform action a0 { doc /* confirm that operations can resume safely @S086 */ }
        }
        part responsibleSupervisor : ResponsibleSupervisor {
            perform action a0 { doc /* keeps a local record @S413 */ }
            perform action a1 { doc /* reports it when service is restored @S413 */ }
        }
        part responsibleTeam : ResponsibleTeam {
            perform action a0 { doc /* reports completion status and outstanding issues @S170 */ }
            perform action a1 { doc /* verifies turbine isolation, rotor restraint, access arrangements, and rescue provisions @S450 */ }
        }
        part review : Review {
            perform action a0 { doc /* identifies hazards, required controls, access arrangements, and any operating coordination needed before work can proceed @S156 */ }
        }
        part reviewTeams : ReviewTeams {
            perform action a0 { doc /* distinguish equipment faults from external causes such as access limitations, weather conditions, and grid restrictions @S922 */ }
        }
        part reviewers : Reviewers {
            perform action a0 { doc /* assess safety effects, cybersecurity risks, interfaces, and the impact on ongoing maintenance activities @S596 */ }
        }
        part reviews : Reviews {
            perform action a0 { doc /* distinguish verified evidence from assumptions, unresolved actions, and proposals that have not yet been approved @S974 */ }
        }
        part riskAssessments : RiskAssessments;
        part rotorBrakeUnit : RotorBrakeUnit {
            perform action a0 { doc /* applies braking only in accordance with the turbine protection sequence and operating limits @S791 */ }
        }
        part route : Route {
            perform action a0 { doc /* does not provide an alternate way to bypass work authorization or site restrictions @S842 */ }
            exhibit state modes {
                state s0 { doc /* in service @S853 */ }
                state s1 { doc /* out of service @S855 */ }
            }
        }
        part routineChecks : RoutineChecks {
            perform action a0 { doc /* confirm that credential readers, indicators, and barrier controls operate as intended @S854 */ }
        }
        part routineRounds : RoutineRounds {
            perform action a0 { doc /* cover room temperature, ventilation, water ingress, lighting, access control, and visible signs of damage @S344 */ }
        }
        part rule : Rule {
            perform action a0 { doc /* determined the outcome @S822 */ }
        }
        part sCADAEngineer : SCADAEngineer {
            perform action a0 { doc /* maintains the configuration and technical integrity of supervisory interfaces @S062 */ }
            perform action a1 { doc /* use individually assigned accounts rather than shared credentials for interactive work @S423 */ }
            perform action a2 { doc /* validates restored configurations and communications @S437 */ }
            perform action a3 { doc /* investigates telemetry gaps or inconsistent measurements @S558 */ }
            perform action a4 { doc /* uses the Firmware Hash Attestation to verify the approved image before loading a release @S593 */ }
            perform action a5 { doc /* verify the approved image @S593 */ }
            perform action a6 { doc /* loading a release @S593 */ }
            perform action a7 { doc /* investigates missing or inconsistent indications @S946 */ }
            perform action a8 { doc /* verifies that status, alarms, and command feedback are consistent across the available control views @S954 */ }
            perform action a9 { doc /* reviews monitoring and control assumptions that affect operational decisions @S968 */ }
        }
        part sCADAGateway : SCADAGateway {
            perform action a0 { doc /* provides a controlled boundary for supervisory data exchange between offshore assets and shore-based operations @S052 */ }
            perform action a1 { doc /* mediates supervisory exchanges @S059 */ }
            perform action a2 { doc /* supports consistent access to operational information @S059 */ }
            perform action a3 { doc /* presents turbine status and control availability to authorized shore personnel @S133 */ }
            perform action a4 { doc /* uses the deviation notice @S159 */ }
            perform action a5 { doc /* flag work packages that may require technical review @S159 */ }
            perform action a6 { doc /* shall provide current operational status to permit reviewers when requested as part of the authorization check @S171 */ }
            perform action a7 { doc /* presents supply alarms and generator status to the Shore Control Room for remote awareness @S192 */ }
            perform action a8 { doc /* provides relay status and interface measurements to the farm monitoring environment @S211 */ }
            perform action a9 { doc /* produces the Session Revocation Receipt when an authenticated control session is terminated @S212 */ }
            perform action a10 { doc /* forwards time-stamped observations to the Shore Control Room for review against configured operating limits @S295 */ }
            perform action a11 { doc /* provides the operational measurements used to track delivered power and instruction response @S369 */ }
            perform action a12 { doc /* records security-relevant access and control events for review @S417 */ }
            perform action a13 { doc /* provides operating data @S447 */ }
            perform action a14 { doc /* presents current generation, export, and equipment status to the operations team @S540 */ }
            perform action a15 { doc /* carries operational data to the Shore Control Room @S767 */ }
            perform action a16 { doc /* preserves source timestamps where available @S767 */ }
            perform action a17 { doc /* supports alarm visibility at the shore operating position @S800 */ }
            perform action a18 { doc /* replacing local emergency controls @S800 */ }
            perform action a19 { doc /* provides operational records used to assess turbine availability and production trends @S914 */ }
            perform action a20 { doc /* preserves available status and alarm information @S946 */ }
        }
        part safetyFunctions : SafetyFunctions {
            perform action a0 { doc /* take priority over energy production, maintenance throughput, and schedule recovery in every degraded mode @S936 */ }
        }
        part safetyPerformanceMeasures : SafetyPerformanceMeasures {
            perform action a0 { doc /* continue to reflect actual operating experience @S933 */ }
        }
        part scheduledExercising : ScheduledExercising {
            perform action a0 { doc /* confirms that the Emergency Generator can start, accept its expected load, and operate for the required test duration @S186 */ }
        }
        part scheduledSurveillance : ScheduledSurveillance {
            perform action a0 { doc /* indicate that blade condition requires review @S440 */ }
        }
        part seaConditions : SeaConditions {
            perform action a0 { doc /* exceed approved limits @S620 */ }
        }
        part seaOrWeatherConditions : SeaOrWeatherConditions {
            perform action a0 { doc /* make transfer unsafe @S499 */ }
        }
        part securityEvents : SecurityEvents {
            perform action a0 { doc /* are retained in protected logs for investigation and audit @S119 */ }
        }
        part sender : Sender {
            perform action a0 { doc /* confirms that the read-back is accurate @S773 */ }
        }
        part sensorHealth : SensorHealth {
            perform action a0 { doc /* are checked as part of routine monitoring @S109 */ }
        }
        part sensors : Sensors {
            perform action a0 { doc /* are selected @S103 */ }
            perform action a1 { doc /* mounted @S103 */ }
            perform action a2 { doc /* limit exposure to spray, icing, vibration, and corrosion @S103 */ }
        }
        part serialControlledParts : SerialControlledParts {
            perform action a0 { doc /* retain traceability from receipt through installation, repair, return, or disposal @S692 */ }
        }
        part serviceOperationsVessel : ServiceOperationsVessel {
            perform action a0 { doc /* may support offshore work @S045 */ }
            perform action a1 { doc /* provides a platform for work that needs longer offshore presence or broader onboard support @S089 */ }
            perform action a2 { doc /* provides a stable offshore base when the work plan requires extended support @S228 */ }
            perform action a3 { doc /* may provide a more stable work platform @S281 */ }
            perform action a4 { doc /* prepares the Recovery Basket Load Sheet for the planned work activity @S461 */ }
            perform action a5 { doc /* may provide accommodation, medical support, and a stable platform @S622 */ }
            perform action a6 { doc /* provides a stable working platform when the response requires additional deck space or lifting capability @S645 */ }
            perform action a7 { doc /* may maintain a safe stand-off @S680 */ }
        }
        part shiftHandover : ShiftHandover {
            perform action a0 { doc /* records outstanding isolations, affected equipment, and any restrictions that remain in force @S730 */ }
        }
        part shiftRecords : ShiftRecords {
            perform action a0 { doc /* capture inspections, alarms, tests, switching actions, defects, and handover items @S365 */ }
            perform action a1 { doc /* capture dispatch instructions, constraint decisions, measured response, and unresolved follow-up actions @S389 */ }
        }
        part shoreControlRoom : ShoreControlRoom {
            perform action a0 { doc /* continuous monitoring @S013 */ }
            perform action a1 { doc /* dispatch coordination @S013 */ }
            perform action a2 { doc /* provides a shore-based operating location for authorized personnel @S040 */ }
            perform action a3 { doc /* provides a shared operational context for personnel responsible for offshore assets @S064 */ }
            perform action a4 { doc /* maintains operational oversight @S097 */ }
            perform action a5 { doc /* provides a point of coordination for shore-based personnel @S097 */ }
            perform action a6 { doc /* maintains operational oversight @S099 */ }
            perform action a7 { doc /* provides a point of coordination for shore-based personnel @S099 */ }
            perform action a8 { doc /* provides a staffed location for supervisory control and operational review @S134 */ }
            perform action a9 { doc /* coordinates operational notices and control-room decisions affecting the farm interface @S214 */ }
            perform action a10 { doc /* maintains an overview of active marine operations and operational restrictions @S238 */ }
            perform action a11 { doc /* escalates an alert when its severity exceeds the operating threshold or when the evidence indicates a developing hazard @S303 */ }
            perform action a12 { doc /* retains the decision record, supporting observations, and response outcome for operational review @S317 */ }
            perform action a13 { doc /* retains the permit status, isolation history, test results, and restoration decision for operational review @S339 */ }
            perform action a14 { doc /* receives concise status updates, including operating limitations and the expected time of the next review @S364 */ }
            perform action a15 { doc /* maintains the current dispatch target, ramp rate, and next review time in the shift record @S371 */ }
            perform action a16 { doc /* uses the tap snapshot @S374 */ }
            perform action a17 { doc /* check the recorded transformer position during export reviews @S374 */ }
            perform action a18 { doc /* maintains the last validated operating limit while seeking clarification through the approved channel @S386 */ }
            perform action a19 { doc /* seeking clarification through the approved channel @S386 */ }
            perform action a20 { doc /* maintains an operational view of affected systems @S420 */ }
            perform action a21 { doc /* coordinates immediate protective actions @S420 */ }
            perform action a22 { doc /* monitors turbine status @S448 */ }
            perform action a23 { doc /* records any operating restrictions required during the remote survey @S448 */ }
            perform action a24 { doc /* sends the Switching Window Acknowledgment @S531 */ }
            perform action a25 { doc /* is entered in the operating log @S531 */ }
            perform action a26 { doc /* confirms that monitoring and operator procedures remain suitable for the revised configuration @S606 */ }
            perform action a27 { doc /* maintains the incident log @S613 */ }
            perform action a28 { doc /* provides a single operational point of contact for offshore teams @S613 */ }
            perform action a29 { doc /* maintains awareness of the decision and the operational restrictions associated with the assessment @S683 */ }
            perform action a30 { doc /* assesses incoming alarms @S798 */ }
            perform action a31 { doc /* confirms the affected asset @S798 */ }
            perform action a32 { doc /* initiates the response appropriate to the reported severity @S798 */ }
            perform action a33 { doc /* monitors the loss of visibility @S937 */ }
            perform action a34 { doc /* applies the approved operating concept during routine operations and abnormal conditions @S963 */ }
        }
        part shorePersonnel : ShorePersonnel {
            perform action a0 { doc /* can anticipate vessel arrivals @S410 */ }
        }
        part shortage : Shortage {
            perform action a0 { doc /* threatens a work window @S702 */ }
        }
        part signs : Signs {
            perform action a0 { doc /* identify the permitted approach @S852 */ }
            perform action a1 { doc /* direct personnel to the controlled entry point @S852 */ }
        }
        part siteMeasurements : SiteMeasurements {
            perform action a0 { doc /* help assess whether a planned response remains feasible @S625 */ }
        }
        part siteSpecificDetectionAndTripSettings : SiteSpecificDetectionAndTripSettings {
            perform action a0 { doc /* account for its design and operating conditions @S795 */ }
        }
        part softwareChanges : SoftwareChanges {
            perform action a0 { doc /* affecting protection functions or control behavior @S597 */ }
            perform action a1 { doc /* receive additional engineering scrutiny @S597 */ }
            perform action a2 { doc /* affecting the Offshore Substation @S603 */ }
        }
        part southAccessScanner : SouthAccessScanner {
            perform action a0 { doc /* records authorized entry at the south access point @S236 */ }
            perform action a1 { doc /* records identity checks at the south shore access point @S395 */ }
            perform action a2 { doc /* records personnel access events at the south access point @S570 */ }
            perform action a3 { doc /* serves the designated southern entry route to the offshore wind farm @S835 */ }
            perform action a4 { doc /* applies the same identity verification standard used at other controlled entry points @S838 */ }
        }
        part sparesHub : SparesHub {
            perform action a0 { doc /* provides a separate view of stock held for regional replenishment and emergency support @S689 */ }
        }
        part spray : Spray {
            perform action a0 { doc /* move through the area @S662 */ }
        }
        part staleOrImplausibleValue : StaleOrImplausibleValue {
            exhibit state modes {
                state s0 { doc /* unverified @S300 */ }
            }
        }
        part startTime : StartTime;
        part stationServiceTransformers : StationServiceTransformers {
            perform action a0 { doc /* supply the facility's auxiliary electrical loads from the medium-voltage collection system @S173 */ }
        }
        part statusIndications : StatusIndications {
            perform action a0 { doc /* support assessment of the normal supply and its protective state @S190 */ }
        }
        part stockVisibility : StockVisibility {
            perform action a0 { doc /* includes quantities on hand, items reserved for approved work, and quantities already committed to transfer @S688 */ }
        }
        part storekeeper : Storekeeper {
            perform action a0 { doc /* checks requested materials against available stock @S092 */ }
            perform action a1 { doc /* coordinates replenishment with the Spares Hub @S092 */ }
            perform action a2 { doc /* prepares requested equipment for dispatch in accordance with the approved work plan @S242 */ }
            perform action a3 { doc /* uses the exception slip to validate an unavailable part @S262 */ }
            perform action a4 { doc /* validate an unavailable part @S262 */ }
            perform action a5 { doc /* checks repair materials and tooling against the approved repair method @S460 */ }
            perform action a6 { doc /* checks that critical spares are available and that packaging is suitable for marine transport @S479 */ }
            perform action a7 { doc /* reconciles physical counts with recorded balances @S690 */ }
            perform action a8 { doc /* records adjustments with a reason and timestamp @S690 */ }
            perform action a9 { doc /* records unavailable quantities and the expected date of the next supply @S703 */ }
            perform action a10 { doc /* presenting them as available stock @S703 */ }
            perform action a11 { doc /* confirms that equipment intended for the lift is ready and properly identified for the work party @S876 */ }
        }
        part substationOperator : SubstationOperator {
            perform action a0 { doc /* confirms that switching actions affecting the export path are within the authorized work scope @S216 */ }
            perform action a1 { doc /* confirms local operating constraints @S268 */ }
            perform action a2 { doc /* applies authorized switching actions @S326 */ }
            perform action a3 { doc /* records the resulting equipment state @S326 */ }
            perform action a4 { doc /* removes isolations only under the approved switching process @S337 */ }
            perform action a5 { doc /* records each restoration action @S337 */ }
            perform action a6 { doc /* maintains the Offshore Substation within approved operating limits @S342 */ }
            perform action a7 { doc /* follows current switching instructions @S342 */ }
            perform action a8 { doc /* reviews alarms, active restrictions, equipment status, and handover notes @S343 */ }
            perform action a9 { doc /* checks Main Transformer temperatures, cooling equipment, oil indications, and abnormal noise against established limits @S345 */ }
            perform action a10 { doc /* verifies that personnel access records are consistent with the planned work and current site occupancy @S351 */ }
            perform action a11 { doc /* confirms fuel level, starting battery condition, ventilation, and readiness of the Emergency Generator for loss of normal supply @S354 */ }
            perform action a12 { doc /* coordinates switching activity that could alter the available export configuration @S382 */ }
            perform action a13 { doc /* confirms that switching conditions affecting the worksite are understood by the relevant personnel @S497 */ }
            perform action a14 { doc /* verifies equipment status and switching points at the Offshore Substation @S517 */ }
            perform action a15 { doc /* accepts the instructions @S530 */ }
            perform action a16 { doc /* checking the equipment state @S530 */ }
            perform action a17 { doc /* confirming authorization with the Control Engineer @S530 */ }
            perform action a18 { doc /* uses the test trace @S532 */ }
            perform action a19 { doc /* verify that the planned restoration checks have completed @S532 */ }
            perform action a20 { doc /* requesting the next switching step @S532 */ }
            perform action a21 { doc /* confirms that export equipment remains within its approved operating range @S549 */ }
            perform action a22 { doc /* reports any substation limitation that could require a lower export target or local equipment action @S559 */ }
            perform action a23 { doc /* reviews the switching sequence @S741 */ }
            perform action a24 { doc /* confirms that each step can be performed within the available interval @S741 */ }
            perform action a25 { doc /* does not begin switching until the window is active and operational authority has been confirmed @S753 */ }
            perform action a26 { doc /* reviews responsibilities and coordination arrangements for substation activities @S971 */ }
        }
        part substitutions : Substitutions {
            perform action a0 { doc /* require engineering acceptance and confirmation that the alternative meets the required interface and operating limits @S704 */ }
        }
        part successfulResponseAtOneLevel : SuccessfulResponseAtOneLevel {
            perform action a0 { doc /* does not conceal a remaining restriction elsewhere @S956 */ }
        }
        part supervisoryFaults : SupervisoryFaults {
            perform action a0 { doc /* require assessment @S796 */ }
            perform action a1 { doc /* do not indicate an active fire @S796 */ }
        }
        part supportingMarineAndShoreFacilities : SupportingMarineAndShoreFacilities;
        part switchingActions : SwitchingActions {
            perform action a0 { doc /* affecting the export path @S216 */ }
        }
        part switchingActivity : SwitchingActivity {
            perform action a0 { doc /* could alter the available export configuration @S382 */ }
        }
        part switchingConditions : SwitchingConditions {
            perform action a0 { doc /* affecting the worksite @S497 */ }
        }
        part switchingOperator : SwitchingOperator {
            perform action a0 { doc /* performs each authorized action @S533 */ }
            perform action a1 { doc /* reports completion @S533 */ }
        }
        part systemPart : System {
            perform action a0 { doc /* raises an alarm @S183 */ }
            perform action a1 { doc /* maintains any available uninterruptible control power @S183 */ }
            perform action a2 { doc /* retains successful and unsuccessful attempts under the site's access record retention policy @S824 */ }
            perform action a3 { doc /* measures operational performance against approved service objectives and documented fleet baselines @S908 */ }
            perform action a4 { doc /* records the affected function, the detected condition, and the time of transition @S935 */ }
            perform action a5 { doc /* retains the event record and recovery decisions for review, trend analysis, and improvement of operating procedures @S957 */ }
        }
        part systemArchitecture : SystemArchitecture {
            perform action a0 { doc /* separates offshore equipment, operational services, and shore-based decision functions @S051 */ }
            perform action a1 { doc /* preserving defined interfaces between them @S051 */ }
        }
        part task : Task {
            perform action a0 { doc /* presents a material personnel or environmental risk @S157 */ }
            perform action a1 { doc /* require a change to substation configuration @S737 */ }
        }
        part taskSelection : TaskSelection {
            perform action a0 { doc /* favors work that can be performed safely under the assessed conditions without relying on precise visual identification or close-range observation @S671 */ }
        }
        part tasks : Tasks {
            perform action a0 { doc /* can safely wait until normal access and support are available @S948 */ }
        }
        part team : Team {
            perform action a0 { doc /* checking forecast trends and current sea state @S271 */ }
            perform action a1 { doc /* also checks current observations and the task-specific limits @S280 */ }
            perform action a2 { doc /* considers forecast uncertainty @S289 */ }
            perform action a3 { doc /* deciding whether to commit crews, fuel, and vessel time to a remote work site @S289 */ }
            perform action a4 { doc /* commit crews, fuel, and vessel time to a remote work site @S289 */ }
            perform action a5 { doc /* relies on them for control decisions @S558 */ }
            perform action a6 { doc /* demonstrating that the transfer or task can be completed within safe limits @S684 */ }
        }
        part technicalReviewers : TechnicalReviewers {
            perform action a0 { doc /* confirm that the work scope is compatible with equipment condition and the planned maintenance method @S158 */ }
            perform action a1 { doc /* distinguish environmental effects from equipment deterioration @S309 */ }
        }
        part technicalTeams : TechnicalTeams {
            perform action a0 { doc /* isolate only the affected connection or service @S433 */ }
            perform action a1 { doc /* review causes, response effectiveness, and corrective actions with operations management @S439 */ }
        }
        part technicians : Technicians {
            perform action a0 { doc /* begin affected tasks @S429 */ }
        }
        part temporaryPersonnel : TemporaryPersonnel {
            perform action a0 { doc /* follow the same identity checks as other entrants @S849 */ }
        }
        part testRequirements : TestRequirements {
            perform action a0 { doc /* fit the approved duration @S750 */ }
        }
        part timeSynchronization : TimeSynchronization {
            perform action a0 { doc /* are checked as part of routine monitoring @S109 */ }
        }
        part timelyClosureOfCorrectiveActions : TimelyClosureOfCorrectiveActions;
        part tools : Tools;
        part transaction : Transaction {
            perform action a0 { doc /* records the credential identifier, decision time, access point, and decision outcome @S821 */ }
            perform action a1 { doc /* records the authorization version and the rule that determined the outcome @S822 */ }
        }
        part transfer : Transfer {
            perform action a0 { doc /* begins @S565 */ }
        }
        part transferArrangement : TransferArrangement {
            perform action a0 { doc /* prevents the normal and emergency sources from being connected in parallel unless an approved synchronizing function is provided @S179 */ }
        }
        part transferArrangements : TransferArrangements {
            perform action a0 { doc /* exceed approved limits @S620 */ }
        }
        part transfers : Transfers {
            perform action a0 { doc /* meet the approved operating limits @S227 */ }
        }
        part turbine : Turbine {
            exhibit state modes {
                state s0 { doc /* Turbine Lockout @S940 */ }
                state s1 { doc /* approved operating state @S444 */ }
            }
        }
        part turbineAlarms : TurbineAlarms {
            perform action a0 { doc /* indicate that blade condition requires review @S440 */ }
        }
        part turbineController : TurbineController {
            perform action a0 { doc /* performs local turbine control functions @S060 */ }
            perform action a1 { doc /* produces the Pitch Deviation Notice @S061 */ }
            perform action a2 { doc /* adjusts turbine output within approved operating limits @S127 */ }
            perform action a3 { doc /* blocks commands that conflict with active protection conditions @S127 */ }
            perform action a4 { doc /* executes authorized control actions @S129 */ }
            perform action a5 { doc /* reports its operating state through established control interfaces @S129 */ }
            perform action a6 { doc /* enters its configured safe operating mode when required auxiliary services are unavailable @S191 */ }
            perform action a7 { doc /* adjusts output in accordance with validated plant commands and local equipment protections @S377 */ }
            perform action a8 { doc /* applies the accepted output target @S545 */ }
            perform action a9 { doc /* retaining its protective control functions @S545 */ }
            perform action a10 { doc /* initiates the configured shutdown response @S789 */ }
            perform action a11 { doc /* retains protective control locally when the supervisory connection is unavailable @S937 */ }
            exhibit state modes {
                state s0 { doc /* configured safe operating mode @S191 */ }
            }
        }
        part turbineLockout : TurbineLockout {
            perform action a0 { doc /* remains in force until the responsible authority confirms that the equipment and work area are safe for subsequent activity @S657 */ }
            perform action a1 { doc /* prevents remote restart @S802 */ }
        }
        part turbineResponse : TurbineResponse;
        part turbineSensorBus : TurbineSensorBus {
            perform action a0 { doc /* provides operating measurements for work that depends on recent machine behavior @S251 */ }
            perform action a1 { doc /* collects operating measurements from the Turbine Controller, Pitch System, Converter Cabinet, and Nacelle Condition Monitor @S294 */ }
            perform action a2 { doc /* carries equipment status used by protective functions and operational monitoring @S788 */ }
        }
        part turbines : Turbines;
        part unplannedMaintenance : UnplannedMaintenance {
            perform action a0 { doc /* use prioritized fault assessment and controlled mobilization appropriate to the severity of the failure @S018 */ }
        }
        part urgentMessages : UrgentMessages {
            perform action a0 { doc /* identify the affected asset, the hazard or condition, the required action, and the person issuing the instruction @S772 */ }
        }
        part urgentPurchases : UrgentPurchases {
            perform action a0 { doc /* require documented authorization @S707 */ }
            perform action a1 { doc /* retain the same traceability and inspection controls as routine receipts @S707 */ }
        }
        part users : Users {
            perform action a0 { doc /* report unusual noise, vibration, door behavior, or control response immediately @S882 */ }
        }
        part validationChecks : ValidationChecks {
            perform action a0 { doc /* cover sensor range, signal freshness, timestamp alignment, and consistency with related measurements @S298 */ }
        }
        part verbalRequest : VerbalRequest {
            perform action a0 { doc /* Neither a verbal request nor a manually presented credential image overrides a scanner denial @S818 */ }
        }
        part verification : Verification {
            perform action a0 { doc /* fails @S609 */ }
        }
        part verifiedHeadcount : VerifiedHeadcount {
            perform action a0 { doc /* differs from the departure record @S390 */ }
        }
        part vessel : Vessel {
            perform action a0 { doc /* leaves port @S398 */ }
            perform action a1 { doc /* gets underway @S399 */ }
            perform action a2 { doc /* departs the work location @S582 */ }
            perform action a3 { doc /* acts on them @S763 */ }
        }
        part vesselAISReceiver : VesselAISReceiver {
            perform action a0 { doc /* produces a Position Quality Flag @S105 */ }
            perform action a1 { doc /* collects vessel position broadcasts @S139 */ }
            perform action a2 { doc /* support marine traffic awareness @S139 */ }
            perform action a3 { doc /* maintains a time-stamped view of nearby vessel movements when broadcast coverage is available @S140 */ }
            perform action a4 { doc /* provides vessel position information for review against the planned route and operating area @S288 */ }
            perform action a5 { doc /* provides vessel position information for movement monitoring @S401 */ }
        }
        part vesselMaster : VesselMaster {
            perform action a0 { doc /* retains authority for navigation, vessel safety, and decisions about whether a transfer can proceed @S079 */ }
            perform action a1 { doc /* evaluates local conditions @S085 */ }
            perform action a2 { doc /* continues to reassess them during the voyage @S085 */ }
            perform action a3 { doc /* confirms that the vessel plan can support the approved personnel and equipment transfer @S161 */ }
            perform action a4 { doc /* confirms departure readiness @S226 */ }
            perform action a5 { doc /* reports any change that could affect the passage @S226 */ }
            perform action a6 { doc /* receives the Transfer Manifest Addendum @S278 */ }
            perform action a7 { doc /* considers the approach and transfer conditions acceptable @S279 */ }
            perform action a8 { doc /* can pause or abort an approach @S284 */ }
            perform action a9 { doc /* produces the Crew Count Correction when a verified headcount differs from the departure record @S390 */ }
            perform action a10 { doc /* confirms the departure roster @S398 */ }
            perform action a11 { doc /* records crew changes that occur during transit or between offshore locations @S403 */ }
            perform action a12 { doc /* maintains an onboard count while personnel are aboard the vessel @S409 */ }
            perform action a13 { doc /* confirms practical arrival and departure estimates against the vessel's operating limits @S476 */ }
            perform action a14 { doc /* confirms that the vessel is safely positioned and that transfer conditions remain acceptable @S498 */ }
            perform action a15 { doc /* confirms that the vessel can meet the agreed timing and maintain safe operating margins @S524 */ }
            perform action a16 { doc /* can meet the agreed timing @S524 */ }
            perform action a17 { doc /* maintain safe operating margins @S524 */ }
            perform action a18 { doc /* are checked @S525 */ }
            perform action a19 { doc /* confirm that assigned personnel and permits are ready @S525 */ }
            perform action a20 { doc /* verifies the number of people physically aboard before departure @S567 */ }
            perform action a21 { doc /* maintains a safe operating position @S577 */ }
            perform action a22 { doc /* retains authority over vessel safety, navigation, and decisions to approach or withdraw from a casualty @S616 */ }
            perform action a23 { doc /* approach @S616 */ }
            perform action a24 { doc /* withdraw from a casualty @S616 */ }
            perform action a25 { doc /* may withdraw @S634 */ }
            perform action a26 { doc /* retains authority over vessel movements @S642 */ }
            perform action a27 { doc /* may decline a task that cannot be completed safely @S642 */ }
            perform action a28 { doc /* deteriorates @S659 */ }
            perform action a29 { doc /* retains authority to proceed, slow, alter course, or hold position based on actual conditions and vessel limits @S677 */ }
            perform action a30 { doc /* proceed @S677 */ }
            perform action a31 { doc /* slow @S677 */ }
            perform action a32 { doc /* alter course @S677 */ }
            perform action a33 { doc /* hold position @S677 */ }
            perform action a34 { doc /* reassess the route and the suitability of continuing toward the work site @S682 */ }
            perform action a35 { doc /* confirms safety-critical instructions using the agreed read-back procedure @S763 */ }
            perform action a36 { doc /* using the agreed read-back procedure @S763 */ }
            perform action a37 { doc /* maintains a safe position and readiness to support personnel recovery @S807 */ }
            perform action a38 { doc /* support personnel recovery @S807 */ }
            perform action a39 { doc /* confirm that personnel and vessels can remain safely accounted for during an extended interruption @S944 */ }
        }
        part vesselOperatingProcedures : VesselOperatingProcedures;
        part vesselPersonnel : VesselPersonnel;
        part vesselPlan : VesselPlan {
            perform action a0 { doc /* can support the approved personnel and equipment transfer @S161 */ }
        }
        part vesselRecoverySupport : VesselRecoverySupport {
            perform action a0 { doc /* coordinates people, vessels, and handling equipment @S636 */ }
        }
        part vessels : Vessels;
        part visibility : Visibility {
            perform action a0 { doc /* exceed approved limits @S620 */ }
            perform action a1 { doc /* can vary across the wind farm @S662 */ }
            perform action a2 { doc /* could prevent reliable control or interpretation of inspection imagery @S673 */ }
        }
        part visibilityAssessments : VisibilityAssessments {
            perform action a0 { doc /* can leave uncertainty @S663 */ }
        }
        part visitors : Visitors {
            perform action a0 { doc /* remain under escort @S508 */ }
            perform action a1 { doc /* follow the same identity checks as other entrants @S849 */ }
        }
        part warehouseSystem : WarehouseSystem {
            perform action a0 { doc /* records stock status @S091 */ }
            perform action a1 { doc /* supports preparation of equipment and consumables for scheduled work @S091 */ }
            perform action a2 { doc /* produces a Backorder Exception Slip when a requested component cannot be supplied by the planned issue date @S163 */ }
            perform action a3 { doc /* records stock movements @S241 */ }
            perform action a4 { doc /* makes current inventory information available for logistics planning @S241 */ }
            perform action a5 { doc /* supports cargo preparation @S478 */ }
            perform action a6 { doc /* arrange receiving space @S655 */ }
            perform action a7 { doc /* preserve traceability for equipment returned ashore @S655 */ }
            perform action a8 { doc /* maintains the authoritative item catalogue, stock balances, and storage locations @S687 */ }
            perform action a9 { doc /* uses recurring failure and repair information @S928 */ }
            perform action a10 { doc /* inform review of critical spares and replenishment assumptions @S928 */ }
        }
        part weatherAnalyst : WeatherAnalyst {
            perform action a0 { doc /* reviews available forecasts @S084 */ }
            perform action a1 { doc /* advises the Marine Coordinator on conditions that may affect marine operations @S084 */ }
            perform action a2 { doc /* reviews forecast limitations @S107 */ }
            perform action a3 { doc /* identifies conditions that may affect vessel access or turbine work @S107 */ }
            perform action a4 { doc /* reviews forecast changes @S232 */ }
            perform action a5 { doc /* advises the Marine Coordinator when conditions may affect the plan @S232 */ }
            perform action a6 { doc /* reviews forecast confidence @S256 */ }
            perform action a7 { doc /* highlights conditions that could invalidate a planned access period @S256 */ }
            perform action a8 { doc /* compares forecast data with recent observations @S272 */ }
            perform action a9 { doc /* advising on the reliability of a work window @S272 */ }
            perform action a10 { doc /* uses the Wave Burst Record @S323 */ }
            perform action a11 { doc /* assess whether the planned access period remains suitable @S323 */ }
            perform action a12 { doc /* produces the Visibility Confidence Note @S472 */ }
            perform action a13 { doc /* summarize confidence in visibility conditions for near-term port and offshore planning @S472 */ }
            perform action a14 { doc /* reviews the forecast @S522 */ }
            perform action a15 { doc /* advises the Duty Planner if conditions could affect the planned sequence @S522 */ }
            perform action a16 { doc /* interprets forecast uncertainty @S626 */ }
            perform action a17 { doc /* communicates material changes to the Rescue Coordinator @S626 */ }
            perform action a18 { doc /* interprets forecast uncertainty @S641 */ }
            perform action a19 { doc /* identifies conditions that could affect safe vessel handling @S641 */ }
            perform action a20 { doc /* assesses forecast uncertainty @S765 */ }
            perform action a21 { doc /* communicates conditions that could affect access, lifting, or work at height @S765 */ }
            perform action a22 { doc /* support entry into Weather Hold when forecast or observed conditions exceed approved operating limits @S939 */ }
        }
        part weatherHold : WeatherHold {
            perform action a0 { doc /* pauses affected marine activity @S086 */ }
            perform action a1 { doc /* prevents mobilization @S259 */ }
        }
        part weatherService : WeatherService {
            perform action a0 { doc /* contributes environmental information to operational planning and coordination @S067 */ }
            perform action a1 { doc /* produces the Squall Window Bulletin for operational awareness @S083 */ }
            perform action a2 { doc /* uses validated environmental observations in forecast products for offshore planning @S106 */ }
            perform action a3 { doc /* issues forecast updates that support timing decisions for remote observation and field work @S128 */ }
            perform action a4 { doc /* provides forecast information for marine planning @S230 */ }
            perform action a5 { doc /* supplies forecast information for evaluating marine and aviation access options @S255 */ }
            perform action a6 { doc /* provides forecast conditions and confidence information for planned work areas and vessel routes @S270 */ }
            perform action a7 { doc /* provide contextual conditions that help reviewers distinguish environmental effects from equipment deterioration @S309 */ }
            perform action a8 { doc /* provide forecasts and measured conditions @S443 */ }
            perform action a9 { doc /* supplies forecast conditions relevant to access and safe execution @S521 */ }
            perform action a10 { doc /* provides forecast information for planning @S624 */ }
            perform action a11 { doc /* provides current forecasts for the recovery area and the planned transit route @S640 */ }
            perform action a12 { doc /* Reported visibility @S662 */ }
            perform action a13 { doc /* prompts review of the observation age, location, and surrounding weather conditions @S666 */ }
            perform action a14 { doc /* provide inputs @S766 */ }
            perform action a15 { doc /* support entry into Weather Hold when forecast or observed conditions exceed approved operating limits @S939 */ }
        }
        part weatherServiceForecast : WeatherServiceForecast {
            perform action a0 { doc /* provides context for expected changes @S664 */ }
        }
        part weatherServiceForecasts : WeatherServiceForecasts {
            perform action a0 { doc /* are considered alongside berth availability @S471 */ }
        }
        part weatherServices : WeatherServices;
        part westRouteLandingDoors : WestRouteLandingDoors {
            perform action a0 { doc /* are inspected for damage, secure closure, and unobstructed movement @S889 */ }
        }
        part westServiceLift : WestServiceLift {
            perform action a0 { doc /* provides vertical access along the west route between the designated service landings @S884 */ }
            perform action a1 { doc /* is placed in service @S893 */ }
            exhibit state modes {
                state s0 { doc /* removed from service @S883 */ }
            }
        }
        part windFarmAssets : WindFarmAssets;
        part work : Work {
            perform action a0 { doc /* can proceed @S156 */ }
            perform action a1 { doc /* begins @S329 */ }
            perform action a2 { doc /* stop @S330 */ }
            perform action a3 { doc /* would reduce generation or access to export equipment @S388 */ }
            perform action a4 { doc /* proceeds @S581 */ }
            perform action a5 { doc /* requiring visual alignment, external inspection, or unobstructed observation @S672 */ }
            perform action a6 { doc /* resumes @S685 */ }
            perform action a7 { doc /* stop @S717 */ }
            exhibit state modes {
                state s0 { doc /* complete @S426 */ }
            }
        }
        part workArrangements : WorkArrangements {
            perform action a0 { doc /* account for applicable safety controls and personnel responsibilities @S095 */ }
        }
        part workParty : WorkParty {
            perform action a0 { doc /* confirms equipment identity using permanent labels and the current site designation @S720 */ }
            perform action a1 { doc /* using permanent labels and the current site designation @S720 */ }
            exhibit state modes {
                state s0 { doc /* complete @S405 */ }
            }
        }
        part workPermitPortal : WorkPermitPortal {
            perform action a0 { doc /* support controlled and secure operations @S049 */ }
            perform action a1 { doc /* supports authorization processes @S070 */ }
            perform action a2 { doc /* planning maintenance work @S149 */ }
            perform action a3 { doc /* reviewing maintenance work @S149 */ }
            perform action a4 { doc /* approving maintenance work @S149 */ }
            perform action a5 { doc /* closing maintenance work @S149 */ }
            perform action a6 { doc /* maintains the request record and its revision history throughout review and execution @S155 */ }
            perform action a7 { doc /* records review decisions @S162 */ }
            perform action a8 { doc /* returns incomplete requests to the requester with the required corrections identified @S162 */ }
            perform action a9 { doc /* records the start, pause, resumption, and completion of authorized work against the permit record @S169 */ }
            perform action a10 { doc /* supports readiness checks for work requiring controlled access or electrical isolation @S265 */ }
            perform action a11 { doc /* block permit release @S321 */ }
            perform action a12 { doc /* produces the Isolation Boundary Sketch @S492 */ }
            perform action a13 { doc /* makes the approved boundary available to the work party and the control team @S713 */ }
            perform action a14 { doc /* retains the current approval @S728 */ }
            perform action a15 { doc /* makes superseded versions unavailable for active work @S728 */ }
            perform action a16 { doc /* reflect the agreed timing and work boundaries @S751 */ }
            perform action a17 { doc /* retains permit decisions and associated approvals in a form that can be retrieved for review @S780 */ }
        }
        part workPlan : WorkPlan {
            perform action a0 { doc /* requires extended support @S228 */ }
        }
        part workScope : WorkScope {
            perform action a0 { doc /* fit the approved duration @S750 */ }
        }
        flow f0 of InputItem from fieldSupervisor to dutyPlanner { doc /* @S076 */ }
        flow f1 of InputItem from maintenancePlanningEngine to dutyPlanner { doc /* @S076 */ }
        flow f2 of SharedViewOfVesselAssignmentsPlannedMovementsAndDispatchStatusItem from fleetDispatchConsole to marineCoordinator { doc /* @S081 */ }
        flow f4 of ConditionsThatMayAffectMarineOperationsItem from weatherAnalyst to marineCoordinator { doc /* @S084 */ }
        flow f5 of ChangesToWorkProgressItem from fieldSupervisor to dutyPlanner { doc /* @S096 */ }
        flow f6 of ObservationsItem from metoceanBuoy to onboardLogger { doc /* @S104 */ }
        flow f7 of ValidatedEnvironmentalObservationsItem from metoceanBuoy to weatherService { doc /* @S106 */ }
        flow f8 of TurbineControlCommandsItem from turbineController to pitchSystem { doc /* @S130 */ }
        flow f9 of TurbineStatusItem from sCADAGateway to authorizedShorePersonnel { doc /* @S133 */ }
        flow f10 of ControlAvailabilityItem from sCADAGateway to authorizedShorePersonnel { doc /* @S133 */ }
        flow f11 of PitchDeviationNoticeItem from turbineController to sCADAGateway { doc /* @S159 */ }
        flow f12 of IncompleteRequestsItem from workPermitPortal to requester { doc /* @S162 */ }
        flow f13 of CurrentOperationalStatusItem from sCADAGateway to permitReviewers { doc /* @S171 */ }
        flow f14 of SupplyAlarmsItem from sCADAGateway to shoreControlRoom { doc /* @S192 */ }
        flow f15 of GeneratorStatusItem from sCADAGateway to shoreControlRoom { doc /* @S192 */ }
        flow f16 of ElectricalPowerItem from offshoreFarm to designatedGridConnectionPoint { doc /* @S199 */ }
        flow f17 of AuthorizedOperatingSignalsItem from gridInterfaceRelay to externalTransmissionSystem { doc /* @S201 */ }
        flow f18 of AuthorizedOperatingSignalsItem from externalTransmissionSystem to gridInterfaceRelay { doc /* @S201 */ }
        flow f19 of RelayStatusItem from sCADAGateway to farmMonitoringEnvironment { doc /* @S211 */ }
        flow f20 of InterfaceMeasurementsItem from sCADAGateway to farmMonitoringEnvironment { doc /* @S211 */ }
        flow f21 of SquallWindowBulletinItem from weatherService to maintenancePlanningEngine { doc /* @S213 */ }
        flow f22 of PositionQualityFlagItem from vesselAISReceiver to fleetDispatchConsole { doc /* @S225 */ }
        flow f23 of UpdateItem from marineCoordinator to affectedTeams { doc /* @S245 */ }
        flow f24 of BackorderExceptionSlipItem from warehouseSystem to storekeeper { doc /* @S262 */ }
        flow f25 of ResultingPlanItem from dutyPlanner to affectedTeams { doc /* @S269 */ }
        flow f26 of ForecastConditionsItem from weatherService to weatherAnalyst { doc /* @S270 */ }
        flow f27 of ConfidenceInformationItem from weatherService to team { doc /* @S270 */ }
        flow f28 of ObservationsItem from metoceanBuoy to team { doc /* @S271 */ }
        flow f29 of ForecastDataItem from weatherService to weatherAnalyst { doc /* @S272 */ }
        flow f30 of ObservationsItem from metoceanBuoy to weatherAnalyst { doc /* @S272 */ }
        flow f31 of TransferManifestAddendumItem from dutyPlanner to vesselMaster { doc /* @S278 */ }
        flow f34 of OperatingMeasurementsItem from turbineController to turbineSensorBus { doc /* @S294 */ }
        flow f35 of OperatingMeasurementsItem from pitchSystem to turbineSensorBus { doc /* @S294 */ }
        flow f36 of OperatingMeasurementsItem from converterCabinet to turbineSensorBus { doc /* @S294 */ }
        flow f37 of OperatingMeasurementsItem from nacelleConditionMonitor to turbineSensorBus { doc /* @S294 */ }
        flow f38 of TimeStampedObservationsItem from sCADAGateway to shoreControlRoom { doc /* @S295 */ }
        flow f39 of AlarmsItem from sCADAGateway to controlEngineer { doc /* @S297 */ }
        flow f40 of IndependentSignalsItem from turbineController to controlEngineer { doc /* @S299 */ }
        flow f41 of IndependentSignalsItem from nacelleConditionMonitor to controlEngineer { doc /* @S299 */ }
        flow f42 of ContextualConditionsItem from weatherService to technicalReviewers { doc /* @S309 */ }
        flow f43 of ContextualConditionsItem from metoceanBuoy to technicalReviewers { doc /* @S309 */ }
        flow f44 of HarnessAuditCardItem from hSEOfficer to crewTransferVessel { doc /* @S312 */ }
        flow f45 of WaveBurstRecordItem from metoceanBuoy to weatherAnalyst { doc /* @S323 */ }
        flow f46 of SessionRevocationReceiptItem from sCADAGateway to cybersecurityGateway { doc /* @S357 */ }
        flow f47 of ConciseStatusUpdatesItem from sCADAGateway to shoreControlRoom { doc /* @S364 */ }
        flow f48 of ActivePowerTargetsItem from gridDispatcher to controlEngineer { doc /* @S367 */ }
        flow f49 of RampInstructionsItem from gridDispatcher to controlEngineer { doc /* @S367 */ }
        flow f50 of TransformerTapSnapshotItem from offshoreSubstation to shoreControlRoom { doc /* @S374 */ }
        flow f51 of ChangeInDestinationOrTransferPlanItem from personnel to vesselMaster { doc /* @S402 */ }
        flow f52 of UnexplainedAbsenceItem from fieldSupervisor to marineCoordinator { doc /* @S412 */ }
        flow f53 of OverdueCheckInItem from fieldSupervisor to marineCoordinator { doc /* @S412 */ }
        flow f54 of UrgentConcernsItem from cybersecurityAnalyst to onDutyOperationsLead { doc /* @S419 */ }
        flow f55 of DeferredTaskRationaleItem from maintenancePlanningEngine to fieldSupervisor { doc /* @S430 */ }
        flow f56 of LeadingEdgeTileImageItem from bladeInspectionDrone to bladeSpecialist { doc /* @S445 */ }
        flow f57 of TaskDurationItem from maintenancePlanningEngine to dutyPlanner { doc /* @S470 */ }
        flow f58 of ResourceDemandItem from maintenancePlanningEngine to dutyPlanner { doc /* @S470 */ }
        flow f59 of DependencyStatusItem from maintenancePlanningEngine to dutyPlanner { doc /* @S470 */ }
        flow f60 of BerthSlotConfirmationItem from portAgent to marineCoordinator { doc /* @S473 */ }
        flow f61 of SiteConditionsItem from outgoingSupervisor to incomingSupervisor { doc /* @S512 */ }
        flow f62 of AccessStatusItem from outgoingSupervisor to incomingSupervisor { doc /* @S512 */ }
        flow f63 of OutstandingHazardsItem from outgoingSupervisor to incomingSupervisor { doc /* @S512 */ }
        flow f64 of PlannedWorkPeriodItem from maintenancePlanningEngine to dutyPlanner { doc /* @S520 */ }
        flow f67 of SwitchingInstructionsItem from controlEngineer to substationOperator { doc /* @S530 */ }
        flow f68 of SwitchingWindowAcknowledgmentItem from shoreControlRoom to substationOperator { doc /* @S531 */ }
        flow f69 of StartTestTraceItem from emergencyGenerator to substationOperator { doc /* @S532 */ }
        flow f70 of CompletionItem from switchingOperator to controlEngineer { doc /* @S533 */ }
        flow f71 of NextInstructionItem from controlEngineer to switchingOperator { doc /* @S533 */ }
        flow f72 of CurrentGenerationItem from sCADAGateway to operationsTeam { doc /* @S540 */ }
        flow f73 of ExportItem from sCADAGateway to operationsTeam { doc /* @S540 */ }
        flow f74 of EquipmentStatusItem from sCADAGateway to operationsTeam { doc /* @S540 */ }
        flow f75 of DiscrepanciesItem from marineCoordinator to shoreControlRoom { doc /* @S578 */ }
        flow f76 of ImmediateControlActionsItem from marineCoordinator to shoreControlRoom { doc /* @S578 */ }
        flow f77 of DiscrepanciesItem from marineCoordinator to dutyPlanner { doc /* @S583 */ }
        flow f78 of MaterialChangesItem from weatherAnalyst to rescueCoordinator { doc /* @S626 */ }
        flow f79 of AlarmIndicationsItem from fireDetectionPanel to responders { doc /* @S629 */ }
        flow f80 of DirectReportsItem from personnel to responders { doc /* @S629 */ }
        flow f81 of RecoveryBasketLoadSheetItem from serviceOperationsVessel to rescueCoordinator { doc /* @S646 */ }
        flow f82 of TechnicalGuidanceItem from controlEngineer to marineCoordinator { doc /* @S658 */ }
        flow f83 of RemainingHazardsItem from fieldSupervisor to marineCoordinator { doc /* @S660 */ }
        flow f84 of VisibilityItem from weatherService to dutyPlanner { doc /* @S662 */ }
        flow f85 of ContextForExpectedChangesItem from weatherServiceForecast to dutyPlanner { doc /* @S664 */ }
        flow f86 of LocalReferenceItem from metoceanBuoy to weatherService { doc /* @S665 */ }
        flow f87 of IsolationBoundaryItem from workPermitPortal to workParty { doc /* @S713 */ }
        flow f88 of IsolationBoundaryItem from workPermitPortal to controlTeam { doc /* @S713 */ }
        flow f89 of IsolationBoundarySketchItem from workPermitPortal to electricalTechnician { doc /* @S716 */ }
        flow f90 of IsolationBoundaryItem from fieldSupervisor to crew { doc /* @S717 */ }
        flow f91 of AccessRestrictionsItem from fieldSupervisor to crew { doc /* @S717 */ }
        flow f92 of ConditionsThatRequireWorkToStopItem from fieldSupervisor to crew { doc /* @S717 */ }
        flow f93 of RemainingOperationalLimitationItem from controlEngineer to affectedPersonnel { doc /* @S734 */ }
        flow f94 of SwitchingWindowAcknowledgmentItem from shoreControlRoom to offshoreSubstation { doc /* @S752 */ }
        flow f95 of TimelyClearAndTraceableInformationItem from operationalCommunications to peopleResponsibleForOffshoreWork { doc /* @S760 */ }
        flow f96 of RelevantMarineAndWeatherInformationItem from marineCoordinator to vesselPersonnel { doc /* @S764 */ }
        flow f97 of RelevantMarineAndWeatherInformationItem from marineCoordinator to dutyPlanner { doc /* @S764 */ }
        flow f98 of OperationalDataItem from sCADAGateway to shoreControlRoom { doc /* @S767 */ }
        flow f99 of ExternalOperatingRequirementsItem from gridDispatcher to gridInterfaceRelay { doc /* @S769 */ }
        flow f100 of ExternalOperatingRequirementsItem from gridDispatcher to responsibleControlPersonnel { doc /* @S769 */ }
        flow f101 of CriticalDetailsItem from receiver to sender { doc /* @S773 */ }
        flow f102 of EquipmentStatusItem from turbineSensorBus to protectiveFunctions { doc /* @S788 */ }
        flow f103 of EquipmentStatusItem from turbineSensorBus to operationalMonitoring { doc /* @S788 */ }
        flow f104 of IncomingAlarmsItem from sCADAGateway to shoreControlRoom { doc /* @S798 */ }
        flow f105 of UnresolvedPersonnelOrAccessConcernsItem from fieldSupervisor to shoreControlRoom { doc /* @S809 */ }
        flow f106 of ActiveFaultIndicationItem from liftSupply to electricalTechnician { doc /* @S867 */ }
        flow f107 of ActiveFaultIndicationItem from protectiveDevices to electricalTechnician { doc /* @S867 */ }
        flow f108 of ReleaseStatusItem from fieldSupervisor to workParty { doc /* @S881 */ }
        flow f109 of OperationalRestrictionsItem from fleetDispatchConsole to dutyPlanner { doc /* @S947 */ }
    }
    requirement def R0 { doc /* maintenance activities required to deliver safe electrical generation @S002 */ subject s : MaintenanceActivities; }
    requirement def R1 { doc /* Safety objectives require work to be authorized @S011 */ subject s : Work; }
    requirement def R2 { doc /* Safety objectives require hazards to be controlled @S011 */ subject s : Hazards; }
    requirement def R3 { doc /* Safety objectives require personnel and vessels to be accounted for throughout each operation @S011 */ subject s : Personnel; }
    requirement def R4 { doc /* Safety objectives require personnel and vessels to be accounted for throughout each operation @S011 */ subject s : Vessels; }
    requirement def R5 { doc /* Administrative access requires authenticated individual accounts and role-based authorization. @S115 */ subject s : AdministrativeAccess; }
    requirement def R6 { doc /* Any material change to scope, conditions, or timing requires reassessment and may suspend the current authorization. @S168 */ subject s : CurrentAuthorization; }
    requirement def R7 { doc /* Juniper Vale shall provide current operational status to permit reviewers when requested as part of the authorization check. @S171 */ subject s : SCADAGateway; }
    requirement def R8 { doc /* Where a turbine response is required, the Control Engineer follows the approved operating procedure and confirms the resulting state through available indications. @S305 */ subject s : TurbineResponse; }
    requirement def R9 { doc /* Larkspur shall repeat a close-range pass when image coverage is insufficient to assess the suspected surface condition. @S314 */ subject s : BladeInspectionDrone; }
    requirement def R10 { doc /* Redoubt shall block permit release until required risk reviews and isolation references are complete. @S321 */ subject s : WorkPermitPortal; }
    requirement def R11 { doc /* A change in equipment condition, task scope, or operating constraint requires the Field Supervisor to pause work and reassess the authorization. @S333 */ subject s : FieldSupervisor; }
    requirement def R12 { doc /* The Export Cable Monitor is reviewed for trends or alarms that require escalation to the Control Engineer. @S346 */ subject s : ExportCableMonitor; }
    requirement def R13 { doc /* Remote sessions require approved connection paths, strong authentication, and active supervision when they can affect live operations. @S427 */ subject s : RemoteSessions; }
    requirement def R14 { doc /* a cybersecurity-related work item must be postponed @S430 */ subject s : CybersecurityRelatedWorkItem; }
    requirement def R15 { doc /* blade condition requires review @S440 */ subject s : BladeCondition; }
    requirement def R16 { doc /* operating restrictions required during the remote survey @S448 */ subject s : OperatingRestrictions; }
    requirement def R17 { doc /* equipment that must be inspected, secured, or transferred before sailing @S477 */ subject s : Equipment; }
    requirement def R18 { doc /* Any change to the work scope requires a renewed safety review before affected work resumes. @S510 */ subject s : ChangeToTheWorkScope; }
    requirement def R19 { doc /* A Grid Constraint requires the Duty Planner to reassess the sequence and obtain revised authorization before work proceeds. @S519 */ subject s : DutyPlanner; }
    requirement def R20 { doc /* Electrical recovery work requires qualified personnel, verified isolation, and a safe means of access before hands-on activity begins. @S631 */ subject s : ElectricalRecoveryWork; }
    requirement def R21 { doc /* A Daughter Craft operation requires particular caution where reduced visibility could compromise separation from other vessels or structures. @S679 */ subject s : DaughterCraft; }
    requirement def R22 { doc /* Substitutions require engineering acceptance and confirmation that the alternative meets the required interface and operating limits. @S704 */ subject s : Substitutions; }
    requirement def R23 { doc /* Urgent purchases require documented authorization and retain the same traceability and inspection controls as routine receipts. @S707 */ subject s : UrgentPurchases; }
    requirement def R24 { doc /* The equipment and energy sources must be made safe before field work begins. @S711 */ subject s : Equipment; }
    requirement def R25 { doc /* The equipment and energy sources must be made safe before field work begins. @S711 */ subject s : EnergySources; }
    requirement def R26 { doc /* Adjacent equipment identified by the approval must remain energized or available for service. @S715 */ subject s : AdjacentEquipment; }
    requirement def R27 { doc /* Work must stop under the conditions briefed by the Field Supervisor. @S717 */ subject s : Work; }
    requirement def R28 { doc /* Where local indication is required, a qualified technician checks the device at the point of isolation. @S719 */ subject s : QualifiedTechnician; }
    requirement def R29 { doc /* No isolation is removed until the work is complete, personnel and tools are accounted for, and the responsible authority approves restoration. @S732 */ subject s : Isolation; }
    requirement def R30 { doc /* The Rotor Brake Unit applies braking only in accordance with the turbine protection sequence and operating limits. @S791 */ subject s : RotorBrakeUnit; }
    requirement def R31 { doc /* supervisory faults that require assessment @S796 */ subject s : SupervisoryFaults; }
    requirement def R32 { doc /* An alarm is not cleared solely because a detector signal has returned to normal. @S797 */ subject s : Alarm; }
    requirement def R33 { doc /* The Electrical Technician performs local inspection only after the area has been assessed as safe and the required electrical isolations are in place. @S801 */ subject s : ElectricalTechnician; }
    requirement def R34 { doc /* The scanner accepts only credentials that can be read reliably and associated with an identifiable person. @S811 */ subject s : NorthAccessScanner; }
    requirement def R35 { doc /* The contingency process requires a named approver and a recorded reason for any temporary access decision. @S829 */ subject s : ApprovedContingencyProcess; }
    requirement def R36 { doc /* Personnel must not hold the barrier open for another entrant. @S847 */ subject s : Personnel; }
    requirement def R37 { doc /* Long or unstable loads are not carried unless an approved handling arrangement keeps the load contained within the car. @S877 */ subject s : LongOrUnstableLoads; }
    requirement def R38 { doc /* Its use is limited to personnel and equipment authorized for the turbine work area. @S885 */ subject s : WestServiceLift; }
    requirement def R39 { doc /* Lighting inside the car and at each landing must be adequate for safe movement and inspection. @S891 */ subject s : LightingInsideTheCarAndAtEachLanding; }
    requirement def R40 { doc /* Door interlocks and other protective devices must be functional before the lift is placed in service. @S893 */ subject s : DoorInterlocks; }
    requirement def R41 { doc /* Door interlocks and other protective devices must be functional before the lift is placed in service. @S893 */ subject s : ProtectiveDevices; }
    requirement def R42 { doc /* Protective devices must not be bypassed to maintain access or avoid delay. @S894 */ subject s : ProtectiveDevices; }
    requirement def R43 { doc /* Any unexpected movement or control response requires the operator to stop the lift at the nearest safe landing when practicable. @S901 */ subject s : Operator; }
    requirement def R44 { doc /* Required inspections and functional checks are completed before affected equipment is returned to automatic control or normal duty. @S953 */ subject s : AffectedEquipment; }
    requirement def R45 { doc /* Changes to operating assumptions, responsibilities, interfaces, or decision authority require documented impact assessment before approval. @S960 */ subject s : ChangesToOperatingAssumptionsResponsibilitiesInterfacesOrDecisionAuthority; }
}
