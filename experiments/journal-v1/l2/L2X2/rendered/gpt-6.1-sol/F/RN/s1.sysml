package L2Model {
    item def AuthorizedOperatingSignalsItem { doc /* @S201 */ }
    item def AvailableTrafficPictureItem { doc /* @S141 */ }
    item def BackorderExceptionSlipItem { doc /* @S262 */ }
    item def BerthSlotConfirmationItem { doc /* @S473 */ }
    item def ChangeInDestinationOrTransferPlanItem { doc /* @S402 */ }
    item def CrewCountCorrectionItem { doc /* @S573 */ }
    item def CurrentGenerationExportAndEquipmentStatusItem { doc /* @S540 */ }
    item def CurrentOperationalStatusItem { doc /* @S171 */ }
    item def DeferredTaskRationaleItem { doc /* @S430 */ }
    item def DiscrepancyAndTheImmediateControlActionsItem { doc /* @S578 */ }
    item def ElectricalPowerItem { doc /* @S199 */ }
    item def ExportLimitAdvisoryItem { doc /* @S541 */ }
    item def ExternalOperatingRequirementsItem { doc /* @S769 */ }
    item def FirmwareHashAttestationItem { doc /* @S593 */ }
    item def HarnessAuditCardItem { doc /* @S312 */ }
    item def IsolationBoundarySketchItem { doc /* @S716 */ }
    item def LeadingEdgeTileImageItem { doc /* @S445 */ }
    item def MaterialChangesItem { doc /* @S626 */ }
    item def OperatingMeasurementsItem { doc /* @S294 */ }
    item def OperationalDataItem { doc /* @S767 */ }
    item def PitchDeviationNoticeItem { doc /* @S159 */ }
    item def PositionQualityFlagItem { doc /* @S225 */ }
    item def RecoveryBasketLoadSheetItem { doc /* @S646 */ }
    item def RelayStatusAndInterfaceMeasurementsItem { doc /* @S211 */ }
    item def ReleaseStatusItem { doc /* @S881 */ }
    item def RelevantMarineAndWeatherInformationItem { doc /* @S764 */ }
    item def RemainingOperationalLimitationItem { doc /* @S734 */ }
    item def ResultingPlanItem { doc /* @S269 */ }
    item def SessionRevocationReceiptItem { doc /* @S357 */ }
    item def SharedViewOfVesselAssignmentsPlannedMovementsAndDispatchStatusItem { doc /* @S081,S082 */ }
    item def SquallWindowBulletinItem { doc /* @S213 */ }
    item def StartTestTraceItem { doc /* @S532 */ }
    item def SupplyAlarmsAndGeneratorStatusItem { doc /* @S192 */ }
    item def SwitchingWindowAcknowledgmentItem { doc /* @S752 */ }
    item def TimeStampedObservationsItem { doc /* @S295 */ }
    item def TransferManifestAddendumItem { doc /* @S278 */ }
    item def TransformerTapSnapshotItem { doc /* @S374 */ }
    item def TurbineControlCommandsItem { doc /* @S130 */ }
    item def TurbineStatusAndControlAvailabilityItem { doc /* @S133 */ }
    item def UnresolvedPersonnelOrAccessConcernsItem { doc /* @S809 */ }
    item def ValidatedEnvironmentalObservationsItem { doc /* @S106 */ }
    item def VisibilityConfidenceNoteItem { doc /* @S669 */ }
    item def WaveBurstRecordItem { doc /* @S323 */ }
    part def AccountabilityRecords { doc /* @S414 */ }
    part def AdjacentEquipment { doc /* @S715 */ }
    part def AffectedPersonnel { doc /* @S734 */ }
    part def AffectedTeams { doc /* @S269 */ }
    part def Approver { doc /* @S979 */ }
    part def AssetOperator { doc /* @S959 */ }
    part def AuditRecord { doc /* @S823 */ }
    part def AuthorizedShorePersonnel { doc /* @S133 */ }
    part def AutomaticControls { doc /* @S177 */ }
    part def BladeInspectionDrone { doc /* @S142,S254,S313,S314,S444,S445 */ }
    part def BladeSpecialist { doc /* @S143,S315,S445,S452,S455,S463,S651 */ }
    part def ControlEngineer { doc /* @S063,S135,S193,S217,S297,S299,S302,S305,S310,S316,S338,S349,S368,S375,S384,S423,S434,S516,S528,S534,S542,S544,S552,S560,S562,S594,S630,S658,S718,S734,S742,S768,S799,S920,S938,S951,S964 */ }
    part def ControlFunctions { doc /* @S002 */ }
    part def ControlRoomStaff { doc /* @S729 */ }
    part def ConverterCabinet { doc /* @S005,S131,S294,S547 */ }
    part def Crew { doc /* @S167,S495,S504,S506,S511 */ }
    part def CrewTransferVessel { doc /* @S045,S087,S215,S279,S312,S643 */ }
    part def CybersecurityAnalyst { doc /* @S117,S419,S428,S435,S593,S781,S929,S969 */ }
    part def CybersecurityGateway { doc /* @S071,S111,S287,S357,S416 */ }
    part def CybersecurityRelatedWorkItem { doc /* @S430 */ }
    part def DaughterCraft { doc /* @S045,S088,S621 */ }
    part def DesignatedAuthorizingRole { doc /* @S165 */ }
    part def DocumentOwner { doc /* @S976 */ }
    part def DoorInterlocks { doc /* @S893 */ }
    part def DutyPlanner { doc /* @S065,S076,S126,S153,S164,S224,S247,S258,S260,S263,S269,S274,S278,S292,S304,S319,S334,S340,S388,S396,S442,S459,S464,S469,S491,S515,S519,S527,S536,S537,S539,S553,S561,S639,S669,S695,S737,S758,S764,S779,S872,S925,S947,S955,S965 */ }
    part def EastServiceLift { doc /* @S859 */ }
    part def ElectricalTechnician { doc /* @S185,S325,S327,S331,S336,S363,S434,S496,S529,S650,S716,S750,S801,S867 */ }
    part def EmergencyGenerator { doc /* @S180,S186,S353,S354,S532,S803 */ }
    part def Entrant { doc /* @S839 */ }
    part def EntryBarrier { doc /* @S846 */ }
    part def Equipment { doc /* @S477 */ }
    part def ExportCableMonitor { doc /* @S006,S200,S252 */ }
    part def FarmMonitoringEnvironment { doc /* @S211 */ }
    part def FieldSupervisor { doc /* @S096,S145,S167,S253,S320,S329,S330,S333,S335,S340,S405,S412,S429,S430,S457,S493,S503,S509,S536,S615,S649,S660,S717,S726,S778,S809,S826,S860,S869,S879,S881,S886,S887,S906,S927,S970 */ }
    part def FieldTeam { doc /* @S729 */ }
    part def FireDetectionPanel { doc /* @S629,S786 */ }
    part def FleetDispatchConsole { doc /* @S041,S069,S081,S082,S203,S225,S260,S370,S385,S543,S917,S947 */ }
    part def Gate { doc /* @S816 */ }
    part def GridConnectionPoint { doc /* @S199 */ }
    part def GridDispatcher { doc /* @S202,S367,S518,S541,S739,S769 */ }
    part def GridInterfaceRelay { doc /* @S190,S201,S221,S372,S373,S541,S551,S769,S942 */ }
    part def HSEOfficer { doc /* @S095,S157,S237,S266,S312,S322,S408,S451,S481,S505,S526,S579,S617,S647,S808,S827,S949,S967 */ }
    part def IncidentLead { doc /* @S432,S436,S619 */ }
    part def IncomingTeam { doc /* @S731 */ }
    part def Inspector { doc /* @S862,S865,S868 */ }
    part def InstallationTeam { doc /* @S853 */ }
    part def Lighting { doc /* @S891 */ }
    part def LocalVisualIndicator { doc /* @S845 */ }
    part def MainTransformer { doc /* @S006 */ }
    part def MaintenanceActivities { doc /* @S002 */ }
    part def MaintenancePlanningEngine { doc /* @S042,S054,S058,S066,S148,S154,S188,S195,S213,S246,S285,S308,S430,S441,S458,S470,S520,S670,S694,S738,S918,S948 */ }
    part def MarineCoordinator { doc /* @S068,S077,S081,S082,S141,S160,S223,S245,S257,S261,S277,S283,S290,S397,S400,S410,S466,S473,S483,S488,S499,S523,S565,S576,S578,S583,S585,S618,S638,S659,S676,S682,S749,S764,S944,S966 */ }
    part def MetoceanBuoy { doc /* @S102,S106,S194,S231,S309,S323,S443,S625,S665,S766 */ }
    part def MonitoringProcess { doc /* @S296 */ }
    part def NacelleConditionMonitor { doc /* @S005,S132,S250,S294,S793,S915 */ }
    part def NorthAccessScanner { doc /* @S235,S394,S569,S810,S811,S813,S831 */ }
    part def Occupants { doc /* @S899,S902,S905 */ }
    part def OffshorePersonnel { doc /* @S804 */ }
    part def OffshoreSubstation { doc /* @S003,S037,S189,S267,S361,S374,S752,S941 */ }
    part def OffshoreSubstationOperator { doc /* @S549 */ }
    part def OffshoreSupportFacilities { doc /* @S002 */ }
    part def OffshoreWindFarm { doc /* @S002,S003,S005,S006,S028,S199,S205 */ }
    part def OffshoreWindFarmOperationsAndMaintenanceSystem { doc /* @S058,S183,S824,S908,S935,S957 */ }
    part def OnboardLogger { doc /* @S104 */ }
    part def OperatingOrganization { doc /* @S098 */ }
    part def OperationalPersonnel { doc /* @S349 */ }
    part def OperationsRadioConsole { doc /* @S239,S627,S762,S806 */ }
    part def OperationsTeam { doc /* @S540 */ }
    part def Operators { doc /* @S184,S832 */ }
    part def Organization { doc /* @S782 */ }
    part def OutgoingSupervisor { doc /* @S512 */ }
    part def Passengers { doc /* @S896 */ }
    part def PermitReviewers { doc /* @S171 */ }
    part def Person { doc /* @S812,S817 */ }
    part def Personnel { doc /* @S393,S402,S406,S431,S501,S771,S828,S847,S856,S903,S981 */ }
    part def PersonnelTrackingConsole { doc /* @S094,S234,S332,S392,S571,S573,S619,S648,S805 */ }
    part def PitchSystem { doc /* @S005,S130,S294,S546,S790 */ }
    part def PortAgent { doc /* @S093,S240,S324,S473 */ }
    part def ProtectiveDevices { doc /* @S894 */ }
    part def QualifiedTechnician { doc /* @S719 */ }
    part def Receiver { doc /* @S773 */ }
    part def Requester { doc /* @S152 */ }
    part def RescueCoordinator { doc /* @S244,S614,S626,S634,S637,S646 */ }
    part def ResponsibleControlPersonnel { doc /* @S769 */ }
    part def ResponsibleManager { doc /* @S784 */ }
    part def ResponsibleSupervisor { doc /* @S413 */ }
    part def ResponsibleTeam { doc /* @S170,S450 */ }
    part def ReviewTeams { doc /* @S922 */ }
    part def Reviewers { doc /* @S596 */ }
    part def RotorBrakeUnit { doc /* @S005,S791 */ }
    part def SCADAEngineer { doc /* @S062,S423,S437,S558,S593,S946,S954,S968 */ }
    part def SCADAGateway { doc /* @S006,S052,S058,S059,S133,S159,S171,S192,S211,S212,S295,S357,S369,S417,S447,S540,S767,S800,S914,S946 */ }
    part def Sender { doc /* @S773 */ }
    part def ServiceOperationsVessel { doc /* @S045,S089,S228,S281,S461,S622,S645,S646,S680 */ }
    part def ShiftRecords { doc /* @S365,S389 */ }
    part def ShoreControlRoom { doc /* @S040,S058,S064,S097,S099,S134,S192,S214,S238,S295,S303,S317,S339,S364,S371,S374,S386,S420,S448,S531,S578,S606,S613,S683,S752,S767,S798,S809,S937,S963 */ }
    part def SouthAccessScanner { doc /* @S236,S395,S570,S835,S838,S840,S843 */ }
    part def SparesHub { doc /* @S689 */ }
    part def StationServiceTransformers { doc /* @S173 */ }
    part def Storekeeper { doc /* @S092,S242,S262,S460,S479,S690,S703,S876 */ }
    part def SubstationOperator { doc /* @S216,S268,S326,S337,S342,S343,S382,S497,S517,S530,S532,S559,S741,S753,S971 */ }
    part def SwitchingOperator { doc /* @S533 */ }
    part def Team { doc /* @S280,S289 */ }
    part def TechnicalReviewers { doc /* @S158 */ }
    part def TechnicalTeams { doc /* @S433,S439 */ }
    part def TemporaryPersonnel { doc /* @S849 */ }
    part def Transaction { doc /* @S821,S822 */ }
    part def TransmissionSystem { doc /* @S201 */ }
    part def TurbineController { doc /* @S005,S060,S061,S127,S129,S130,S159,S191,S294,S377,S545,S789,S937 */ }
    part def TurbineLockout { doc /* @S802 */ }
    part def TurbineSensorBus { doc /* @S005,S251,S294,S788 */ }
    part def TurbineStructures { doc /* @S003 */ }
    part def Turbines { doc /* @S003 */ }
    part def Users { doc /* @S882 */ }
    part def VesselAISReceiver { doc /* @S105,S139,S140,S141,S225,S288,S401 */ }
    part def VesselMaster { doc /* @S079,S085,S161,S226,S278,S284,S390,S398,S402,S403,S409,S476,S498,S524,S567,S573,S577,S616,S634,S642,S677,S682,S763,S807,S944 */ }
    part def VesselPersonnel { doc /* @S764 */ }
    part def Visitors { doc /* @S849 */ }
    part def WarehouseSystem { doc /* @S091,S163,S241,S262,S478,S687,S928 */ }
    part def WeatherAnalyst { doc /* @S084,S107,S232,S256,S272,S323,S472,S522,S626,S641,S669,S765,S939 */ }
    part def WeatherHold { doc /* @S086,S259 */ }
    part def WeatherService { doc /* @S067,S083,S106,S128,S213,S230,S255,S270,S309,S443,S521,S624,S640,S664,S766,S939 */ }
    part def WestServiceLift { doc /* @S884 */ }
    part def WindFarmAssets { doc /* @S002 */ }
    part def WorkParty { doc /* @S720,S881 */ }
    part def WorkPermitPortal { doc /* @S070,S155,S162,S169,S265,S321,S492,S713,S716,S728,S780 */ }
    part system {
        part accountabilityRecords : AccountabilityRecords {
            perform action a0 { doc /* retain the time, location, responsible role, and disposition of each material movement @S414 */ }
        }
        part adjacentEquipment : AdjacentEquipment;
        part affectedPersonnel : AffectedPersonnel;
        part affectedTeams : AffectedTeams;
        part approver : Approver {
            perform action a0 { doc /* confirms that comments are resolved or explicitly accepted @S979 */ }
        }
        part assetOperator : AssetOperator {
            perform action a0 { doc /* assigns an accountable owner to maintain the document and coordinate its approval @S959 */ }
        }
        part auditRecord : AuditRecord {
            perform action a0 { doc /* distinguishes a rejected credential from an authorization that lacks the required scope @S823 */ }
        }
        part authorizedShorePersonnel : AuthorizedShorePersonnel;
        part automaticControls : AutomaticControls {
            perform action a0 { doc /* initiate the Emergency Generator start sequence @S177 */ }
        }
        part bladeInspectionDrone : BladeInspectionDrone {
            perform action a0 { doc /* captures close-range visual observations of accessible blade surfaces @S142 */ }
            perform action a1 { doc /* can support inspection planning when blade access from a vessel or by rope team is not justified @S254 */ }
            perform action a2 { doc /* produces the Leading Edge Tile Image during a close-range survey of the blade surface @S313 */ }
            perform action a3 { doc /* repeat a close-range pass when image coverage is insufficient to assess the suspected surface condition @S314 */ }
            perform action a4 { doc /* capture repeatable views of blade surfaces while the turbine is in an approved operating state @S444 */ }
        }
        part bladeSpecialist : BladeSpecialist {
            perform action a0 { doc /* plans inspection passes to provide consistent coverage of areas selected for examination @S143 */ }
            perform action a1 { doc /* reviews available inspection evidence @S315 */ }
            perform action a2 { doc /* reports whether further examination is warranted @S315 */ }
            perform action a3 { doc /* reviews the tile image to classify visible damage and identify areas requiring closer assessment @S445 */ }
            perform action a4 { doc /* examines the affected surface using suitable lighting, measurement tools, and nondestructive inspection methods @S452 */ }
            perform action a5 { doc /* distinguishes cosmetic damage from conditions that could affect structural integrity or safe turbine operation @S455 */ }
            perform action a6 { doc /* records the completed work and verifies that the repaired area meets the applicable acceptance criteria @S463 */ }
            perform action a7 { doc /* identifies fragile blade components and specifies padding or restraints to prevent handling damage @S651 */ }
        }
        part controlEngineer : ControlEngineer {
            perform action a0 { doc /* uses the shore-based operational picture @S063 */ }
            perform action a1 { doc /* assess equipment status @S063 */ }
            perform action a2 { doc /* coordinate response @S063 */ }
            perform action a3 { doc /* reviews alarms and operating conditions @S135 */ }
            perform action a4 { doc /* issuing a remote command @S135 */ }
            perform action a5 { doc /* reviews persistent alarms and coordinates electrical support with the Substation Operator @S193 */ }
            perform action a6 { doc /* verifies that dispatch changes are reflected in the applicable control settings before implementation @S217 */ }
            perform action a7 { doc /* reviews alarms alongside recent operating trends rather than treating an isolated threshold crossing as a confirmed fault @S297 */ }
            perform action a8 { doc /* compares disputed readings with independent signals from the Turbine Controller and Nacelle Condition Monitor where available @S299 */ }
            perform action a9 { doc /* records the evidence considered and the basis for accepting, rejecting, or continuing to monitor an alert @S302 */ }
            perform action a10 { doc /* follows the approved operating procedure and confirms the resulting state through available indications @S305 */ }
            perform action a11 { doc /* requests an on-site inspection when remote evidence cannot resolve a material uncertainty @S310 */ }
            perform action a12 { doc /* reassesses the alert after field findings or corrected sensor data become available @S316 */ }
            perform action a13 { doc /* reviews the restored equipment state and confirms that required operational checks are complete @S338 */ }
            perform action a14 { doc /* investigates unexplained discrepancies @S349 */ }
            perform action a15 { doc /* reviews each instruction for consistency with current plant status @S368 */ }
            perform action a16 { doc /* applying it @S368 */ }
            perform action a17 { doc /* confirms that the control response follows the instruction and remains within the permitted ramp rate @S375 */ }
            perform action a18 { doc /* records the reason for any temporary deviation from the requested output and the action taken @S384 */ }
            perform action a19 { doc /* use individually assigned accounts rather than shared credentials for interactive work @S423 */ }
            perform action a20 { doc /* coordinate any operational changes with the relevant duty role before implementation @S434 */ }
            perform action a21 { doc /* checks the current network configuration and confirms that the proposed sequence supports the approved work @S516 */ }
            perform action a22 { doc /* prepares clear switching instructions with one action per step and an explicit hold point where needed @S528 */ }
            perform action a23 { doc /* monitors available indications and confirms that each reported state change matches the approved sequence @S534 */ }
            perform action a24 { doc /* verifies the permitted level, its effective time, and any required ramp rate @S542 */ }
            perform action a25 { doc /* changing operating targets @S542 */ }
            perform action a26 { doc /* reduces active power in controlled steps and checks that measured export follows the revised target @S544 */ }
            perform action a27 { doc /* compares actual export with the permitted level and investigates any persistent mismatch @S552 */ }
            perform action a28 { doc /* escalates any condition that threatens equipment limits, protection coordination, or safe operation @S560 */ }
            perform action a29 { doc /* confirms authorization and restores output gradually while monitoring equipment response @S562 */ }
            perform action a30 { doc /* confirms that proposed changes have a clear operational purpose and defined scope @S594 */ }
            perform action a31 { doc /* supports remote shutdown actions when communications and equipment status allow safe intervention @S630 */ }
            perform action a32 { doc /* provides technical guidance when recovery handling could affect turbine systems or restart readiness @S658 */ }
            perform action a33 { doc /* checks that remote indications agree with the approved switching state @S718 */ }
            perform action a34 { doc /* authorizing access @S718 */ }
            perform action a35 { doc /* verifies the restoration state and communicates any remaining operational limitation to affected personnel @S734 */ }
            perform action a36 { doc /* checks that turbine operations can be managed safely while the substation work is in progress @S742 */ }
            perform action a37 { doc /* reviews alarms and operating trends with the SCADA Engineer when an abnormal condition may require intervention @S768 */ }
            perform action a38 { doc /* verifies the equipment state and checks that protection actions have completed @S799 */ }
            perform action a39 { doc /* authorizing any further operational action @S799 */ }
            perform action a40 { doc /* examines significant operational deviations and records the technical findings for review @S920 */ }
            perform action a41 { doc /* suspends those commands and uses approved local procedures until reliable control is restored @S938 */ }
            perform action a42 { doc /* coordinates technical recovery with the relevant field and shore roles @S951 */ }
            perform action a43 { doc /* reviews control-room practices and confirms that operational procedures remain consistent with the concept @S964 */ }
        }
        part controlFunctions : ControlFunctions;
        part controlRoomStaff : ControlRoomStaff {
            perform action a0 { doc /* use the same revision when confirming isolation status @S729 */ }
        }
        part converterCabinet : ConverterCabinet {
            perform action a0 { doc /* manages electrical conversion while observing equipment limits and protective interlocks @S131 */ }
            perform action a1 { doc /* remains within its electrical and thermal ratings throughout the reduction @S547 */ }
        }
        part crew : Crew {
            perform action a0 { doc /* starts work @S167 */ }
            perform action a1 { doc /* confirms that the marked limits match the current isolation points and the approved maintenance scope @S495 */ }
            perform action a2 { doc /* inspects personal protective equipment, communications equipment, and rescue equipment for serviceability @S504 */ }
            perform action a3 { doc /* tests the required radio channel with the Operations Radio Console @S506 */ }
            perform action a4 { doc /* separating into work teams @S506 */ }
            perform action a5 { doc /* maintains clear access to fire equipment, escape routes, and lifting areas throughout the task @S511 */ }
        }
        part crewTransferVessel : CrewTransferVessel {
            perform action a0 { doc /* may support offshore work @S045 */ }
            perform action a1 { doc /* transports authorized personnel and routine tools between shore and offshore work locations @S087 */ }
            perform action a2 { doc /* reports its approach and departure status in accordance with the approved marine coordination procedure @S215 */ }
            perform action a3 { doc /* proceeds only when the Vessel Master considers the approach and transfer conditions acceptable @S279 */ }
            perform action a4 { doc /* uses the Harness Audit Card to verify the applicable equipment checks before personnel transfer @S312 */ }
            perform action a5 { doc /* transports personnel and small equipment only when sea conditions and transfer arrangements are acceptable @S643 */ }
        }
        part cybersecurityAnalyst : CybersecurityAnalyst {
            perform action a0 { doc /* monitors gateway events for unusual access patterns and configuration changes @S117 */ }
            perform action a1 { doc /* reviews alerts, assesses their operational significance, and escalates urgent concerns to the on-duty operations lead @S419 */ }
            perform action a2 { doc /* produces the Firmware Hash Attestation for controlled software releases @S428 */ }
            perform action a3 { doc /* preserves relevant logs and technical evidence while limiting access to personnel assigned to the investigation @S435 */ }
            perform action a4 { doc /* protects access logs and communication records against unauthorized alteration or disclosure @S781 */ }
            perform action a5 { doc /* reviews performance records for evidence that cybersecurity controls affect operational availability or recovery @S929 */ }
            perform action a6 { doc /* assesses changes that could affect access, communications, or the integrity of operational records @S969 */ }
        }
        part cybersecurityGateway : CybersecurityGateway {
            perform action a0 { doc /* provides a security boundary for connected operational services @S071 */ }
            perform action a1 { doc /* establishes a controlled boundary between authorized shore-side services and offshore operational networks @S111 */ }
            perform action a2 { doc /* blocks a route change when the required authorization is incomplete @S287 */ }
            perform action a3 { doc /* uses the revocation receipt to support access control during routine account and session reviews @S357 */ }
            perform action a4 { doc /* monitors traffic between operational networks and approved external connections @S416 */ }
        }
        part cybersecurityRelatedWorkItem : CybersecurityRelatedWorkItem;
        part daughterCraft : DaughterCraft {
            perform action a0 { doc /* may support offshore work @S045 */ }
            perform action a1 { doc /* can support short-range transfers when the operating plan and conditions permit its use @S088 */ }
            perform action a2 { doc /* may support a local response only when its crew, equipment, and launch conditions are suitable @S621 */ }
        }
        part designatedAuthorizingRole : DesignatedAuthorizingRole {
            perform action a0 { doc /* grants permission @S165 */ }
        }
        part documentOwner : DocumentOwner {
            perform action a0 { doc /* schedules periodic review and initiates an additional review after material operational, technical, or regulatory change @S976 */ }
        }
        part doorInterlocks : DoorInterlocks;
        part dutyPlanner : DutyPlanner {
            perform action a0 { doc /* uses the Maintenance Planning Engine @S065 */ }
            perform action a1 { doc /* prepare and review maintenance activities @S065 */ }
            perform action a2 { doc /* develops daily work priorities with input from the Field Supervisor and the Maintenance Planning Engine @S076 */ }
            perform action a3 { doc /* prepares the Transfer Manifest Addendum to capture approved vessel deployment changes @S126 */ }
            perform action a4 { doc /* reviews the request for completeness and assigns it to the appropriate planning queue @S153 */ }
            perform action a5 { doc /* resolves outstanding supply and scheduling issues @S164 */ }
            perform action a6 { doc /* submitting the request for authorization @S164 */ }
            perform action a7 { doc /* updates work priorities when access conditions or resource availability change @S224 */ }
            perform action a8 { doc /* reviews the ranked queue and confirms that urgent work has a clear technical basis and a feasible execution path @S247 */ }
            perform action a9 { doc /* considers Crew Transfer Vessel, Daughter Craft, Service Operations Vessel, and Helideck access when selecting a mobilization method @S258 */ }
            perform action a10 { doc /* confirms the operating priority @S260 */ }
            perform action a11 { doc /* accounts for part availability, technician competence, and estimated task duration @S263 */ }
            perform action a12 { doc /* committing a work window @S263 */ }
            perform action a13 { doc /* revises priorities when asset condition, access forecasts, or resource availability changes @S269 */ }
            perform action a14 { doc /* communicates the resulting plan to affected teams @S269 */ }
            perform action a15 { doc /* checks that the expected conditions remain within the limits for the task, transfer method, and vessel @S274 */ }
            perform action a16 { doc /* adjusts the executable plan when a delay, cancellation, or alternative access method changes resource demand @S292 */ }
            perform action a17 { doc /* reviews accepted alerts for immediate response needs and for effects on the executable maintenance plan @S304 */ }
            perform action a18 { doc /* submits a defined task scope, work location, crew, and requested operating window for review @S319 */ }
            perform action a19 { doc /* coordinates any revised work window with the relevant operational roles @S334 */ }
            perform action a20 { doc /* closes the work authorization @S340 */ }
            perform action a21 { doc /* considers active dispatch constraints when scheduling work that would reduce generation or access to export equipment @S388 */ }
            perform action a22 { doc /* verifies that planned crew assignments match the approved work schedule before mobilization @S396 */ }
            perform action a23 { doc /* confirms the inspection priority and coordinates access with the Marine Coordinator or the Field Supervisor @S442 */ }
            perform action a24 { doc /* assigns a target repair window and coordinates required personnel, equipment, and vessel capacity @S459 */ }
            perform action a25 { doc /* updates the maintenance record and schedules follow-up inspection when residual uncertainty or defect history warrants it @S464 */ }
            perform action a26 { doc /* compares task readiness with the expected departure window @S469 */ }
            perform action a27 { doc /* committing crews and equipment to a marine campaign @S469 */ }
            perform action a28 { doc /* checks that the planned task matches the approved work authorization and that required personnel and equipment are available @S491 */ }
            perform action a29 { doc /* develops the proposed sequence with the Control Engineer and identifies affected equipment and operating limits @S515 */ }
            perform action a30 { doc /* reassess the sequence and obtain revised authorization @S519 */ }
            perform action a31 { doc /* records the proposed sequence, required approvals, execution roles, and planned communications in the operating record @S527 */ }
            perform action a32 { doc /* authorizes restoration or release of the work area @S536 */ }
            perform action a33 { doc /* records the final equipment state, approvals, deviations, and handover information for the incoming shift @S537 */ }
            perform action a34 { doc /* treats a confirmed restriction as a Grid Constraint until the applicable limit is clarified or withdrawn @S539 */ }
            perform action a35 { doc /* records the revised operating basis and coordinates updated targets @S553 */ }
            perform action a36 { doc /* maintains a clear record of the restriction, response actions, approvals, and outstanding checks for shift handover @S561 */ }
            perform action a37 { doc /* confirms that the recovery task does not conflict with other offshore work @S639 */ }
            perform action a38 { doc /* uses the Visibility Confidence Note when considering task readiness and the conditions that would require a decision to pause or defer work @S669 */ }
            perform action a39 { doc /* reviews forecast demand against current stock @S695 */ }
            perform action a40 { doc /* confirming work readiness @S695 */ }
            perform action a41 { doc /* consolidates proposed work periods and identifies tasks that require a change to substation configuration @S737 */ }
            perform action a42 { doc /* records actual start and finish times to improve future estimates and coordination @S758 */ }
            perform action a43 { doc /* links relevant communications and work records to the applicable work package and operating plan @S779 */ }
            perform action a44 { doc /* confirms that the planned work can proceed within the lift capacity and operating limits @S872 */ }
            perform action a45 { doc /* uses reliability findings to adjust work priorities and planned maintenance intervals when justified @S925 */ }
            perform action a46 { doc /* can prioritize urgent safety work and maintainable generation capacity @S947 */ }
            perform action a47 { doc /* updates operating priorities and deferred work @S955 */ }
            perform action a48 { doc /* checks that maintenance priorities, resource plans, and operational constraints are reflected in planned work @S965 */ }
        }
        part eastServiceLift : EastServiceLift {
            perform action a0 { doc /* runs a door-interlock and overload check @S859 */ }
            perform action a1 { doc /* accepting a movement request @S859 */ }
        }
        part electricalTechnician : ElectricalTechnician {
            perform action a0 { doc /* verifies protective device settings and transfer interlocks during planned maintenance @S185 */ }
            perform action a1 { doc /* identifies the electrical sources, isolation points, and verification steps required by the approved scope @S325 */ }
            perform action a2 { doc /* verifies the relevant local isolation and secures the equipment against unintended energization @S327 */ }
            perform action a3 { doc /* proves the test instrument, tests for absence of voltage, and proves the instrument again where the procedure requires it @S331 */ }
            perform action a4 { doc /* checks that the work area is ready for restoration @S336 */ }
            perform action a5 { doc /* reports any outstanding defects or restrictions @S336 */ }
            perform action a6 { doc /* supports fault diagnosis and maintenance under the applicable work authorization and isolation controls @S363 */ }
            perform action a7 { doc /* coordinate any operational changes with the relevant duty role before implementation @S434 */ }
            perform action a8 { doc /* verifies electrical isolation at the work location before work on electrical equipment begins @S496 */ }
            perform action a9 { doc /* verifies equipment labels and confirms the intended switching points before execution @S529 */ }
            perform action a10 { doc /* isolates and protects recovered electrical equipment before it is placed in temporary storage @S650 */ }
            perform action a11 { doc /* uses the boundary sketch to identify the approved isolation points @S716 */ }
            perform action a12 { doc /* starting the work @S716 */ }
            perform action a13 { doc /* confirms that the work scope and test requirements fit the approved duration @S750 */ }
            perform action a14 { doc /* performs local inspection only after the area has been assessed as safe and the required electrical isolations are in place @S801 */ }
            perform action a15 { doc /* verifies that the lift supply and protective devices show no active fault indication @S867 */ }
        }
        part emergencyGenerator : EmergencyGenerator {
            perform action a0 { doc /* supplies the designated emergency distribution bus @S180 */ }
            perform action a1 { doc /* can start, accept its expected load, and operate for the required test duration @S186 */ }
            perform action a2 { doc /* produces the Start Test Trace during its scheduled functional test @S353 */ }
            perform action a3 { doc /* confirms fuel level, starting battery condition, ventilation, and readiness of the Emergency Generator for loss of normal supply @S354 */ }
            perform action a4 { doc /* supports essential functions when normal electrical supplies are unavailable, subject to its designated load priorities @S803 */ }
        }
        part entrant : Entrant {
            perform action a0 { doc /* presents an individually assigned credential for validation @S839 */ }
        }
        part entryBarrier : EntryBarrier {
            exhibit state modes {
                state s0 { doc /* closed @S846 */ }
            }
        }
        part equipment : Equipment;
        part exportCableMonitor : ExportCableMonitor {
            perform action a0 { doc /* provides measurements that support assessment of the export path @S200 */ }
            perform action a1 { doc /* helps planners assess whether cable condition warrants inspection or corrective intervention @S252 */ }
        }
        part farmMonitoringEnvironment : FarmMonitoringEnvironment;
        part fieldSupervisor : FieldSupervisor {
            perform action a0 { doc /* coordinates task execution offshore @S096 */ }
            perform action a1 { doc /* keeps the Duty Planner informed of changes to work progress @S096 */ }
            perform action a2 { doc /* considers remote observations alongside site conditions @S145 */ }
            perform action a3 { doc /* recommending follow-up work @S145 */ }
            perform action a4 { doc /* verifies that the approved conditions remain valid @S167 */ }
            perform action a5 { doc /* checks reported faults against available evidence and identifies work that requires an offshore visit @S253 */ }
            perform action a6 { doc /* confirms that the proposed method, access arrangements, and work party are suitable for the task @S320 */ }
            perform action a7 { doc /* confirms that the permit is active and the required isolations have been independently verified @S329 */ }
            perform action a8 { doc /* briefs the crew on the permit limits, isolation boundaries, communications, and conditions requiring work to stop @S330 */ }
            perform action a9 { doc /* pause work and reassess the authorization @S333 */ }
            perform action a10 { doc /* confirms that tools, temporary connections, and personnel are clear @S335 */ }
            perform action a11 { doc /* requesting isolation removal @S335 */ }
            perform action a12 { doc /* confirms completion or formally records any remaining work @S340 */ }
            perform action a13 { doc /* confirms the work party is complete before personnel enter the work area @S405 */ }
            perform action a14 { doc /* escalates any unexplained absence or overdue check-in to Marine Coordinator without delay @S412 */ }
            perform action a15 { doc /* checks that cybersecurity requirements are included in the work briefing before technicians begin affected tasks @S429 */ }
            perform action a16 { doc /* uses the Deferred Task Rationale when a cybersecurity-related work item must be postponed @S430 */ }
            perform action a17 { doc /* confirms that close-access findings are documented before personnel leave the work area @S457 */ }
            perform action a18 { doc /* reviews the worksite limits with the crew before anyone enters the controlled area @S493 */ }
            perform action a19 { doc /* verifies each worker's authorization, competence, and fitness for the assigned task @S503 */ }
            perform action a20 { doc /* pauses the job if actual conditions differ from the approved method or the marked worksite boundaries @S509 */ }
            perform action a21 { doc /* confirms personnel are clear of affected equipment @S536 */ }
            perform action a22 { doc /* directs personnel at the affected work site until control is formally transferred @S615 */ }
            perform action a23 { doc /* maintains control of the work area and stops handling if personnel enter a restricted zone @S649 */ }
            perform action a24 { doc /* reports remaining hazards @S660 */ }
            perform action a25 { doc /* confirms that temporary securing arrangements are adequate for transit @S660 */ }
            perform action a26 { doc /* briefs the crew on the boundary, access restrictions, and conditions that require work to stop @S717 */ }
            perform action a27 { doc /* confirms that every crew member understands the limits of the approved work area @S726 */ }
            perform action a28 { doc /* ensures that field observations and work outcomes are entered promptly while the details remain verifiable @S778 */ }
            perform action a29 { doc /* confirms work party status @S809 */ }
            perform action a30 { doc /* reports unresolved personnel or access concerns to the Shore Control Room @S809 */ }
            perform action a31 { doc /* reviews unusual denial patterns and unresolved access exceptions during the work shift @S826 */ }
            perform action a32 { doc /* coordinates the inspection before the first planned movement of each operating shift @S860 */ }
            perform action a33 { doc /* records the inspection result and any observed defects in the maintenance system @S869 */ }
            perform action a34 { doc /* confirms that no person is exposed to a suspended or shifting load during movement @S879 */ }
            perform action a35 { doc /* communicates the release status to the work party and records the time that service is authorized @S881 */ }
            perform action a36 { doc /* confirms that the work authorization covers the intended landing and task @S886 */ }
            perform action a37 { doc /* verifies that the landing is accessible and that the route is clear of obstructions @S887 */ }
            perform action a38 { doc /* ensures that the lift is left secure and that any irregularity is reported through the established site process @S906 */ }
            perform action a39 { doc /* provides feedback on whether revised procedures and controls are practical during offshore work @S927 */ }
            perform action a40 { doc /* confirms that field execution practices and escalation routes are workable for offshore personnel @S970 */ }
        }
        part fieldTeam : FieldTeam {
            perform action a0 { doc /* use the same revision when confirming isolation status @S729 */ }
        }
        part fireDetectionPanel : FireDetectionPanel {
            perform action a0 { doc /* provides alarm indications that responders use alongside direct reports from personnel on site @S629 */ }
            perform action a1 { doc /* supervises detection circuits @S786 */ }
            perform action a2 { doc /* annunciates alarms with location and fault information @S786 */ }
        }
        part fleetDispatchConsole : FleetDispatchConsole {
            perform action a0 { doc /* supports the coordination of operational resources across the farm @S041 */ }
            perform action a1 { doc /* provides a fleet-level view of dispatch activity for operational coordination @S069 */ }
            perform action a2 { doc /* gives the Marine Coordinator a shared view of vessel assignments, planned movements, and dispatch status @S081 */ }
            perform action a3 { doc /* allocates requested farm output among available generating units @S203 */ }
            perform action a4 { doc /* uses the quality flag to support movement planning @S225 */ }
            perform action a5 { doc /* assigns vessel and crew resources to approved work packages @S260 */ }
            perform action a6 { doc /* compares the requested output with available turbine capability and known operating restrictions @S370 */ }
            perform action a7 { doc /* retains the instruction history and the corresponding plant response for later review @S385 */ }
            perform action a8 { doc /* supports coordinated adjustment of turbine output across the affected operating area @S543 */ }
            perform action a9 { doc /* provides a fleet-level view of operating status and response to emerging constraints @S917 */ }
            perform action a10 { doc /* presents operational restrictions @S947 */ }
        }
        part gate : Gate {
            exhibit state modes {
                state s0 { doc /* secured @S816 */ }
            }
        }
        part gridConnectionPoint : GridConnectionPoint;
        part gridDispatcher : GridDispatcher {
            perform action a0 { doc /* sets external dispatch requirements within the applicable connection agreement @S202 */ }
            perform action a1 { doc /* issues active-power targets and ramp instructions through the established dispatch channel @S367 */ }
            perform action a2 { doc /* confirms applicable grid requirements and any restrictions on changing the connection state @S518 */ }
            perform action a3 { doc /* receives the Export Limit Advisory and uses it to set the permitted export level @S541 */ }
            perform action a4 { doc /* confirms that the requested period is compatible with export requirements and network operating limits @S739 */ }
            perform action a5 { doc /* communicates external operating requirements to the Grid Interface Relay and the responsible control personnel @S769 */ }
        }
        part gridInterfaceRelay : GridInterfaceRelay {
            perform action a0 { doc /* provides status indications that support assessment of the normal supply and its protective state @S190 */ }
            perform action a1 { doc /* exchanges authorized operating signals with the transmission system at the agreed interface @S201 */ }
            perform action a2 { doc /* maintains the farm's dispatch boundary while allowing local systems to manage turbine-level operation @S221 */ }
            perform action a3 { doc /* produces an Export Limit Advisory when available export capability falls below the active dispatch target @S372 */ }
            perform action a4 { doc /* applies the accepted export ceiling to control outputs and records its effective time for audit @S373 */ }
            perform action a5 { doc /* retains its protection settings unless an authorized switching plan requires a controlled change @S551 */ }
            perform action a6 { doc /* applies the configured response to a Grid Constraint @S942 */ }
        }
        part hSEOfficer : HSEOfficer {
            perform action a0 { doc /* verifies that work arrangements account for applicable safety controls and personnel responsibilities @S095 */ }
            perform action a1 { doc /* reviews the proposed controls when the task presents a material personnel or environmental risk @S157 */ }
            perform action a2 { doc /* produces the Harness Audit Card before the applicable transfer activity @S237 */ }
            perform action a3 { doc /* reviews hazards and confirms that proposed controls match the task scope and site conditions @S266 */ }
            perform action a4 { doc /* reviews task hazards and confirms that required controls are assigned @S322 */ }
            perform action a5 { doc /* verifies that personnel expected at the work site are accounted for during scheduled checks @S408 */ }
            perform action a6 { doc /* reviews the work method, exposure controls, and emergency arrangements before personnel approach the rotor @S451 */ }
            perform action a7 { doc /* checks that access controls, emergency arrangements, and handling precautions are suitable for the planned activity @S481 */ }
            perform action a8 { doc /* checks that emergency routes, muster points, and rescue arrangements are understood by everyone at the worksite @S505 */ }
            perform action a9 { doc /* reviews task hazards and confirms that required controls are in place before switching is authorized @S526 */ }
            perform action a10 { doc /* assesses any safety implications and advises whether the affected activity can continue @S579 */ }
            perform action a11 { doc /* advises on personnel hazards, rescue procedures, and the use of emergency equipment @S617 */ }
            perform action a12 { doc /* reviews the handling method, lifting points, and exclusion zones before loads are moved @S647 */ }
            perform action a13 { doc /* advises on exposure, evacuation, and re-entry criteria in coordination with the incident response team @S808 */ }
            perform action a14 { doc /* can use the recorded entry history to support personnel accountability during an incident @S827 */ }
            perform action a15 { doc /* reviews any proposed workaround that changes established access, isolation, or personnel-control arrangements @S949 */ }
            perform action a16 { doc /* evaluates safety controls, emergency arrangements, and lessons from reported events @S967 */ }
        }
        part incidentLead : IncidentLead {
            perform action a0 { doc /* classifies each report, assigns an owner, and records its time, scope, and current status @S432 */ }
            perform action a1 { doc /* confirms that the threat is contained and the affected system is suitable for return to service @S436 */ }
            perform action a2 { doc /* verifies headcounts with the teams involved @S619 */ }
        }
        part incomingTeam : IncomingTeam {
            perform action a0 { doc /* independently checks the boundary status @S731 */ }
            perform action a1 { doc /* accepting responsibility for ongoing work @S731 */ }
        }
        part inspector : Inspector {
            perform action a0 { doc /* confirms that the car floor and landing thresholds are clear of loose material and standing water @S862 */ }
            perform action a1 { doc /* checks the operating controls for damage, legibility, and secure mounting @S865 */ }
            perform action a2 { doc /* confirms that the rated capacity and operating instructions remain legible at the car entrance @S868 */ }
        }
        part installationTeam : InstallationTeam {
            perform action a0 { doc /* verifies the scanner, barrier, and communications before the route is placed in service @S853 */ }
        }
        part lighting : Lighting;
        part localVisualIndicator : LocalVisualIndicator {
            perform action a0 { doc /* communicates whether entry is permitted or denied @S845 */ }
        }
        part mainTransformer : MainTransformer;
        part maintenanceActivities : MaintenanceActivities;
        part maintenancePlanningEngine : MaintenancePlanningEngine {
            perform action a0 { doc /* supports the preparation and sequencing of maintenance activities @S042 */ }
            perform action a1 { doc /* supports work preparation @S054 */ }
            perform action a2 { doc /* organizing maintenance needs, resource considerations, and planning constraints @S054 */ }
            perform action a3 { doc /* supports planning decisions without replacing the judgment of the Duty Planner @S066 */ }
            perform action a4 { doc /* can use reviewed condition information when prioritizing future maintenance activities @S148 */ }
            perform action a5 { doc /* can use reviewed condition information when prioritizing future maintenance activities @S154 */ }
            perform action a6 { doc /* schedules inspections and corrective work using equipment condition and operating history @S188 */ }
            perform action a7 { doc /* schedules periodic reviews of standby electrical maintenance requirements and outstanding corrective work @S195 */ }
            perform action a8 { doc /* uses the Squall Window Bulletin when reviewing the timing of planned work @S213 */ }
            perform action a9 { doc /* ranks planned and corrective work using asset condition, safety exposure, production impact, access feasibility, and resource availability @S246 */ }
            perform action a10 { doc /* produces the Deferred Task Rationale when weather prevents a planned task from proceeding @S285 */ }
            perform action a11 { doc /* receives validated condition information for prioritization and scheduling of follow-up work @S308 */ }
            perform action a12 { doc /* combines inspection intervals, prior defect history, and turbine availability to propose survey dates @S441 */ }
            perform action a13 { doc /* uses the assessed severity, defect growth rate, weather exposure, and production impact to support repair prioritization @S458 */ }
            perform action a14 { doc /* supports this review by presenting task duration, resource demand, and dependency status @S470 */ }
            perform action a15 { doc /* provides the planned work period and identifies dependencies with other scheduled tasks @S520 */ }
            perform action a16 { doc /* can help identify tasks that may be rescheduled when visibility is uncertain @S670 */ }
            perform action a17 { doc /* uses planned work demand and part criticality to support replenishment forecasts @S694 */ }
            perform action a18 { doc /* checks task durations, dependencies, and resource assumptions before a window is proposed @S738 */ }
            perform action a19 { doc /* supports review of planned work, resource demand, and maintenance completion performance @S918 */ }
            perform action a20 { doc /* separates safety-critical work from tasks that can safely wait until normal access and support are available @S948 */ }
        }
        part marineCoordinator : MarineCoordinator {
            perform action a0 { doc /* considers offshore conditions and vessel availability @S068 */ }
            perform action a1 { doc /* coordinating access to work sites @S068 */ }
            perform action a2 { doc /* aligns vessel availability with crew readiness, port access, and the planned work locations @S077 */ }
            perform action a3 { doc /* uses that view to coordinate the Crew Transfer Vessel, the Service Operations Vessel, and the Daughter Craft as conditions require @S082 */ }
            perform action a4 { doc /* uses the available traffic picture to support coordination of offshore movements @S141 */ }
            perform action a5 { doc /* checks that the planned access method and timing are practical for the work location @S160 */ }
            perform action a6 { doc /* maintains the daily marine plan and resolves conflicts between planned activities @S223 */ }
            perform action a7 { doc /* records changes to the movement plan and ensures that affected teams receive the update @S245 */ }
            perform action a8 { doc /* compares expected access conditions with vessel capability, transit time, and worksite limits @S257 */ }
            perform action a9 { doc /* coordinates resource changes with the Vessel Master and affected work teams @S261 */ }
            perform action a10 { doc /* reviews access options and vessel availability when a work window narrows @S277 */ }
            perform action a11 { doc /* reassesses the route when wind direction, wave conditions, or visibility changes materially @S283 */ }
            perform action a12 { doc /* seeks an updated forecast @S290 */ }
            perform action a13 { doc /* confirming a departure or transfer plan @S290 */ }
            perform action a14 { doc /* reviews the intended crew movement against vessel capacity and operating conditions @S397 */ }
            perform action a15 { doc /* monitors reported vessel movements during transit to offshore locations @S400 */ }
            perform action a16 { doc /* reviews return movements so that shore personnel can anticipate vessel arrivals @S410 */ }
            perform action a17 { doc /* maintains a rolling view of berth occupancy, planned arrivals, departure estimates, and vessel service requirements @S466 */ }
            perform action a18 { doc /* uses the Berth Slot Confirmation to align an approved vessel arrival with the assigned berth window @S473 */ }
            perform action a19 { doc /* resolves competing berth requests by considering task urgency, vessel compatibility, and the consequences of delay @S483 */ }
            perform action a20 { doc /* reviews safe alternatives such as a later slot, a different suitable berth, or vessel standby @S488 */ }
            perform action a21 { doc /* suspends access when sea or weather conditions make transfer unsafe @S499 */ }
            perform action a22 { doc /* aligns vessel movements with the approved access plan and operational constraints @S523 */ }
            perform action a23 { doc /* establishes the expected personnel count and destination for each movement before transfer begins @S565 */ }
            perform action a24 { doc /* pauses further personnel transfers when a discrepancy is identified @S576 */ }
            perform action a25 { doc /* informs the Shore Control Room of the discrepancy and the immediate control actions @S578 */ }
            perform action a26 { doc /* escalates any unresolved discrepancy to the Duty Planner and records the time of escalation @S583 */ }
            perform action a27 { doc /* confirms that the count is reconciled or an authorized response is in place @S585 */ }
            perform action a28 { doc /* maintains awareness of vessel locations, access constraints, and available marine support @S618 */ }
            perform action a29 { doc /* assigns suitable vessels and maintains a common plan for their approach and departure @S638 */ }
            perform action a30 { doc /* pauses the recovery and agrees a safe holding position with the Vessel Master @S659 */ }
            perform action a31 { doc /* reviews how uncertainty affects the planned transit, transfer location, and available alternatives @S676 */ }
            perform action a32 { doc /* reassess the route and the suitability of continuing toward the work site @S682 */ }
            perform action a33 { doc /* checks vessel movements and crew transfer timing against the proposed period @S749 */ }
            perform action a34 { doc /* shares relevant marine and weather information with vessel personnel and the Duty Planner @S764 */ }
            perform action a35 { doc /* confirm that personnel and vessels can remain safely accounted for during an extended interruption @S944 */ }
            perform action a36 { doc /* reviews vessel coordination arrangements and verifies that marine responsibilities are understood @S966 */ }
        }
        part metoceanBuoy : MetoceanBuoy {
            perform action a0 { doc /* measures wind speed and direction, wave height and period, current, air temperature, and barometric pressure @S102 */ }
            perform action a1 { doc /* produces the Wave Burst Record at the configured sampling interval @S194 */ }
            perform action a2 { doc /* reports local sea conditions for use in access planning @S231 */ }
            perform action a3 { doc /* provide contextual conditions that help reviewers distinguish environmental effects from equipment deterioration @S309 */ }
            perform action a4 { doc /* provide forecasts and measured conditions for assessing whether remote or close-access work is safe @S443 */ }
            perform action a5 { doc /* provides site measurements that help assess whether a planned response remains feasible @S625 */ }
            perform action a6 { doc /* provides a local reference that can help identify differences between forecast conditions and conditions at sea @S665 */ }
            perform action a7 { doc /* provide inputs that are reviewed alongside direct observations from offshore personnel @S766 */ }
        }
        part monitoringProcess : MonitoringProcess {
            perform action a0 { doc /* retains the source, timestamp, and turbine identifier for each observation so that abnormal readings can be traced to their origin @S296 */ }
        }
        part nacelleConditionMonitor : NacelleConditionMonitor {
            perform action a0 { doc /* provides equipment measurements for ongoing assessment of turbine health @S132 */ }
            perform action a1 { doc /* provides condition data that helps distinguish developing degradation from transient alarms @S250 */ }
            perform action a2 { doc /* provides condition information that can help distinguish a developing equipment fault from a confirmed fire alarm @S793 */ }
            perform action a3 { doc /* supports assessment of equipment condition and emerging degradation @S915 */ }
        }
        part northAccessScanner : NorthAccessScanner {
            perform action a0 { doc /* records authorized entry at the north access point @S235 */ }
            perform action a1 { doc /* records identity checks at the north shore access point @S394 */ }
            perform action a2 { doc /* records personnel access events at the north access point @S569 */ }
            perform action a3 { doc /* validates each presented credential against current access authorization @S810 */ }
            perform action a4 { doc /* enabling controlled entry @S810 */ }
            perform action a5 { doc /* accepts only credentials that can be read reliably and associated with an identifiable person @S811 */ }
            perform action a6 { doc /* checks that the authorization is active for the scheduled work period @S813 */ }
            perform action a7 { doc /* displays a clear outcome without exposing unnecessary personal information to people nearby @S831 */ }
        }
        part occupants : Occupants {
            perform action a0 { doc /* remain inside the car and avoid interfering with the controls or doors @S899 */ }
            perform action a1 { doc /* use the designated alarm or communication method and remain inside the car @S902 */ }
            perform action a2 { doc /* exit without crowding @S905 */ }
        }
        part offshorePersonnel : OffshorePersonnel {
            perform action a0 { doc /* follow posted escape routes and muster at the designated assembly point when evacuation is ordered @S804 */ }
        }
        part offshoreSubstation : OffshoreSubstation {
            perform action a0 { doc /* provides the farm's offshore electrical collection and switching environment @S037 */ }
            perform action a1 { doc /* maintains the designated emergency distribution bus within its approved operating limits @S189 */ }
            perform action a2 { doc /* sends a Transformer Tap Snapshot when a transformer condition review is requested @S267 */ }
            perform action a3 { doc /* uses the Switching Window Acknowledgment to confirm that the approved switching window is available for the planned work @S752 */ }
            perform action a4 { doc /* enters Substation Degraded when a protection, auxiliary supply, or monitoring impairment limits safe switching or export capability @S941 */ }
            exhibit state modes {
                state s0 { doc /* Substation Degraded @S361 */ }
            }
        }
        part offshoreSubstationOperator : OffshoreSubstationOperator {
            perform action a0 { doc /* confirms that export equipment remains within its approved operating range @S549 */ }
        }
        part offshoreSupportFacilities : OffshoreSupportFacilities;
        part offshoreWindFarm : OffshoreWindFarm {
            perform action a0 { doc /* operates in a variable marine environment @S028 */ }
            perform action a1 { doc /* exports electrical power through the Offshore Substation, Main Transformer, and export cable to the designated grid connection point @S199 */ }
            perform action a2 { doc /* reports measured active power at the grid boundary for operational monitoring and settlement processes @S205 */ }
        }
        part offshoreWindFarmOperationsAndMaintenanceSystem : OffshoreWindFarmOperationsAndMaintenanceSystem {
            perform action a0 { doc /* raises an alarm @S183 */ }
            perform action a1 { doc /* maintains any available uninterruptible control power @S183 */ }
            perform action a2 { doc /* retains successful and unsuccessful attempts under the site's access record retention policy @S824 */ }
            perform action a3 { doc /* measures operational performance against approved service objectives and documented fleet baselines @S908 */ }
            perform action a4 { doc /* records the affected function, the detected condition, and the time of transition so that operators can assess the scope and duration of the impairment @S935 */ }
            perform action a5 { doc /* retains the event record and recovery decisions for review, trend analysis, and improvement of operating procedures @S957 */ }
        }
        part onboardLogger : OnboardLogger {
            perform action a0 { doc /* timestamps observations and retains a local history during intermittent communications @S104 */ }
        }
        part operatingOrganization : OperatingOrganization {
            perform action a0 { doc /* uses defined handoffs so that dispatch, marine judgment, work supervision, and stores control remain accountable functions @S098 */ }
        }
        part operationalPersonnel : OperationalPersonnel {
            perform action a0 { doc /* rely on remote indications @S349 */ }
        }
        part operationsRadioConsole : OperationsRadioConsole {
            perform action a0 { doc /* supports routine communications and escalation during offshore activity @S239 */ }
            perform action a1 { doc /* supports communications between the Shore Control Room, vessels, and offshore work teams @S627 */ }
            perform action a2 { doc /* supports voice communication with the Crew Transfer Vessel, Service Operations Vessel, and Daughter Craft when they are within radio coverage @S762 */ }
            perform action a3 { doc /* provides a coordinated communications channel for response instructions and status reports @S806 */ }
        }
        part operationsTeam : OperationsTeam;
        part operators : Operators {
            perform action a0 { doc /* use the approved recovery procedure @S184 */ }
            perform action a1 { doc /* assess the fault, preserve essential services, and restore the normal supply when it is safe to do so @S184 */ }
            perform action a2 { doc /* verify the scanner clock and connectivity during routine readiness checks @S832 */ }
        }
        part organization : Organization {
            perform action a0 { doc /* retains voice recordings, system logs, and work records according to the approved retention schedule and applicable legal obligations @S782 */ }
        }
        part outgoingSupervisor : OutgoingSupervisor {
            perform action a0 { doc /* briefs the incoming supervisor on site conditions, access status, and outstanding hazards @S512 */ }
        }
        part passengers : Passengers {
            perform action a0 { doc /* distribute themselves and their equipment to avoid obstructing the doors or control panel @S896 */ }
        }
        part permitReviewers : PermitReviewers;
        part person : Person {
            perform action a0 { doc /* presents the credential at the controlled entry point and waits for the scanner response @S812 */ }
            perform action a1 { doc /* contact the Field Supervisor or the HSE Officer for review @S817 */ }
        }
        part personnel : Personnel {
            perform action a0 { doc /* confirm their identity @S393 */ }
            perform action a1 { doc /* entering controlled shore access areas @S393 */ }
            perform action a2 { doc /* report any change in destination or transfer plan to the Vessel Master as soon as practicable @S402 */ }
            perform action a3 { doc /* report their arrival and departure at each active work location using the approved site process @S406 */ }
            perform action a4 { doc /* report suspected compromise, lost credentials, and unexplained equipment behavior promptly through the established operations channel @S431 */ }
            perform action a5 { doc /* use the North Access Scanner or South Access Scanner at the designated entry point @S501 */ }
            perform action a6 { doc /* use the approved fallback method @S771 */ }
            perform action a7 { doc /* report the outage as soon as practicable @S771 */ }
            perform action a8 { doc /* follow the approved contingency process rather than bypassing the gate @S828 */ }
            perform action a9 { doc /* not hold the barrier open for another entrant @S847 */ }
            perform action a10 { doc /* use an approved alternative entry process rather than an uncontrolled bypass @S856 */ }
            perform action a11 { doc /* do not attempt to open doors or climb out of a stopped car without direction from the response team @S903 */ }
            perform action a12 { doc /* receive appropriate communication or training before the change takes effect @S981 */ }
        }
        part personnelTrackingConsole : PersonnelTrackingConsole {
            perform action a0 { doc /* helps the organization maintain an accurate view of personnel assigned to offshore activities @S094 */ }
            perform action a1 { doc /* maintains the offshore personnel roster and expected return times @S234 */ }
            perform action a2 { doc /* supports confirmation that personnel assigned to the task are accounted for at the work location @S332 */ }
            perform action a3 { doc /* maintains the current accountability status for personnel assigned to offshore work @S392 */ }
            perform action a4 { doc /* maintains the operational count for active marine movements @S571 */ }
            perform action a5 { doc /* update a verified personnel total @S573 */ }
            perform action a6 { doc /* supports personnel accounting @S619 */ }
            perform action a7 { doc /* supports confirmation that all assigned personnel have returned to a safe location @S648 */ }
            perform action a8 { doc /* supports accountability checks for personnel assigned to the affected work area @S805 */ }
        }
        part pitchSystem : PitchSystem {
            perform action a0 { doc /* changes blade angle in response to turbine control commands and local protection logic @S130 */ }
            perform action a1 { doc /* adjusts blade angle within its operating envelope and does not override local protection limits @S546 */ }
            perform action a2 { doc /* moves the blades to the defined safe position when commanded during an emergency shutdown @S790 */ }
        }
        part portAgent : PortAgent {
            perform action a0 { doc /* supports shore-side arrangements for vessel calls, crew access, and staged cargo @S093 */ }
            perform action a1 { doc /* coordinates port services and confirms that planned departures can be supported @S240 */ }
            perform action a2 { doc /* issues the Berth Slot Confirmation for the planned work period @S324 */ }
        }
        part protectiveDevices : ProtectiveDevices;
        part qualifiedTechnician : QualifiedTechnician {
            perform action a0 { doc /* checks the device at the point of isolation @S719 */ }
        }
        part receiver : Receiver {
            perform action a0 { doc /* repeats critical details @S773 */ }
        }
        part requester : Requester {
            perform action a0 { doc /* identifies the equipment affected and describes the intended work in terms that can be checked against operating constraints @S152 */ }
        }
        part rescueCoordinator : RescueCoordinator {
            perform action a0 { doc /* maintains the response arrangements for incidents involving vessels or personnel @S244 */ }
            perform action a1 { doc /* leads rescue planning and coordinates requests for external assistance @S614 */ }
            perform action a2 { doc /* revises the response plan @S634 */ }
            perform action a3 { doc /* establishes the recovery objective and confirms who has authority to suspend the operation @S637 */ }
            perform action a4 { doc /* uses the load sheet to confirm that recovery baskets are secured and their contents are accounted for before transfer @S646 */ }
        }
        part responsibleControlPersonnel : ResponsibleControlPersonnel;
        part responsibleManager : ResponsibleManager {
            perform action a0 { doc /* reviews record completeness after significant events and assigns correction or follow-up actions where evidence is missing @S784 */ }
        }
        part responsibleSupervisor : ResponsibleSupervisor {
            perform action a0 { doc /* keeps a local record @S413 */ }
            perform action a1 { doc /* reports it when service is restored @S413 */ }
        }
        part responsibleTeam : ResponsibleTeam {
            perform action a0 { doc /* reports completion status and outstanding issues @S170 */ }
            perform action a1 { doc /* verifies turbine isolation, rotor restraint, access arrangements, and rescue provisions @S450 */ }
        }
        part reviewTeams : ReviewTeams {
            perform action a0 { doc /* distinguish equipment faults from external causes such as access limitations, weather conditions, and grid restrictions @S922 */ }
        }
        part reviewers : Reviewers {
            perform action a0 { doc /* assess safety effects, cybersecurity risks, interfaces, and the impact on ongoing maintenance activities @S596 */ }
        }
        part rotorBrakeUnit : RotorBrakeUnit {
            perform action a0 { doc /* applies braking only in accordance with the turbine protection sequence and operating limits @S791 */ }
        }
        part sCADAEngineer : SCADAEngineer {
            perform action a0 { doc /* maintains the configuration and technical integrity of supervisory interfaces @S062 */ }
            perform action a1 { doc /* use individually assigned accounts rather than shared credentials for interactive work @S423 */ }
            perform action a2 { doc /* validates restored configurations and communications before normal monitoring responsibilities resume @S437 */ }
            perform action a3 { doc /* investigates telemetry gaps or inconsistent measurements before the team relies on them for control decisions @S558 */ }
            perform action a4 { doc /* uses the Firmware Hash Attestation to verify the approved image @S593 */ }
            perform action a5 { doc /* loading a release @S593 */ }
            perform action a6 { doc /* investigates missing or inconsistent indications @S946 */ }
            perform action a7 { doc /* verifies that status, alarms, and command feedback are consistent across the available control views @S954 */ }
            perform action a8 { doc /* reviews monitoring and control assumptions that affect operational decisions @S968 */ }
        }
        part sCADAGateway : SCADAGateway {
            perform action a0 { doc /* provides a controlled boundary for supervisory data exchange between offshore assets and shore-based operations @S052 */ }
            perform action a1 { doc /* mediates supervisory exchanges @S059 */ }
            perform action a2 { doc /* supports consistent access to operational information @S059 */ }
            perform action a3 { doc /* presents turbine status and control availability to authorized shore personnel @S133 */ }
            perform action a4 { doc /* uses the deviation notice to flag work packages that may require technical review @S159 */ }
            perform action a5 { doc /* provide current operational status to permit reviewers when requested as part of the authorization check @S171 */ }
            perform action a6 { doc /* presents supply alarms and generator status to the Shore Control Room for remote awareness @S192 */ }
            perform action a7 { doc /* provides relay status and interface measurements to the farm monitoring environment @S211 */ }
            perform action a8 { doc /* produces the Session Revocation Receipt when an authenticated control session is terminated @S212 */ }
            perform action a9 { doc /* forwards time-stamped observations to the Shore Control Room for review against configured operating limits @S295 */ }
            perform action a10 { doc /* provides the operational measurements used to track delivered power and instruction response @S369 */ }
            perform action a11 { doc /* records security-relevant access and control events for review @S417 */ }
            perform action a12 { doc /* provides operating data that helps distinguish persistent defects from transient changes in blade appearance @S447 */ }
            perform action a13 { doc /* presents current generation, export, and equipment status to the operations team @S540 */ }
            perform action a14 { doc /* carries operational data to the Shore Control Room and preserves source timestamps where available @S767 */ }
            perform action a15 { doc /* supports alarm visibility at the shore operating position without replacing local emergency controls @S800 */ }
            perform action a16 { doc /* provides operational records used to assess turbine availability and production trends @S914 */ }
            perform action a17 { doc /* preserves available status and alarm information @S946 */ }
        }
        part sender : Sender {
            perform action a0 { doc /* confirms that the read-back is accurate @S773 */ }
        }
        part serviceOperationsVessel : ServiceOperationsVessel {
            perform action a0 { doc /* may support offshore work @S045 */ }
            perform action a1 { doc /* provides a platform for work that needs longer offshore presence or broader onboard support @S089 */ }
            perform action a2 { doc /* provides a stable offshore base when the work plan requires extended support @S228 */ }
            perform action a3 { doc /* may provide a more stable work platform @S281 */ }
            perform action a4 { doc /* prepares the Recovery Basket Load Sheet for the planned work activity @S461 */ }
            perform action a5 { doc /* may provide accommodation, medical support, and a stable platform when its position and capability permit @S622 */ }
            perform action a6 { doc /* provides a stable working platform when the response requires additional deck space or lifting capability @S645 */ }
            perform action a7 { doc /* may maintain a safe stand-off while the visibility assessment is clarified @S680 */ }
        }
        part shiftRecords : ShiftRecords {
            perform action a0 { doc /* capture inspections, alarms, tests, switching actions, defects, and handover items so that decisions remain traceable @S365 */ }
            perform action a1 { doc /* capture dispatch instructions, constraint decisions, measured response, and unresolved follow-up actions @S389 */ }
        }
        part shoreControlRoom : ShoreControlRoom {
            perform action a0 { doc /* provides a shore-based operating location for authorized personnel @S040 */ }
            perform action a1 { doc /* provides a shared operational context for personnel responsible for offshore assets @S064 */ }
            perform action a2 { doc /* maintains operational oversight and provides a point of coordination for shore-based personnel @S097 */ }
            perform action a3 { doc /* maintains operational oversight and provides a point of coordination for shore-based personnel @S099 */ }
            perform action a4 { doc /* provides a staffed location for supervisory control and operational review @S134 */ }
            perform action a5 { doc /* coordinates operational notices and control-room decisions affecting the farm interface @S214 */ }
            perform action a6 { doc /* maintains an overview of active marine operations and operational restrictions @S238 */ }
            perform action a7 { doc /* escalates an alert when its severity exceeds the operating threshold or when the evidence indicates a developing hazard @S303 */ }
            perform action a8 { doc /* retains the decision record, supporting observations, and response outcome for operational review @S317 */ }
            perform action a9 { doc /* retains the permit status, isolation history, test results, and restoration decision for operational review @S339 */ }
            perform action a10 { doc /* receives concise status updates, including operating limitations and the expected time of the next review @S364 */ }
            perform action a11 { doc /* maintains the current dispatch target, ramp rate, and next review time in the shift record @S371 */ }
            perform action a12 { doc /* uses the tap snapshot to check the recorded transformer position during export reviews @S374 */ }
            perform action a13 { doc /* maintains the last validated operating limit while seeking clarification through the approved channel @S386 */ }
            perform action a14 { doc /* maintains an operational view of affected systems and coordinates immediate protective actions @S420 */ }
            perform action a15 { doc /* monitors turbine status and records any operating restrictions required during the remote survey @S448 */ }
            perform action a16 { doc /* sends the Switching Window Acknowledgment @S531 */ }
            perform action a17 { doc /* confirms that monitoring and operator procedures remain suitable for the revised configuration @S606 */ }
            perform action a18 { doc /* maintains the incident log and provides a single operational point of contact for offshore teams @S613 */ }
            perform action a19 { doc /* maintains awareness of the decision and the operational restrictions associated with the assessment @S683 */ }
            perform action a20 { doc /* assesses incoming alarms, confirms the affected asset, and initiates the response appropriate to the reported severity @S798 */ }
            perform action a21 { doc /* monitors the loss of visibility @S937 */ }
            perform action a22 { doc /* applies the approved operating concept during routine operations and abnormal conditions @S963 */ }
        }
        part southAccessScanner : SouthAccessScanner {
            perform action a0 { doc /* records authorized entry at the south access point @S236 */ }
            perform action a1 { doc /* records identity checks at the south shore access point @S395 */ }
            perform action a2 { doc /* records personnel access events at the south access point @S570 */ }
            perform action a3 { doc /* serves the designated southern entry route to the offshore wind farm @S835 */ }
            perform action a4 { doc /* applies the same identity verification standard used at other controlled entry points @S838 */ }
            perform action a5 { doc /* checks that the credential is active and belongs to the person presenting it @S840 */ }
            perform action a6 { doc /* records each successful entry and each denied attempt with a time reference @S843 */ }
        }
        part sparesHub : SparesHub {
            perform action a0 { doc /* provides a separate view of stock held for regional replenishment and emergency support @S689 */ }
        }
        part stationServiceTransformers : StationServiceTransformers {
            perform action a0 { doc /* supply the facility's auxiliary electrical loads from the medium-voltage collection system @S173 */ }
        }
        part storekeeper : Storekeeper {
            perform action a0 { doc /* checks requested materials against available stock @S092 */ }
            perform action a1 { doc /* coordinates replenishment with the Spares Hub @S092 */ }
            perform action a2 { doc /* prepares requested equipment for dispatch in accordance with the approved work plan @S242 */ }
            perform action a3 { doc /* uses the exception slip to validate an unavailable part @S262 */ }
            perform action a4 { doc /* checks repair materials and tooling against the approved repair method before mobilization @S460 */ }
            perform action a5 { doc /* checks that critical spares are available and that packaging is suitable for marine transport @S479 */ }
            perform action a6 { doc /* reconciles physical counts with recorded balances and records adjustments with a reason and timestamp @S690 */ }
            perform action a7 { doc /* records unavailable quantities and the expected date of the next supply without presenting them as available stock @S703 */ }
            perform action a8 { doc /* confirms that equipment intended for the lift is ready and properly identified for the work party @S876 */ }
        }
        part substationOperator : SubstationOperator {
            perform action a0 { doc /* confirms that switching actions affecting the export path are within the authorized work scope @S216 */ }
            perform action a1 { doc /* confirms local operating constraints @S268 */ }
            perform action a2 { doc /* applies authorized switching actions and records the resulting equipment state @S326 */ }
            perform action a3 { doc /* removes isolations only under the approved switching process and records each restoration action @S337 */ }
            perform action a4 { doc /* maintains the Offshore Substation within approved operating limits and follows current switching instructions @S342 */ }
            perform action a5 { doc /* reviews alarms, active restrictions, equipment status, and handover notes @S343 */ }
            perform action a6 { doc /* coordinates switching activity that could alter the available export configuration @S382 */ }
            perform action a7 { doc /* confirms that switching conditions affecting the worksite are understood by the relevant personnel @S497 */ }
            perform action a8 { doc /* verifies equipment status and switching points at the Offshore Substation @S517 */ }
            perform action a9 { doc /* checking the equipment state and confirming authorization with the Control Engineer @S530 */ }
            perform action a10 { doc /* accepts the instructions @S530 */ }
            perform action a11 { doc /* uses the test trace to verify that the planned restoration checks have completed @S532 */ }
            perform action a12 { doc /* requesting the next switching step @S532 */ }
            perform action a13 { doc /* reports any substation limitation that could require a lower export target or local equipment action @S559 */ }
            perform action a14 { doc /* reviews the switching sequence and confirms that each step can be performed within the available interval @S741 */ }
            perform action a15 { doc /* does not begin switching until the window is active and operational authority has been confirmed @S753 */ }
            perform action a16 { doc /* reviews responsibilities and coordination arrangements for substation activities @S971 */ }
        }
        part switchingOperator : SwitchingOperator {
            perform action a0 { doc /* performs each authorized action @S533 */ }
            perform action a1 { doc /* reports completion @S533 */ }
        }
        part team : Team {
            perform action a0 { doc /* checks current observations and the task-specific limits @S280 */ }
            perform action a1 { doc /* considers forecast uncertainty when deciding whether to commit crews, fuel, and vessel time to a remote work site @S289 */ }
        }
        part technicalReviewers : TechnicalReviewers {
            perform action a0 { doc /* confirm that the work scope is compatible with equipment condition and the planned maintenance method @S158 */ }
        }
        part technicalTeams : TechnicalTeams {
            perform action a0 { doc /* isolate only the affected connection or service where this can be done without creating an unsafe operating condition @S433 */ }
            perform action a1 { doc /* review causes, response effectiveness, and corrective actions with operations management @S439 */ }
        }
        part temporaryPersonnel : TemporaryPersonnel {
            perform action a0 { doc /* follow the same identity checks as other entrants @S849 */ }
        }
        part transaction : Transaction {
            perform action a0 { doc /* records the credential identifier, decision time, access point, and decision outcome @S821 */ }
            perform action a1 { doc /* records the authorization version and the rule that determined the outcome @S822 */ }
        }
        part transmissionSystem : TransmissionSystem;
        part turbineController : TurbineController {
            perform action a0 { doc /* performs local turbine control functions within the offshore equipment environment @S060 */ }
            perform action a1 { doc /* produces the Pitch Deviation Notice for operational handling @S061 */ }
            perform action a2 { doc /* adjusts turbine output within approved operating limits @S127 */ }
            perform action a3 { doc /* blocks commands that conflict with active protection conditions @S127 */ }
            perform action a4 { doc /* executes authorized control actions @S129 */ }
            perform action a5 { doc /* reports its operating state through established control interfaces @S129 */ }
            perform action a6 { doc /* enters its configured safe operating mode when required auxiliary services are unavailable @S191 */ }
            perform action a7 { doc /* adjusts output in accordance with validated plant commands and local equipment protections @S377 */ }
            perform action a8 { doc /* applies the accepted output target while retaining its protective control functions @S545 */ }
            perform action a9 { doc /* initiates the configured shutdown response when a confirmed fire condition requires turbine protection @S789 */ }
            perform action a10 { doc /* retains protective control locally when the supervisory connection is unavailable @S937 */ }
            exhibit state modes {
                state s0 { doc /* configured safe operating mode @S191 */ }
            }
        }
        part turbineLockout : TurbineLockout {
            perform action a0 { doc /* prevents remote restart while personnel investigate a fire alarm or complete post-event checks @S802 */ }
        }
        part turbineSensorBus : TurbineSensorBus {
            perform action a0 { doc /* provides operating measurements for work that depends on recent machine behavior @S251 */ }
            perform action a1 { doc /* collects operating measurements from the Turbine Controller, Pitch System, Converter Cabinet, and Nacelle Condition Monitor @S294 */ }
            perform action a2 { doc /* carries equipment status used by protective functions and operational monitoring @S788 */ }
        }
        part turbineStructures : TurbineStructures;
        part turbines : Turbines;
        part users : Users {
            perform action a0 { doc /* report unusual noise, vibration, door behavior, or control response immediately @S882 */ }
        }
        part vesselAISReceiver : VesselAISReceiver {
            perform action a0 { doc /* produces a Position Quality Flag when position integrity checks fail or confidence falls below its configured threshold @S105 */ }
            perform action a1 { doc /* collects vessel position broadcasts to support marine traffic awareness @S139 */ }
            perform action a2 { doc /* maintains a time-stamped view of nearby vessel movements when broadcast coverage is available @S140 */ }
            perform action a3 { doc /* provides vessel position information for review against the planned route and operating area @S288 */ }
            perform action a4 { doc /* provides vessel position information for movement monitoring @S401 */ }
        }
        part vesselMaster : VesselMaster {
            perform action a0 { doc /* retains authority for navigation, vessel safety, and decisions about whether a transfer can proceed @S079 */ }
            perform action a1 { doc /* evaluates local conditions before departure @S085 */ }
            perform action a2 { doc /* continues to reassess them during the voyage @S085 */ }
            perform action a3 { doc /* confirms that the vessel plan can support the approved personnel and equipment transfer @S161 */ }
            perform action a4 { doc /* confirms departure readiness @S226 */ }
            perform action a5 { doc /* reports any change that could affect the passage @S226 */ }
            perform action a6 { doc /* receives the Transfer Manifest Addendum before departure @S278 */ }
            perform action a7 { doc /* can pause or abort an approach when observed conditions differ from the forecast or deteriorate during transit @S284 */ }
            perform action a8 { doc /* produces the Crew Count Correction when a verified headcount differs from the departure record @S390 */ }
            perform action a9 { doc /* confirms the departure roster before the vessel leaves port @S398 */ }
            perform action a10 { doc /* records crew changes that occur during transit or between offshore locations @S403 */ }
            perform action a11 { doc /* maintains an onboard count while personnel are aboard the vessel @S409 */ }
            perform action a12 { doc /* confirms practical arrival and departure estimates against the vessel's operating limits @S476 */ }
            perform action a13 { doc /* confirms that the vessel is safely positioned and that transfer conditions remain acceptable @S498 */ }
            perform action a14 { doc /* confirms that the vessel can meet the agreed timing and maintain safe operating margins @S524 */ }
            perform action a15 { doc /* verifies the number of people physically aboard before departure @S567 */ }
            perform action a16 { doc /* maintains a safe operating position while the discrepancy is investigated @S577 */ }
            perform action a17 { doc /* retains authority over vessel safety, navigation, and decisions to approach or withdraw from a casualty @S616 */ }
            perform action a18 { doc /* may withdraw @S634 */ }
            perform action a19 { doc /* retains authority over vessel movements and may decline a task that cannot be completed safely @S642 */ }
            perform action a20 { doc /* retains authority to proceed, slow, alter course, or hold position based on actual conditions and vessel limits @S677 */ }
            perform action a21 { doc /* reassess the route and the suitability of continuing toward the work site @S682 */ }
            perform action a22 { doc /* confirms safety-critical instructions using the agreed read-back procedure before the vessel acts on them @S763 */ }
            perform action a23 { doc /* maintains a safe position and readiness to support personnel recovery when directed by the response lead @S807 */ }
            perform action a24 { doc /* confirm that personnel and vessels can remain safely accounted for during an extended interruption @S944 */ }
        }
        part vesselPersonnel : VesselPersonnel;
        part visitors : Visitors {
            perform action a0 { doc /* follow the same identity checks as other entrants @S849 */ }
        }
        part warehouseSystem : WarehouseSystem {
            perform action a0 { doc /* records stock status @S091 */ }
            perform action a1 { doc /* supports preparation of equipment and consumables for scheduled work @S091 */ }
            perform action a2 { doc /* produces a Backorder Exception Slip when a requested component cannot be supplied by the planned issue date @S163 */ }
            perform action a3 { doc /* records stock movements and makes current inventory information available for logistics planning @S241 */ }
            perform action a4 { doc /* supports cargo preparation so that planned loads can be assembled before the vessel occupies the berth @S478 */ }
            perform action a5 { doc /* maintains the authoritative item catalogue, stock balances, and storage locations @S687 */ }
            perform action a6 { doc /* uses recurring failure and repair information to inform review of critical spares and replenishment assumptions @S928 */ }
        }
        part weatherAnalyst : WeatherAnalyst {
            perform action a0 { doc /* reviews available forecasts @S084 */ }
            perform action a1 { doc /* advises the Marine Coordinator on conditions that may affect marine operations @S084 */ }
            perform action a2 { doc /* reviews forecast limitations and identifies conditions that may affect vessel access or turbine work @S107 */ }
            perform action a3 { doc /* reviews forecast changes and advises the Marine Coordinator when conditions may affect the plan @S232 */ }
            perform action a4 { doc /* reviews forecast confidence and highlights conditions that could invalidate a planned access period @S256 */ }
            perform action a5 { doc /* compares forecast data with recent observations @S272 */ }
            perform action a6 { doc /* advising on the reliability of a work window @S272 */ }
            perform action a7 { doc /* uses the Wave Burst Record to assess whether the planned access period remains suitable @S323 */ }
            perform action a8 { doc /* produces the Visibility Confidence Note to summarize confidence in visibility conditions for near-term port and offshore planning @S472 */ }
            perform action a9 { doc /* reviews the forecast and advises the Duty Planner if conditions could affect the planned sequence @S522 */ }
            perform action a10 { doc /* interprets forecast uncertainty and communicates material changes to the Rescue Coordinator @S626 */ }
            perform action a11 { doc /* interprets forecast uncertainty and identifies conditions that could affect safe vessel handling @S641 */ }
            perform action a12 { doc /* assesses forecast uncertainty and communicates conditions that could affect access, lifting, or work at height @S765 */ }
            perform action a13 { doc /* support entry into Weather Hold when forecast or observed conditions exceed approved operating limits @S939 */ }
        }
        part weatherHold : WeatherHold {
            perform action a0 { doc /* pauses affected marine activity @S086 */ }
            perform action a1 { doc /* prevents mobilization when forecast or observed conditions exceed the approved operating limits @S259 */ }
        }
        part weatherService : WeatherService {
            perform action a0 { doc /* contributes environmental information to operational planning and coordination @S067 */ }
            perform action a1 { doc /* produces the Squall Window Bulletin for operational awareness @S083 */ }
            perform action a2 { doc /* uses validated environmental observations in forecast products for offshore planning @S106 */ }
            perform action a3 { doc /* issues forecast updates that support timing decisions for remote observation and field work @S128 */ }
            perform action a4 { doc /* provides forecast information for marine planning @S230 */ }
            perform action a5 { doc /* supplies forecast information for evaluating marine and aviation access options @S255 */ }
            perform action a6 { doc /* provides forecast conditions and confidence information for planned work areas and vessel routes @S270 */ }
            perform action a7 { doc /* provide contextual conditions that help reviewers distinguish environmental effects from equipment deterioration @S309 */ }
            perform action a8 { doc /* provide forecasts and measured conditions for assessing whether remote or close-access work is safe @S443 */ }
            perform action a9 { doc /* supplies forecast conditions relevant to access and safe execution @S521 */ }
            perform action a10 { doc /* provides forecast information for planning @S624 */ }
            perform action a11 { doc /* provides current forecasts for the recovery area and the planned transit route @S640 */ }
            perform action a12 { doc /* provides context for expected changes @S664 */ }
            perform action a13 { doc /* provide inputs that are reviewed alongside direct observations from offshore personnel @S766 */ }
            perform action a14 { doc /* support entry into Weather Hold when forecast or observed conditions exceed approved operating limits @S939 */ }
        }
        part westServiceLift : WestServiceLift {
            perform action a0 { doc /* provides vertical access along the west route between the designated service landings @S884 */ }
        }
        part windFarmAssets : WindFarmAssets;
        part workParty : WorkParty {
            perform action a0 { doc /* confirms equipment identity using permanent labels and the current site designation @S720 */ }
        }
        part workPermitPortal : WorkPermitPortal {
            perform action a0 { doc /* supports authorization processes that govern work under controlled conditions @S070 */ }
            perform action a1 { doc /* maintains the request record and its revision history throughout review and execution @S155 */ }
            perform action a2 { doc /* records review decisions @S162 */ }
            perform action a3 { doc /* returns incomplete requests to the requester with the required corrections identified @S162 */ }
            perform action a4 { doc /* records the start, pause, resumption, and completion of authorized work against the permit record @S169 */ }
            perform action a5 { doc /* supports readiness checks for work requiring controlled access or electrical isolation @S265 */ }
            perform action a6 { doc /* block permit release until required risk reviews and isolation references are complete @S321 */ }
            perform action a7 { doc /* produces the Isolation Boundary Sketch @S492 */ }
            perform action a8 { doc /* makes the approved boundary available to the work party and the control team @S713 */ }
            perform action a9 { doc /* retains the current approval and makes superseded versions unavailable for active work @S728 */ }
            perform action a10 { doc /* retains permit decisions and associated approvals in a form that can be retrieved for review @S780 */ }
        }
        flow f0 of SharedViewOfVesselAssignmentsPlannedMovementsAndDispatchStatusItem from fleetDispatchConsole to marineCoordinator { doc /* @S081 */ }
        flow f2 of ValidatedEnvironmentalObservationsItem from metoceanBuoy to weatherService { doc /* @S106 */ }
        flow f3 of TurbineControlCommandsItem from turbineController to pitchSystem { doc /* @S130 */ }
        flow f4 of TurbineStatusAndControlAvailabilityItem from sCADAGateway to authorizedShorePersonnel { doc /* @S133 */ }
        flow f5 of AvailableTrafficPictureItem from vesselAISReceiver to marineCoordinator { doc /* @S141 */ }
        flow f6 of PitchDeviationNoticeItem from turbineController to sCADAGateway { doc /* @S159 */ }
        flow f7 of CurrentOperationalStatusItem from sCADAGateway to permitReviewers { doc /* @S171 */ }
        flow f8 of SupplyAlarmsAndGeneratorStatusItem from sCADAGateway to shoreControlRoom { doc /* @S192 */ }
        flow f9 of ElectricalPowerItem from offshoreWindFarm to gridConnectionPoint { doc /* @S199 */ }
        flow f10 of AuthorizedOperatingSignalsItem from gridInterfaceRelay to transmissionSystem { doc /* @S201 */ }
        flow f11 of AuthorizedOperatingSignalsItem from transmissionSystem to gridInterfaceRelay { doc /* @S201 */ }
        flow f12 of RelayStatusAndInterfaceMeasurementsItem from sCADAGateway to farmMonitoringEnvironment { doc /* @S211 */ }
        flow f13 of SquallWindowBulletinItem from weatherService to maintenancePlanningEngine { doc /* @S213 */ }
        flow f14 of PositionQualityFlagItem from vesselAISReceiver to fleetDispatchConsole { doc /* @S225 */ }
        flow f15 of BackorderExceptionSlipItem from warehouseSystem to storekeeper { doc /* @S262 */ }
        flow f16 of ResultingPlanItem from dutyPlanner to affectedTeams { doc /* @S269 */ }
        flow f17 of TransferManifestAddendumItem from dutyPlanner to vesselMaster { doc /* @S278 */ }
        flow f18 of OperatingMeasurementsItem from turbineController to turbineSensorBus { doc /* @S294 */ }
        flow f19 of OperatingMeasurementsItem from pitchSystem to turbineSensorBus { doc /* @S294 */ }
        flow f20 of OperatingMeasurementsItem from converterCabinet to turbineSensorBus { doc /* @S294 */ }
        flow f21 of OperatingMeasurementsItem from nacelleConditionMonitor to turbineSensorBus { doc /* @S294 */ }
        flow f22 of TimeStampedObservationsItem from sCADAGateway to shoreControlRoom { doc /* @S295 */ }
        flow f23 of HarnessAuditCardItem from hSEOfficer to crewTransferVessel { doc /* @S312 */ }
        flow f24 of WaveBurstRecordItem from metoceanBuoy to weatherAnalyst { doc /* @S323 */ }
        flow f25 of SessionRevocationReceiptItem from sCADAGateway to cybersecurityGateway { doc /* @S357 */ }
        flow f26 of TransformerTapSnapshotItem from offshoreSubstation to shoreControlRoom { doc /* @S374 */ }
        flow f27 of ChangeInDestinationOrTransferPlanItem from personnel to vesselMaster { doc /* @S402 */ }
        flow f28 of DeferredTaskRationaleItem from maintenancePlanningEngine to fieldSupervisor { doc /* @S430 */ }
        flow f29 of LeadingEdgeTileImageItem from bladeInspectionDrone to bladeSpecialist { doc /* @S445 */ }
        flow f30 of BerthSlotConfirmationItem from portAgent to marineCoordinator { doc /* @S473 */ }
        flow f31 of StartTestTraceItem from emergencyGenerator to substationOperator { doc /* @S532 */ }
        flow f32 of CurrentGenerationExportAndEquipmentStatusItem from sCADAGateway to operationsTeam { doc /* @S540 */ }
        flow f33 of ExportLimitAdvisoryItem from gridInterfaceRelay to gridDispatcher { doc /* @S541 */ }
        flow f34 of CrewCountCorrectionItem from vesselMaster to personnelTrackingConsole { doc /* @S573 */ }
        flow f35 of DiscrepancyAndTheImmediateControlActionsItem from marineCoordinator to shoreControlRoom { doc /* @S578 */ }
        flow f36 of FirmwareHashAttestationItem from cybersecurityAnalyst to sCADAEngineer { doc /* @S593 */ }
        flow f37 of MaterialChangesItem from weatherAnalyst to rescueCoordinator { doc /* @S626 */ }
        flow f38 of RecoveryBasketLoadSheetItem from serviceOperationsVessel to rescueCoordinator { doc /* @S646 */ }
        flow f39 of VisibilityConfidenceNoteItem from weatherAnalyst to dutyPlanner { doc /* @S669 */ }
        flow f40 of IsolationBoundarySketchItem from workPermitPortal to electricalTechnician { doc /* @S716 */ }
        flow f41 of RemainingOperationalLimitationItem from controlEngineer to affectedPersonnel { doc /* @S734 */ }
        flow f42 of SwitchingWindowAcknowledgmentItem from shoreControlRoom to offshoreSubstation { doc /* @S752 */ }
        flow f43 of RelevantMarineAndWeatherInformationItem from marineCoordinator to dutyPlanner { doc /* @S764 */ }
        flow f44 of RelevantMarineAndWeatherInformationItem from marineCoordinator to vesselPersonnel { doc /* @S764 */ }
        flow f45 of OperationalDataItem from sCADAGateway to shoreControlRoom { doc /* @S767 */ }
        flow f46 of ExternalOperatingRequirementsItem from gridDispatcher to gridInterfaceRelay { doc /* @S769 */ }
        flow f47 of ExternalOperatingRequirementsItem from gridDispatcher to responsibleControlPersonnel { doc /* @S769 */ }
        flow f48 of UnresolvedPersonnelOrAccessConcernsItem from fieldSupervisor to shoreControlRoom { doc /* @S809 */ }
        flow f49 of ReleaseStatusItem from fieldSupervisor to workParty { doc /* @S881 */ }
    }
    requirement def R0 { doc /* Juniper Vale shall provide current operational status to permit reviewers when requested as part of the authorization check. @S171 */ subject s : SCADAGateway; }
    requirement def R1 { doc /* Larkspur shall repeat a close-range pass when image coverage is insufficient to assess the suspected surface condition. @S314 */ subject s : BladeInspectionDrone; }
    requirement def R2 { doc /* Redoubt shall block permit release until required risk reviews and isolation references are complete. @S321 */ subject s : WorkPermitPortal; }
    requirement def R3 { doc /* Field Supervisor uses the Deferred Task Rationale when a cybersecurity-related work item must be postponed. @S430 */ subject s : CybersecurityRelatedWorkItem; }
    requirement def R4 { doc /* Port staging areas are reserved for equipment that must be inspected, secured, or transferred before sailing. @S477 */ subject s : Equipment; }
    requirement def R5 { doc /* It also records any adjacent equipment that must remain energized or available for service. @S715 */ subject s : AdjacentEquipment; }
    requirement def R6 { doc /* Personnel must not hold the barrier open for another entrant. @S847 */ subject s : Personnel; }
    requirement def R7 { doc /* Lighting inside the car and at each landing must be adequate for safe movement and inspection. @S891 */ subject s : Lighting; }
    requirement def R8 { doc /* Door interlocks and other protective devices must be functional before the lift is placed in service. @S893 */ subject s : DoorInterlocks; }
    requirement def R9 { doc /* Protective devices must not be bypassed to maintain access or avoid delay. @S894 */ subject s : ProtectiveDevices; }
}
