package L2Model {
    item def ABackorderExceptionSlipItem { doc /* @S262 */ }
    item def APositionQualityFlagItem { doc /* @S225 */ }
    item def AccessRestrictionsItem { doc /* @S717 */ }
    item def AccessStatusItem { doc /* @S512 */ }
    item def ActiveFaultIndicationItem { doc /* @S867 */ }
    item def ActivePowerTargetsItem { doc /* @S368 */ }
    item def AlarmItem { doc /* @S902 */ }
    item def AlarmIndicationsItem { doc /* @S629 */ }
    item def AlarmsItem { doc /* @S798 */ }
    item def AlertItem { doc /* @S419 */ }
    item def AnExportLimitAdvisoryItem { doc /* @S541 */ }
    item def AuthorizedOperatingSignalsItem { doc /* @S201 */ }
    item def BerthSlotConfirmationItem { doc /* @S473 */ }
    item def ChangeInDestinationOrTransferPlanItem { doc /* @S402 */ }
    item def ChangesToWorkProgressItem { doc /* @S096 */ }
    item def CloseRangeVisualObservationsOfAccessibleBladeSurfacesItem { doc /* @S145 */ }
    item def CompletionItem { doc /* @S533 */ }
    item def CompletionStatusItem { doc /* @S170 */ }
    item def ConditionsItem { doc /* @S232,S500,S717 */ }
    item def ConditionsThatMayAffectMarineOperationsItem { doc /* @S084 */ }
    item def ContextualConditionsItem { doc /* @S309 */ }
    item def ControlAvailabilityItem { doc /* @S133 */ }
    item def CredentialItem { doc /* @S839 */ }
    item def CurrentGenerationItem { doc /* @S540 */ }
    item def CurrentOperationalStatusItem { doc /* @S171 */ }
    item def DefectsItem { doc /* @S869 */ }
    item def DirectReportsItem { doc /* @S629 */ }
    item def DiscrepancyItem { doc /* @S578,S583 */ }
    item def ElectricalPowerItem { doc /* @S199 */ }
    item def EnvironmentalInformationItem { doc /* @S067 */ }
    item def EquipmentStatusItem { doc /* @S540,S630,S788 */ }
    item def ExportItem { doc /* @S540 */ }
    item def ExternalOperatingRequirementsItem { doc /* @S769 */ }
    item def ForecastConditionsItem { doc /* @S521,S522,S939 */ }
    item def GeneratorStatusItem { doc /* @S192 */ }
    item def ImmediateControlActionsItem { doc /* @S578 */ }
    item def IncompleteRequestsItem { doc /* @S162 */ }
    item def IndependentSignalsItem { doc /* @S299 */ }
    item def InputItem { doc /* @S076 */ }
    item def InspectionResultItem { doc /* @S869 */ }
    item def InterfaceMeasurementsItem { doc /* @S211 */ }
    item def IsolationBoundaryItem { doc /* @S713,S717 */ }
    item def MaterialChangesItem { doc /* @S626 */ }
    item def ObservationsItem { doc /* @S271,S317 */ }
    item def OperatingMeasurementsItem { doc /* @S294 */ }
    item def OperationalDataItem { doc /* @S767 */ }
    item def OperationalPointOfContactItem { doc /* @S613 */ }
    item def OperationalRestrictionsItem { doc /* @S947 */ }
    item def OutstandingHazardsItem { doc /* @S512 */ }
    item def OutstandingIssuesItem { doc /* @S170 */ }
    item def OverdueCheckInItem { doc /* @S412 */ }
    item def PlanItem { doc /* @S269 */ }
    item def PlannedWorkPeriodItem { doc /* @S520 */ }
    item def PointOfCoordinationItem { doc /* @S097,S099 */ }
    item def RampInstructionsItem { doc /* @S368 */ }
    item def RelayStatusItem { doc /* @S211 */ }
    item def ReleaseStatusItem { doc /* @S881 */ }
    item def RelevantMarineAndWeatherInformationItem { doc /* @S764 */ }
    item def RemainingOperationalLimitationItem { doc /* @S734 */ }
    item def SharedViewOfVesselAssignmentsPlannedMovementsAndDispatchStatusItem { doc /* @S081,S082 */ }
    item def SiteConditionsItem { doc /* @S512 */ }
    item def SquallWindowBulletinItem { doc /* @S213 */ }
    item def StartTestTraceItem { doc /* @S532 */ }
    item def SupplyAlarmsItem { doc /* @S192 */ }
    item def SwitchingInstructionsItem { doc /* @S530 */ }
    item def SwitchingWindowAcknowledgmentItem { doc /* @S531,S752 */ }
    item def TheCrewCountCorrectionItem { doc /* @S573 */ }
    item def TheDeferredTaskRationaleItem { doc /* @S430 */ }
    item def TheFirmwareHashAttestationItem { doc /* @S593 */ }
    item def TheHarnessAuditCardItem { doc /* @S312 */ }
    item def TheIsolationBoundarySketchItem { doc /* @S716 */ }
    item def TheLeadingEdgeTileImageItem { doc /* @S445 */ }
    item def ThePitchDeviationNoticeItem { doc /* @S159 */ }
    item def TheRecoveryBasketLoadSheetItem { doc /* @S646 */ }
    item def TheSessionRevocationReceiptItem { doc /* @S357 */ }
    item def TheTransferManifestAddendumItem { doc /* @S278 */ }
    item def TheVisibilityConfidenceNoteItem { doc /* @S669 */ }
    item def TheWaveBurstRecordItem { doc /* @S323 */ }
    item def TimeStampedObservationsItem { doc /* @S295 */ }
    item def TimeStampedViewOfNearbyVesselMovementsItem { doc /* @S141,S749 */ }
    item def TimelyClearAndTraceableInformationItem { doc /* @S760 */ }
    item def TransformerTapSnapshotItem { doc /* @S374 */ }
    item def TurbineControlCommandsItem { doc /* @S130 */ }
    item def TurbineStatusItem { doc /* @S133,S448 */ }
    item def UnexplainedAbsenceItem { doc /* @S412 */ }
    item def UnresolvedPersonnelOrAccessConcernsItem { doc /* @S809 */ }
    item def UpdateItem { doc /* @S245 */ }
    item def UrgentConcernsItem { doc /* @S419 */ }
    item def VesselPositionInformationItem { doc /* @S400,S401 */ }
    part def AbnormalCondition { doc /* @S768 */ }
    part def AbnormalElectricalCondition { doc /* @S360 */ }
    part def Access { doc /* @S028 */ }
    part def AccessConditions { doc /* @S224 */ }
    part def AccessManagement { doc /* @S022 */ }
    part def AccessRecords { doc /* @S825 */ }
    part def AccountabilityRecords { doc /* @S414 */ }
    part def AccountableOwner { doc /* @S959 */ }
    part def ActionsTaken { doc /* @S584 */ }
    part def ActiveRestrictions { doc /* @S871 */ }
    part def ActiveWorkAuthorizations { doc /* @S350 */ }
    part def Activity { doc /* @S751 */ }
    part def ActualConditions { doc /* @S755 */ }
    part def AdjacentEquipment { doc /* @S715 */ }
    part def AdministrativeAccess { doc /* @S115 */ }
    part def AffectedActivity { doc /* @S579 */ }
    part def AffectedEquipment { doc /* @S740 */ }
    part def AffectedServices { doc /* @S122 */ }
    part def AffectedTeams { doc /* @S245,S269 */ }
    part def AffectedWork { doc /* @S510 */ }
    part def AlarmPriorities { doc /* @S796 */ }
    part def AlarmThresholds { doc /* @S108 */ }
    part def Alarms { doc /* @S378 */ }
    part def Alternative { doc /* @S704 */ }
    part def AlternativeAccessMethod { doc /* @S292 */ }
    part def ApplicableHandlingRequirements { doc /* @S699 */ }
    part def Approval { doc /* @S714,S715 */ }
    part def ApprovedElectricalConfiguration { doc /* @S387 */ }
    part def ApprovedImprovements { doc /* @S932 */ }
    part def ApprovedProcedures { doc /* @S972 */ }
    part def ApprovedSwitchingWindow { doc /* @S752,S753 */ }
    part def ApprovedWindow { doc /* @S740 */ }
    part def Architecture { doc /* @S072 */ }
    part def Area { doc /* @S801 */ }
    part def AreasRequiringCloserAssessment { doc /* @S445 */ }
    part def ArrayOfTurbines { doc /* @S003 */ }
    part def AssetOperator { doc /* @S959 */ }
    part def Assignment { doc /* @S407 */ }
    part def AssuranceArrangements { doc /* @S983 */ }
    part def AssuranceEvidence { doc /* @S972 */ }
    part def Attempt { doc /* @S820,S824 */ }
    part def AuditFindings { doc /* @S972 */ }
    part def AuditRecord { doc /* @S823 */ }
    part def Authority { doc /* @S122,S657 */ }
    part def Authorization { doc /* @S168,S407,S813,S815 */ }
    part def AuthorizationLifecycle { doc /* @S151 */ }
    part def AuthorizationProcesses { doc /* @S070 */ }
    part def AuthorizedPersonnel { doc /* @S358 */ }
    part def AuthorizedShorePersonnel { doc /* @S133 */ }
    part def AuthorizedSwitchingPlan { doc /* @S551 */ }
    part def AutomaticControls { doc /* @S177 */ }
    part def AuxiliaryElectricalLoads { doc /* @S173 */ }
    part def AvailableExportCapability { doc /* @S372 */ }
    part def BackupPower { doc /* @S025 */ }
    part def BarrierControls { doc /* @S854 */ }
    part def BladeCondition { doc /* @S440 */ }
    part def BladeInspectionDrone { doc /* @S142,S145,S254,S313,S314,S444,S445 */ }
    part def BladeSpecialist { doc /* @S143,S315,S445,S452,S455,S463,S651 */ }
    part def BoundaryRecords { doc /* @S735 */ }
    part def CableCondition { doc /* @S252 */ }
    part def Cancellation { doc /* @S292 */ }
    part def Car { doc /* @S863,S902,S903,S904 */ }
    part def CarFloor { doc /* @S890 */ }
    part def Change { doc /* @S981 */ }
    part def ChangeThatCouldAffectThePassage { doc /* @S226 */ }
    part def ChangeToTheWorkScope { doc /* @S510 */ }
    part def Changes { doc /* @S960,S969 */ }
    part def ChangesToAccessRules { doc /* @S833 */ }
    part def ChangesToTheTaskEquipmentStateOrWorkLocation { doc /* @S727 */ }
    part def CloseRangeVisualObservationsOfAccessibleBladeSurfaces { doc /* @S147 */ }
    part def Commands { doc /* @S127 */ }
    part def CommunicationChannel { doc /* @S771 */ }
    part def Communications { doc /* @S025,S413,S535,S659 */ }
    part def CompetenceRecords { doc /* @S972 */ }
    part def CompletionOfRequiredControls { doc /* @S912 */ }
    part def Concept { doc /* @S001,S005,S006,S019,S050,S983 */ }
    part def Condition { doc /* @S362,S560,S883,S907 */ }
    part def ConditionData { doc /* @S250 */ }
    part def ConditionEvidence { doc /* @S249 */ }
    part def ConditionInformation { doc /* @S793 */ }
    part def Conditions { doc /* @S232,S256,S259,S330,S381,S455,S500,S522,S535,S634,S641,S669 */ }
    part def ConditionsThatMayAffectMarineOperations { doc /* @S765 */ }
    part def ConditionsThatMayAffectVesselAccessOrTurbineWork { doc /* @S107 */ }
    part def Confidence { doc /* @S105 */ }
    part def ConfigurationBaseline { doc /* @S589 */ }
    part def ConfiguredIdentityAndAuthorizationChecks { doc /* @S819 */ }
    part def ConfirmedFaults { doc /* @S248 */ }
    part def ConfirmedFireCondition { doc /* @S789 */ }
    part def ContextualConditions { doc /* @S309 */ }
    part def ContingencyProcess { doc /* @S829 */ }
    part def ContinuedResponse { doc /* @S633 */ }
    part def Control { doc /* @S834 */ }
    part def ControlEngineer { doc /* @S063,S135,S193,S217,S297,S299,S302,S305,S310,S316,S338,S349,S368,S375,S384,S423,S434,S516,S528,S530,S533,S534,S535,S542,S544,S552,S560,S562,S594,S630,S658,S718,S734,S742,S768,S799,S920,S938,S951,S964 */ }
    part def ControlFunctions { doc /* @S002 */ }
    part def ControlResponse { doc /* @S375 */ }
    part def ControlRoomDecisions { doc /* @S214 */ }
    part def ControlRoomStaff { doc /* @S729 */ }
    part def ControlTeam { doc /* @S713 */ }
    part def ControlledBoundary { doc /* @S112 */ }
    part def ControlledLifecycle { doc /* @S587 */ }
    part def Controls { doc /* @S892 */ }
    part def ConverterCabinet { doc /* @S005,S035,S131,S294,S547 */ }
    part def CorrectedSensorData { doc /* @S316 */ }
    part def Corrections { doc /* @S777 */ }
    part def Credential { doc /* @S823,S840 */ }
    part def CredentialReaders { doc /* @S854 */ }
    part def Crew { doc /* @S167,S495,S504,S506,S511,S678,S717,S721 */ }
    part def CrewAccountability { doc /* @S391 */ }
    part def CrewChanges { doc /* @S403 */ }
    part def CrewMember { doc /* @S726 */ }
    part def CrewTransferVessel { doc /* @S021,S045,S087,S215,S279,S312,S568,S643,S678 */ }
    part def CurrentStatus { doc /* @S584 */ }
    part def Curtailment { doc /* @S556 */ }
    part def Cybersecurity { doc /* @S025 */ }
    part def CybersecurityAnalyst { doc /* @S117,S419,S428,S435,S593,S781,S929,S969 */ }
    part def CybersecurityControls { doc /* @S929 */ }
    part def CybersecurityGateway { doc /* @S071,S111,S287,S357,S416 */ }
    part def CybersecurityOperations { doc /* @S415 */ }
    part def CybersecurityRelatedWorkItem { doc /* @S430 */ }
    part def DamagedOrContaminatedItems { doc /* @S653 */ }
    part def DaughterCraft { doc /* @S021,S045,S088,S568,S621 */ }
    part def DaughterCraftOperation { doc /* @S679 */ }
    part def DecisionRecords { doc /* @S293 */ }
    part def Decisions { doc /* @S365 */ }
    part def Defect { doc /* @S870 */ }
    part def DefectHistory { doc /* @S464 */ }
    part def DefectRecords { doc /* @S453 */ }
    part def DeferredTaskRationale { doc /* @S286 */ }
    part def Delay { doc /* @S292,S754 */ }
    part def DeliveredEnergy { doc /* @S910 */ }
    part def DeliveryLocation { doc /* @S699 */ }
    part def Denial { doc /* @S817 */ }
    part def Deployment { doc /* @S608 */ }
    part def DesignatedApprover { doc /* @S979 */ }
    part def DesignatedAuthorizingRole { doc /* @S165 */ }
    part def DesignatedGridConnectionPoint { doc /* @S199 */ }
    part def DetectionCoverage { doc /* @S787 */ }
    part def DetectorSignal { doc /* @S797 */ }
    part def DifferenceBetweenTheExpectedAndObservedCount { doc /* @S575 */ }
    part def DifferencesBetweenObservationTimesAndLocations { doc /* @S663 */ }
    part def Discrepancy { doc /* @S583,S666 */ }
    part def DispatchRecord { doc /* @S708 */ }
    part def DocumentOwner { doc /* @S976 */ }
    part def DocumentedImpactAssessment { doc /* @S961 */ }
    part def Door { doc /* @S863 */ }
    part def DoorInterlocks { doc /* @S893 */ }
    part def Doors { doc /* @S898 */ }
    part def DueDate { doc /* @S249 */ }
    part def DurationOfGridRelatedRestrictions { doc /* @S910 */ }
    part def DutyPlanner { doc /* @S065,S076,S096,S126,S153,S164,S224,S247,S258,S260,S263,S269,S274,S278,S292,S304,S319,S334,S340,S388,S396,S442,S459,S464,S469,S491,S515,S519,S520,S527,S536,S537,S539,S553,S561,S583,S639,S669,S695,S737,S758,S764,S779,S872,S925,S947,S955,S965 */ }
    part def EastServiceLift { doc /* @S859 */ }
    part def ElectricalAbsenceOfVoltageChecks { doc /* @S724 */ }
    part def ElectricalEnclosures { doc /* @S787 */ }
    part def ElectricalRecoveryWork { doc /* @S631 */ }
    part def ElectricalTechnician { doc /* @S185,S325,S327,S331,S336,S363,S434,S496,S529,S650,S716,S750,S770,S801,S867 */ }
    part def EmergencyArrangements { doc /* @S612 */ }
    part def EmergencyDistributionBus { doc /* @S180 */ }
    part def EmergencyEgress { doc /* @S857 */ }
    part def EmergencyGenerator { doc /* @S180,S183,S186,S353,S356,S532,S803,S945 */ }
    part def EmergencyResponseOrganizations { doc /* @S024 */ }
    part def EmergencySource { doc /* @S196 */ }
    part def EmergencyStop { doc /* @S892 */ }
    part def EnablingFunctions { doc /* @S049 */ }
    part def EndTime { doc /* @S740 */ }
    part def EnergyProductionMeasures { doc /* @S910 */ }
    part def EnergySources { doc /* @S711 */ }
    part def Entrant { doc /* @S839 */ }
    part def Entries { doc /* @S775 */ }
    part def Entry { doc /* @S845 */ }
    part def EntryBarrier { doc /* @S846 */ }
    part def EnvironmentalLimits { doc /* @S233 */ }
    part def EnvironmentalObservations { doc /* @S100 */ }
    part def Equipment { doc /* @S328,S341,S477,S535,S711,S736,S876,S895 */ }
    part def EquipmentCondition { doc /* @S028 */ }
    part def EquipmentState { doc /* @S735 */ }
    part def EquipmentStatus { doc /* @S146,S348 */ }
    part def Estimate { doc /* @S667 */ }
    part def Event { doc /* @S307 */ }
    part def EventInvestigations { doc /* @S972 */ }
    part def Evidence { doc /* @S303 */ }
    part def ExpectedLoad { doc /* @S895 */ }
    part def ExpectedOperatingState { doc /* @S740 */ }
    part def ExpectedPersonnelCount { doc /* @S584 */ }
    part def ExportCable { doc /* @S199 */ }
    part def ExportCableMonitor { doc /* @S006,S038,S200,S252 */ }
    part def ExportEquipment { doc /* @S549 */ }
    part def ExportRestriction { doc /* @S538,S539,S553,S554 */ }
    part def ExportSystem { doc /* @S038 */ }
    part def ExternalInterfaces { doc /* @S024 */ }
    part def ExternalOrganizations { doc /* @S027 */ }
    part def ExternalTransmissionSystem { doc /* @S201 */ }
    part def ExternalWork { doc /* @S748 */ }
    part def Facility { doc /* @S173 */ }
    part def FailureAnalyses { doc /* @S923 */ }
    part def FarmMonitoringEnvironment { doc /* @S211 */ }
    part def Fault { doc /* @S208 */ }
    part def FieldFindings { doc /* @S316 */ }
    part def FieldSupervisor { doc /* @S076,S096,S145,S167,S253,S320,S329,S330,S333,S335,S340,S405,S412,S429,S430,S457,S493,S503,S509,S536,S615,S649,S660,S717,S726,S778,S809,S826,S860,S869,S879,S881,S886,S887,S906,S927,S970 */ }
    part def FieldTeam { doc /* @S729 */ }
    part def FieldWork { doc /* @S711 */ }
    part def FinalWindow { doc /* @S747 */ }
    part def Fire { doc /* @S792 */ }
    part def FireDetectionPanel { doc /* @S352,S629,S786,S798,S945 */ }
    part def FireProtection { doc /* @S025,S785 */ }
    part def FleetDispatchConsole { doc /* @S041,S069,S081,S082,S203,S225,S260,S370,S385,S543,S917,S947 */ }
    part def FleetDispatchConsoleSchedules { doc /* @S485 */ }
    part def FogBanks { doc /* @S662 */ }
    part def Forecast { doc /* @S280,S664 */ }
    part def ForecastUpdates { doc /* @S128 */ }
    part def Gate { doc /* @S816 */ }
    part def GenerationCapability { doc /* @S942 */ }
    part def GoOrNoGoDecision { doc /* @S674 */ }
    part def Grid { doc /* @S347 */ }
    part def GridConstraint { doc /* @S210,S519,S746 */ }
    part def GridDispatch { doc /* @S024 */ }
    part def GridDispatcher { doc /* @S202,S367,S368,S518,S541,S739,S769,S942 */ }
    part def GridInterfaceRelay { doc /* @S190,S197,S201,S221,S372,S373,S541,S551,S743,S769,S942 */ }
    part def GridRequirements { doc /* @S028 */ }
    part def HSEOfficer { doc /* @S095,S157,S237,S266,S312,S322,S408,S451,S481,S505,S526,S579,S617,S647,S808,S827,S949,S967 */ }
    part def HandlingArrangement { doc /* @S877 */ }
    part def HandsOnActivity { doc /* @S631 */ }
    part def HandsOnWork { doc /* @S725 */ }
    part def HazardousEnergySources { doc /* @S725 */ }
    part def Hazards { doc /* @S011 */ }
    part def Helideck { doc /* @S021 */ }
    part def IncidentLead { doc /* @S432,S436,S619 */ }
    part def IncomingSupervisor { doc /* @S512 */ }
    part def IncomingTeam { doc /* @S731 */ }
    part def Indication { doc /* @S535 */ }
    part def Indicators { doc /* @S854 */ }
    part def Inspection { doc /* @S861 */ }
    part def InspectionRecord { doc /* @S456 */ }
    part def Inspector { doc /* @S862,S865,S868 */ }
    part def InstallationTeam { doc /* @S853 */ }
    part def Instruction { doc /* @S773 */ }
    part def Instructions { doc /* @S770 */ }
    part def Interface { doc /* @S220 */ }
    part def Inventory { doc /* @S023 */ }
    part def InventoryRecord { doc /* @S686 */ }
    part def Isolation { doc /* @S732 */ }
    part def IsolationBoundaries { doc /* @S350 */ }
    part def IsolationBoundary { doc /* @S711 */ }
    part def IsolationDevice { doc /* @S722 */ }
    part def Items { doc /* @S701 */ }
    part def ItemsReservedForApprovedWork { doc /* @S688 */ }
    part def Label { doc /* @S378,S379,S380,S381,S383,S384,S386,S387,S392,S399,S400 */ }
    part def Landing { doc /* @S887 */ }
    part def LaterReviewers { doc /* @S775 */ }
    part def LessonsLearned { doc /* @S933 */ }
    part def Lift { doc /* @S883,S893,S906 */ }
    part def LiftSupply { doc /* @S867 */ }
    part def Lighting { doc /* @S891 */ }
    part def LocalConditions { doc /* @S664 */ }
    part def LocalIndication { doc /* @S719 */ }
    part def LocalProtectionFunctions { doc /* @S137 */ }
    part def LocalReference { doc /* @S665 */ }
    part def LocalSystems { doc /* @S221 */ }
    part def LocalVisualIndicator { doc /* @S845 */ }
    part def Location { doc /* @S580 */ }
    part def LossOfCriticalMonitoring { doc /* @S360 */ }
    part def LowCloud { doc /* @S662 */ }
    part def LowStockAlerts { doc /* @S701 */ }
    part def MachinerySpaces { doc /* @S787 */ }
    part def MainTransformer { doc /* @S006,S038,S199,S744 */ }
    part def Maintenance { doc /* @S490 */ }
    part def MaintenanceActivities { doc /* @S002 */ }
    part def MaintenancePlanningEngine { doc /* @S042,S054,S058,S066,S076,S148,S154,S188,S195,S213,S246,S285,S308,S430,S441,S458,S470,S520,S670,S694,S738,S918,S948 */ }
    part def MaintenanceRecords { doc /* @S972 */ }
    part def MaintenanceSystem { doc /* @S869 */ }
    part def ManuallyPresentedCredentialImage { doc /* @S818 */ }
    part def MarineAccess { doc /* @S748 */ }
    part def MarineActivity { doc /* @S943 */ }
    part def MarineCoordination { doc /* @S021,S075,S222 */ }
    part def MarineCoordinator { doc /* @S068,S077,S081,S082,S084,S141,S160,S223,S232,S245,S257,S261,S277,S283,S290,S397,S400,S401,S410,S412,S466,S473,S483,S488,S499,S523,S565,S576,S578,S583,S585,S618,S638,S659,S676,S682,S749,S764,S944,S966 */ }
    part def MeasuredConditions { doc /* @S291 */ }
    part def MeasuredDelivery { doc /* @S383 */ }
    part def MeasuredExport { doc /* @S544 */ }
    part def MeasurementIntervals { doc /* @S108 */ }
    part def Measurements { doc /* @S200 */ }
    part def MetoceanBuoy { doc /* @S102,S194,S231,S271,S309,S317,S323,S443,S625,S665,S766 */ }
    part def MetoceanObservations { doc /* @S024 */ }
    part def Mismatch { doc /* @S721 */ }
    part def MonitoringAndControlAssumptions { doc /* @S968 */ }
    part def MonitoringAndControlFunctions { doc /* @S006 */ }
    part def MonitoringImpairment { doc /* @S941 */ }
    part def MonitoringProcess { doc /* @S296 */ }
    part def MonitoringRules { doc /* @S418 */ }
    part def NacelleConditionMonitor { doc /* @S005,S035,S132,S250,S294,S299,S793,S915 */ }
    part def NeedDate { doc /* @S699 */ }
    part def NetworkSegmentation { doc /* @S120 */ }
    part def NormalElectricalSupplies { doc /* @S803 */ }
    part def NormalMonitoringResponsibilities { doc /* @S437 */ }
    part def NormalSupply { doc /* @S174,S190,S196 */ }
    part def NormalWork { doc /* @S635 */ }
    part def NorthAccessScanner { doc /* @S235,S394,S569,S810,S811 */ }
    part def Observations { doc /* @S271,S306 */ }
    part def ObservedCount { doc /* @S584 */ }
    part def Occupants { doc /* @S898,S899,S902,S905 */ }
    part def OffshoreFarm { doc /* @S199,S205 */ }
    part def OffshoreGenerationAssets { doc /* @S027 */ }
    part def OffshorePersonnel { doc /* @S804 */ }
    part def OffshoreRecovery { doc /* @S636 */ }
    part def OffshoreRecoveryPlans { doc /* @S633 */ }
    part def OffshoreSubstation { doc /* @S003,S037,S038,S173,S189,S199,S267,S361,S374,S752,S941 */ }
    part def OffshoreSubstationOperator { doc /* @S549 */ }
    part def OffshoreSupportFacilities { doc /* @S002 */ }
    part def OffshoreTeams { doc /* @S613 */ }
    part def OffshoreWindFarm { doc /* @S028 */ }
    part def OnDutyOperationsLead { doc /* @S419 */ }
    part def OnboardLogger { doc /* @S104 */ }
    part def OperatingData { doc /* @S447 */ }
    part def OperatingInstructions { doc /* @S868 */ }
    part def OperatingLimits { doc /* @S281 */ }
    part def OperatingModel { doc /* @S013 */ }
    part def OperatingOrganization { doc /* @S075,S094,S098 */ }
    part def OperatingPersonnel { doc /* @S341,S349 */ }
    part def OperationalAssessment { doc /* @S667 */ }
    part def OperationalBoundary { doc /* @S002,S025,S027,S034 */ }
    part def OperationalCommunications { doc /* @S760 */ }
    part def OperationalDecisions { doc /* @S624 */ }
    part def OperationalHandoverRecords { doc /* @S611 */ }
    part def OperationalMonitoring { doc /* @S788 */ }
    part def OperationalNotices { doc /* @S214 */ }
    part def OperationalPersonnel { doc /* @S027,S073,S074 */ }
    part def OperationalPlanningAndCoordination { doc /* @S067 */ }
    part def OperationalProcedures { doc /* @S122 */ }
    part def OperationalRecords { doc /* @S774 */ }
    part def OperationalReports { doc /* @S440 */ }
    part def OperationalSystem { doc /* @S058 */ }
    part def OperationalValue { doc /* @S249 */ }
    part def Operations { doc /* @S086 */ }
    part def OperationsRadioConsole { doc /* @S239,S627,S762,S806 */ }
    part def OperationsTeam { doc /* @S540,S558 */ }
    part def Operator { doc /* @S356,S359,S360,S361,S376,S878,S888,S890,S892,S895,S898,S900,S901,S904,S905,S983 */ }
    part def Operators { doc /* @S184,S832,S935 */ }
    part def Organization { doc /* @S782 */ }
    part def OtherAreasIdentifiedByTheSiteFireRiskAssessment { doc /* @S787 */ }
    part def OutgoingSupervisor { doc /* @S512 */ }
    part def Overheating { doc /* @S792 */ }
    part def Parts { doc /* @S697 */ }
    part def Passengers { doc /* @S896 */ }
    part def People { doc /* @S502 */ }
    part def PeopleResponsibleForOffshoreWork { doc /* @S760 */ }
    part def PerformanceDefinitions { doc /* @S913 */ }
    part def PerformanceMeasures { doc /* @S933 */ }
    part def Permit { doc /* @S329,S735 */ }
    part def PermitControls { doc /* @S318 */ }
    part def PermitReviewers { doc /* @S171 */ }
    part def Permits { doc /* @S525 */ }
    part def PermittedFunctions { doc /* @S121 */ }
    part def Person { doc /* @S425,S812,S817,S840 */ }
    part def PersonIssuingTheInstruction { doc /* @S772 */ }
    part def PersonMakingTheChange { doc /* @S777 */ }
    part def PersonRemovingEachControl { doc /* @S733 */ }
    part def PersonResponsibleForApplyingTheControl { doc /* @S714 */ }
    part def PersonalProtection { doc /* @S723 */ }
    part def Personnel { doc /* @S011,S243,S335,S393,S402,S405,S406,S409,S411,S431,S451,S457,S482,S501,S525,S536,S607,S629,S648,S649,S732,S734,S771,S802,S828,S836,S847,S856,S873,S874,S903,S981 */ }
    part def PersonnelMovements { doc /* @S585 */ }
    part def PersonnelTrackingConsole { doc /* @S094,S234,S332,S392,S571,S573,S619,S648,S805,S874 */ }
    part def PersonsStillUnaccountedFor { doc /* @S584 */ }
    part def PhysicalBoundary { doc /* @S003 */ }
    part def PitchSystem { doc /* @S005,S034,S130,S294,S546,S601,S790 */ }
    part def PlannedCrewAssignments { doc /* @S396 */ }
    part def PlannedOutage { doc /* @S745 */ }
    part def PlannedRestorationChecks { doc /* @S532 */ }
    part def PlannedTask { doc /* @S285,S491 */ }
    part def PlannedTests { doc /* @S219 */ }
    part def PlannedWork { doc /* @S872 */ }
    part def Planners { doc /* @S252 */ }
    part def PortAgent { doc /* @S093,S240,S324,S473 */ }
    part def PortAndBerthCoordination { doc /* @S465 */ }
    part def PortConditions { doc /* @S471 */ }
    part def PortSchedule { doc /* @S468 */ }
    part def PortSupport { doc /* @S024 */ }
    part def PositionIntegrityChecks { doc /* @S105 */ }
    part def Procedure { doc /* @S331 */ }
    part def Production { doc /* @S910 */ }
    part def ProhibitedPaths { doc /* @S121 */ }
    part def ProposedControls { doc /* @S266 */ }
    part def ProposedSequence { doc /* @S516,S535 */ }
    part def ProposedWorkaround { doc /* @S949 */ }
    part def ProtectedOperationalNetworks { doc /* @S100 */ }
    part def ProtectionActions { doc /* @S799 */ }
    part def ProtectionAlarm { doc /* @S360 */ }
    part def ProtectionCoordination { doc /* @S208 */ }
    part def ProtectiveDevices { doc /* @S867,S893,S894 */ }
    part def ProtectiveFunctions { doc /* @S788 */ }
    part def QualifiedTechnician { doc /* @S719 */ }
    part def QuantitiesAlreadyCommittedToTransfer { doc /* @S688 */ }
    part def QuantitiesOnHand { doc /* @S688 */ }
    part def Rain { doc /* @S662 */ }
    part def Ramping { doc /* @S556 */ }
    part def RatedCapacity { doc /* @S868 */ }
    part def Receiver { doc /* @S773 */ }
    part def Reconciliation { doc /* @S564 */ }
    part def Record { doc /* @S584,S844 */ }
    part def Records { doc /* @S776 */ }
    part def RecoveredComponents { doc /* @S656 */ }
    part def Recovery { doc /* @S436,S952 */ }
    part def RecoveryHandling { doc /* @S658 */ }
    part def RecoveryTask { doc /* @S639 */ }
    part def ReducedVisibility { doc /* @S679 */ }
    part def ReleasedRevisions { doc /* @S980 */ }
    part def ReliabilityReviews { doc /* @S921 */ }
    part def RemoteAdministrativeFunctions { doc /* @S118 */ }
    part def RemoteEvidence { doc /* @S310 */ }
    part def RemoteIndications { doc /* @S718 */ }
    part def RemoteOperation { doc /* @S138 */ }
    part def RemoteRequests { doc /* @S137 */ }
    part def RemoteSessions { doc /* @S427 */ }
    part def RemoteSurveys { doc /* @S444 */ }
    part def RepairPlans { doc /* @S462 */ }
    part def RepairedArea { doc /* @S463 */ }
    part def ReplenishmentCoordination { doc /* @S023 */ }
    part def ReplenishmentRequests { doc /* @S699 */ }
    part def ReportedEvents { doc /* @S912 */ }
    part def ReportedStateChange { doc /* @S534 */ }
    part def Requester { doc /* @S152,S162 */ }
    part def RequiredElectricalIsolations { doc /* @S801 */ }
    part def RequiredOperatingConditions { doc /* @S736 */ }
    part def RequiredOperationalChecks { doc /* @S338 */ }
    part def RequiredQuantity { doc /* @S699 */ }
    part def RescueCoordinator { doc /* @S244,S614,S626,S634,S637,S646 */ }
    part def Reservations { doc /* @S693 */ }
    part def ResidualUncertainty { doc /* @S464 */ }
    part def ResourceAvailability { doc /* @S224 */ }
    part def Responders { doc /* @S629 */ }
    part def Response { doc /* @S306,S645,S956 */ }
    part def ResponsibleAuthority { doc /* @S732 */ }
    part def ResponsibleControlPersonnel { doc /* @S769 */ }
    part def ResponsibleManager { doc /* @S784 */ }
    part def ResponsibleOperationalAuthority { doc /* @S500 */ }
    part def ResponsibleOperationsStaff { doc /* @S754 */ }
    part def ResponsibleOperator { doc /* @S952 */ }
    part def ResponsibleOrganization { doc /* @S019 */ }
    part def ResponsiblePersonnel { doc /* @S086 */ }
    part def ResponsibleSupervisor { doc /* @S413 */ }
    part def ResponsibleTeam { doc /* @S170,S450 */ }
    part def RestorationChecks { doc /* @S759 */ }
    part def Restrictions { doc /* @S378,S730 */ }
    part def Review { doc /* @S156 */ }
    part def ReviewTeams { doc /* @S922 */ }
    part def Reviewers { doc /* @S309,S596 */ }
    part def Reviews { doc /* @S974 */ }
    part def RiskAssessments { doc /* @S972 */ }
    part def RotorBrakeUnit { doc /* @S005,S034,S791 */ }
    part def Route { doc /* @S842,S853,S855,S887 */ }
    part def RoutineChecks { doc /* @S854 */ }
    part def RoutineRounds { doc /* @S344 */ }
    part def RoutineTools { doc /* @S335 */ }
    part def Rule { doc /* @S822 */ }
    part def SCADAEngineer { doc /* @S062,S423,S437,S558,S593,S946,S954,S968 */ }
    part def SCADAGateway { doc /* @S006,S052,S058,S059,S133,S159,S171,S192,S211,S212,S295,S357,S369,S417,S447,S448,S540,S630,S767,S788,S800,S914,S946 */ }
    part def SafetyFunctions { doc /* @S936 */ }
    part def SafetyPerformanceMeasures { doc /* @S912 */ }
    part def Scanner { doc /* @S839,S840,S843,S846,S856 */ }
    part def ScheduledExercising { doc /* @S186 */ }
    part def ScheduledSurveillance { doc /* @S440 */ }
    part def SeaOrWeatherConditions { doc /* @S499 */ }
    part def Section { doc /* @S123,S563 */ }
    part def SecurityMonitoring { doc /* @S421 */ }
    part def Sender { doc /* @S773 */ }
    part def Sensors { doc /* @S103 */ }
    part def SerialControlledParts { doc /* @S692 */ }
    part def Service { doc /* @S413 */ }
    part def ServiceOperationsVessel { doc /* @S021,S045,S089,S228,S281,S461,S622,S645,S646,S680 */ }
    part def Severity { doc /* @S303 */ }
    part def ShiftHandover { doc /* @S730 */ }
    part def ShiftRecords { doc /* @S365,S389 */ }
    part def ShoreBasedPersonnel { doc /* @S097,S099 */ }
    part def ShoreBasedPlanning { doc /* @S075 */ }
    part def ShoreControlRoom { doc /* @S040,S058,S064,S097,S099,S134,S192,S214,S238,S295,S303,S317,S339,S364,S371,S374,S386,S419,S420,S448,S531,S578,S606,S613,S683,S752,S767,S798,S809,S937,S963 */ }
    part def ShorePersonnel { doc /* @S410 */ }
    part def ShortLivedFluctuations { doc /* @S555 */ }
    part def Shortage { doc /* @S702 */ }
    part def Signs { doc /* @S852 */ }
    part def SiteFireRiskAssessment { doc /* @S787 */ }
    part def SiteMeasurements { doc /* @S625 */ }
    part def SiteSpecificDetectionAndTripSettings { doc /* @S795 */ }
    part def SoftwareChanges { doc /* @S597,S603 */ }
    part def SouthAccessScanner { doc /* @S236,S395,S570,S813,S814,S816,S828,S831,S835,S838 */ }
    part def SparesHub { doc /* @S689 */ }
    part def Spray { doc /* @S662 */ }
    part def StableConditions { doc /* @S196 */ }
    part def StaleOrImplausibleValue { doc /* @S300 */ }
    part def StartTime { doc /* @S740 */ }
    part def StationServiceTransformers { doc /* @S173 */ }
    part def StatusIndications { doc /* @S190 */ }
    part def Step { doc /* @S741 */ }
    part def StockVisibility { doc /* @S688 */ }
    part def Storekeeper { doc /* @S092,S242,S262,S460,S479,S690,S703,S876 */ }
    part def SubstationLimitation { doc /* @S559 */ }
    part def SubstationOperator { doc /* @S216,S268,S326,S337,S342,S343,S345,S351,S354,S382,S497,S517,S530,S531,S532,S559,S741,S753,S770,S971 */ }
    part def SubstationSwitchingWindows { doc /* @S736 */ }
    part def SubstationWork { doc /* @S742 */ }
    part def Substitutions { doc /* @S704 */ }
    part def SupersededVersions { doc /* @S728 */ }
    part def SupervisoryFaults { doc /* @S796 */ }
    part def SupplyInterfaces { doc /* @S023 */ }
    part def SupportingMarineAndShoreFacilities { doc /* @S027 */ }
    part def SwitchingActions { doc /* @S216 */ }
    part def SwitchingActivity { doc /* @S382 */ }
    part def SwitchingCoordination { doc /* @S514 */ }
    part def SwitchingOperator { doc /* @S533 */ }
    part def System { doc /* @S015,S183,S824,S902,S908,S935,S956,S957 */ }
    part def SystemArchitecture { doc /* @S051 */ }
    part def Task { doc /* @S157,S737 */ }
    part def TaskSelection { doc /* @S671 */ }
    part def Tasks { doc /* @S948 */ }
    part def Team { doc /* @S271,S280,S289,S684 */ }
    part def TechnicalReviewers { doc /* @S158 */ }
    part def TechnicalTeams { doc /* @S433,S439 */ }
    part def Technicians { doc /* @S075,S429 */ }
    part def TemporaryConnections { doc /* @S335 */ }
    part def TemporaryPersonnel { doc /* @S849 */ }
    part def TestRequirements { doc /* @S750 */ }
    part def TimelyClosureOfCorrectiveActions { doc /* @S912 */ }
    part def Tools { doc /* @S895 */ }
    part def Transaction { doc /* @S821,S822 */ }
    part def Transfer { doc /* @S079,S196,S404,S565 */ }
    part def TransferArrangement { doc /* @S179 */ }
    part def Turbine { doc /* @S033,S034,S035,S444,S940 */ }
    part def TurbineAlarms { doc /* @S440 */ }
    part def TurbineController { doc /* @S005,S033,S060,S061,S127,S129,S130,S159,S191,S294,S299,S377,S545,S789,S937 */ }
    part def TurbineLockout { doc /* @S657,S802 */ }
    part def TurbineOperations { doc /* @S742 */ }
    part def TurbineResponse { doc /* @S305 */ }
    part def TurbineSensorBus { doc /* @S005,S251,S294,S788 */ }
    part def TurbineStructures { doc /* @S003 */ }
    part def Turbines { doc /* @S003 */ }
    part def Uncertainty { doc /* @S676,S682,S684 */ }
    part def Unnamed { doc /* @S151,S152,S162,S163,S165,S166,S168,S170,S171 */ }
    part def UnplannedMaintenance { doc /* @S018 */ }
    part def UrgentMessages { doc /* @S772 */ }
    part def UrgentPurchases { doc /* @S707 */ }
    part def Users { doc /* @S882 */ }
    part def Validation { doc /* @S846 */ }
    part def ValidationChecks { doc /* @S298 */ }
    part def VerbalRequest { doc /* @S818 */ }
    part def Verification { doc /* @S609 */ }
    part def VerifiedHeadcount { doc /* @S390 */ }
    part def Vessel { doc /* @S398,S399,S478,S488,S524,S582,S763 */ }
    part def VesselAISReceiver { doc /* @S105,S139,S140,S141,S225,S288,S400,S401,S749 */ }
    part def VesselCapability { doc /* @S659 */ }
    part def VesselCrews { doc /* @S075 */ }
    part def VesselMaster { doc /* @S079,S085,S161,S226,S278,S279,S284,S390,S398,S402,S403,S409,S476,S498,S524,S525,S567,S573,S577,S616,S634,S642,S677,S682,S763,S807,S944 */ }
    part def VesselMovements { doc /* @S681 */ }
    part def VesselOperatingProcedures { doc /* @S021 */ }
    part def VesselPersonnel { doc /* @S764 */ }
    part def VesselPlan { doc /* @S161 */ }
    part def VesselRecoverySupport { doc /* @S636 */ }
    part def Vessels { doc /* @S011 */ }
    part def Visibility { doc /* @S146,S662,S673 */ }
    part def Visitors { doc /* @S508,S849 */ }
    part def WarehouseSystem { doc /* @S091,S163,S241,S262,S478,S687,S928 */ }
    part def Weather { doc /* @S146,S285,S659 */ }
    part def WeatherAnalyst { doc /* @S084,S107,S232,S256,S272,S323,S472,S500,S521,S522,S626,S641,S669,S765,S939 */ }
    part def WeatherConditions { doc /* @S557 */ }
    part def WeatherHold { doc /* @S086,S259 */ }
    part def WeatherService { doc /* @S067,S083,S106,S128,S213,S230,S255,S270,S309,S443,S471,S521,S522,S624,S640,S748,S766,S939 */ }
    part def WeatherServices { doc /* @S024 */ }
    part def WestServiceLift { doc /* @S884,S907 */ }
    part def WindFarmAssets { doc /* @S002 */ }
    part def Window { doc /* @S738 */ }
    part def Work { doc /* @S011,S156,S251,S253,S265,S281,S291,S329,S330,S388,S426,S496,S500,S519,S581,S672,S685,S717,S727,S732 */ }
    part def WorkArea { doc /* @S336 */ }
    part def WorkArrangements { doc /* @S095 */ }
    part def WorkOnTheMainTransformer { doc /* @S744 */ }
    part def WorkPackages { doc /* @S159 */ }
    part def WorkParty { doc /* @S405,S713,S720,S733,S881 */ }
    part def WorkPermitPortal { doc /* @S070,S149,S155,S162,S169,S265,S321,S492,S713,S716,S728,S751,S780 */ }
    part def WorkPlan { doc /* @S228 */ }
    part def WorkScope { doc /* @S750 */ }
    part def WorkforceInterfaces { doc /* @S022 */ }
    part system {
        part abnormalCondition : AbnormalCondition {
            perform action a0 { doc /* may require intervention @S768 */ }
        }
        part abnormalElectricalCondition : AbnormalElectricalCondition {
            perform action a0 { doc /* occurs @S360 */ }
        }
        part access : Access {
            perform action a0 { doc /* influence the timing and conduct of work @S028 */ }
        }
        part accessConditions : AccessConditions {
            perform action a0 { doc /* change @S224 */ }
        }
        part accessManagement : AccessManagement;
        part accessRecords : AccessRecords {
            exhibit state modes {
                state s0 { doc /* available to authorized reviewers @S825 */ }
            }
        }
        part accountabilityRecords : AccountabilityRecords {
            perform action a0 { doc /* retain the time, location, responsible role, and disposition of each material movement @S414 */ }
        }
        part accountableOwner : AccountableOwner {
            perform action a0 { doc /* maintain the document @S959 */ }
            perform action a1 { doc /* coordinate its approval @S959 */ }
        }
        part actionsTaken : ActionsTaken;
        part activeRestrictions : ActiveRestrictions {
            perform action a0 { doc /* could conflict with lift operation @S871 */ }
        }
        part activeWorkAuthorizations : ActiveWorkAuthorizations {
            exhibit state modes {
                state s0 { doc /* current @S350 */ }
            }
        }
        part activity : Activity {
            perform action a0 { doc /* begins @S751 */ }
        }
        part actualConditions : ActualConditions {
            perform action a0 { doc /* make the planned sequence unsafe or incompatible with grid requirements @S755 */ }
        }
        part adjacentEquipment : AdjacentEquipment {
            perform action a0 { doc /* must remain energized or available for service @S715 */ }
            exhibit state modes {
                state s0 { doc /* available for service @S715 */ }
                state s1 { doc /* energized @S715 */ }
            }
        }
        part administrativeAccess : AdministrativeAccess {
            perform action a0 { doc /* requires authenticated individual accounts and role-based authorization @S115 */ }
        }
        part affectedActivity : AffectedActivity {
            perform action a0 { doc /* can continue @S579 */ }
        }
        part affectedEquipment : AffectedEquipment;
        part affectedServices : AffectedServices {
            exhibit state modes {
                state s0 { doc /* normal operation @S122 */ }
            }
        }
        part affectedTeams : AffectedTeams {
            perform action a0 { doc /* receive the update @S245 */ }
        }
        part affectedWork : AffectedWork {
            perform action a0 { doc /* resumes @S510 */ }
        }
        part alarmPriorities : AlarmPriorities {
            perform action a0 { doc /* distinguish immediate danger from supervisory faults @S796 */ }
        }
        part alarmThresholds : AlarmThresholds {
            perform action a0 { doc /* support both trend analysis and timely operational decisions @S108 */ }
        }
        part alarms : Alarms {
            perform action a0 { doc /* could affect export capability @S378 */ }
        }
        part alternative : Alternative {
            perform action a0 { doc /* meets the required interface and operating limits @S704 */ }
        }
        part alternativeAccessMethod : AlternativeAccessMethod {
            perform action a0 { doc /* changes resource demand @S292 */ }
        }
        part applicableHandlingRequirements : ApplicableHandlingRequirements;
        part approval : Approval {
            perform action a0 { doc /* identifies each isolation point, the required device position, and the person responsible for applying the control @S714 */ }
            perform action a1 { doc /* records any adjacent equipment that must remain energized or available for service @S715 */ }
        }
        part approvedElectricalConfiguration : ApprovedElectricalConfiguration {
            perform action a0 { doc /* explicitly supports it @S387 */ }
        }
        part approvedImprovements : ApprovedImprovements {
            perform action a0 { doc /* deliver the intended result @S932 */ }
            perform action a1 { doc /* do not introduce adverse effects @S932 */ }
        }
        part approvedProcedures : ApprovedProcedures;
        part approvedSwitchingWindow : ApprovedSwitchingWindow {
            exhibit state modes {
                state s0 { doc /* active @S753 */ }
                state s1 { doc /* available @S752 */ }
            }
        }
        part approvedWindow : ApprovedWindow;
        part architecture : Architecture {
            perform action a0 { doc /* assigns defined responsibilities to interfaces @S072 */ }
            perform action a1 { doc /* defined @S072 */ }
        }
        part area : Area {
            exhibit state modes {
                state s0 { doc /* safe @S801 */ }
            }
        }
        part areasRequiringCloserAssessment : AreasRequiringCloserAssessment {
            perform action a0 { doc /* requiring closer assessment @S445 */ }
        }
        part arrayOfTurbines : ArrayOfTurbines;
        part assetOperator : AssetOperator {
            perform action a0 { doc /* assigns an accountable owner to maintain the document and coordinate its approval @S959 */ }
        }
        part assignment : Assignment {
            exhibit state modes {
                state s0 { doc /* current @S407 */ }
            }
        }
        part assuranceArrangements : AssuranceArrangements {
            perform action a0 { doc /* provide sufficient evidence that the concept remains effective @S983 */ }
        }
        part assuranceEvidence : AssuranceEvidence;
        part attempt : Attempt {
            perform action a0 { doc /* receives a unique transaction identifier for later reference @S820 */ }
            exhibit state modes {
                state s0 { doc /* successful @S824 */ }
                state s1 { doc /* unsuccessful @S824 */ }
            }
        }
        part auditFindings : AuditFindings;
        part auditRecord : AuditRecord {
            perform action a0 { doc /* distinguishes a rejected credential from an authorization that lacks the required scope @S823 */ }
        }
        part authority : Authority {
            perform action a0 { doc /* approving access @S122 */ }
            perform action a1 { doc /* responding to alarms @S122 */ }
            perform action a2 { doc /* returning affected services to normal operation @S122 */ }
            perform action a3 { doc /* confirms that the equipment and work area are safe for subsequent activity @S657 */ }
        }
        part authorization : Authorization {
            perform action a0 { doc /* results in a denied entry decision @S815 */ }
            exhibit state modes {
                state s0 { doc /* active @S813 */ }
                state s1 { doc /* current @S407 */ }
                state s2 { doc /* expired @S815 */ }
                state s3 { doc /* incomplete @S815 */ }
                state s4 { doc /* suspended @S815 */ }
            }
        }
        part authorizationLifecycle : AuthorizationLifecycle {
            perform action a0 { doc /* begins when a work request is entered with its location, scope, planned duration, and responsible team @S151 */ }
        }
        part authorizationProcesses : AuthorizationProcesses {
            perform action a0 { doc /* govern work under controlled conditions @S070 */ }
        }
        part authorizedPersonnel : AuthorizedPersonnel {
            perform action a0 { doc /* using approved instructions and positive confirmation of equipment identity @S358 */ }
        }
        part authorizedShorePersonnel : AuthorizedShorePersonnel;
        part authorizedSwitchingPlan : AuthorizedSwitchingPlan {
            perform action a0 { doc /* requires a controlled change @S551 */ }
        }
        part automaticControls : AutomaticControls {
            perform action a0 { doc /* initiate the Emergency Generator start sequence @S177 */ }
        }
        part auxiliaryElectricalLoads : AuxiliaryElectricalLoads;
        part availableExportCapability : AvailableExportCapability {
            perform action a0 { doc /* falls below the active dispatch target @S372 */ }
        }
        part backupPower : BackupPower;
        part barrierControls : BarrierControls {
            perform action a0 { doc /* operate as intended @S854 */ }
        }
        part bladeCondition : BladeCondition {
            perform action a0 { doc /* requires review @S440 */ }
        }
        part bladeInspectionDrone : BladeInspectionDrone {
            perform action a0 { doc /* captures close-range visual observations of accessible blade surfaces @S142 */ }
            perform action a1 { doc /* can support inspection planning @S254 */ }
            perform action a2 { doc /* produces the Leading Edge Tile Image @S313 */ }
            perform action a3 { doc /* repeat a close-range pass @S314 */ }
            perform action a4 { doc /* assess the suspected surface condition @S314 */ }
            perform action a5 { doc /* capture repeatable views of blade surfaces @S444 */ }
        }
        part bladeSpecialist : BladeSpecialist {
            perform action a0 { doc /* plans inspection passes @S143 */ }
            perform action a1 { doc /* provide consistent coverage of areas selected for examination @S143 */ }
            perform action a2 { doc /* reviews available inspection evidence @S315 */ }
            perform action a3 { doc /* reports whether further examination is warranted @S315 */ }
            perform action a4 { doc /* reviews the tile image @S445 */ }
            perform action a5 { doc /* classify visible damage @S445 */ }
            perform action a6 { doc /* identify areas requiring closer assessment @S445 */ }
            perform action a7 { doc /* examines the affected surface using suitable lighting, measurement tools, and nondestructive inspection methods @S452 */ }
            perform action a8 { doc /* using suitable lighting, measurement tools, and nondestructive inspection methods @S452 */ }
            perform action a9 { doc /* distinguishes cosmetic damage from conditions that could affect structural integrity or safe turbine operation @S455 */ }
            perform action a10 { doc /* records the completed work @S463 */ }
            perform action a11 { doc /* verifies that the repaired area meets the applicable acceptance criteria @S463 */ }
            perform action a12 { doc /* identifies fragile blade components @S651 */ }
            perform action a13 { doc /* specifies padding or restraints @S651 */ }
            perform action a14 { doc /* prevent handling damage @S651 */ }
        }
        part boundaryRecords : BoundaryRecords {
            perform action a0 { doc /* are closed @S735 */ }
        }
        part cableCondition : CableCondition {
            perform action a0 { doc /* warrants inspection or corrective intervention @S252 */ }
        }
        part cancellation : Cancellation {
            perform action a0 { doc /* changes resource demand @S292 */ }
        }
        part car : Car {
            perform action a0 { doc /* cannot move while a door is open @S863 */ }
            perform action a1 { doc /* stops between landings @S902 */ }
            exhibit state modes {
                state s0 { doc /* level @S904 */ }
                state s1 { doc /* stationary @S904 */ }
                state s2 { doc /* stopped @S903 */ }
                state s3 { doc /* stopped between landings @S902 */ }
            }
        }
        part carFloor : CarFloor {
            exhibit state modes {
                state s0 { doc /* level with the boarding landing @S890 */ }
            }
        }
        part change : Change {
            perform action a0 { doc /* takes effect @S981 */ }
        }
        part changeThatCouldAffectThePassage : ChangeThatCouldAffectThePassage {
            perform action a0 { doc /* could affect the passage @S226 */ }
        }
        part changeToTheWorkScope : ChangeToTheWorkScope {
            perform action a0 { doc /* requires a renewed safety review @S510 */ }
        }
        part changes : Changes {
            perform action a0 { doc /* require documented impact assessment before approval @S960 */ }
            perform action a1 { doc /* could affect access, communications, or the integrity of operational records @S969 */ }
        }
        part changesToAccessRules : ChangesToAccessRules {
            perform action a0 { doc /* become effective at the entry point @S833 */ }
            exhibit state modes {
                state s0 { doc /* effective @S833 */ }
            }
        }
        part changesToTheTaskEquipmentStateOrWorkLocation : ChangesToTheTaskEquipmentStateOrWorkLocation {
            perform action a0 { doc /* require a review of the boundary @S727 */ }
        }
        part closeRangeVisualObservationsOfAccessibleBladeSurfaces : CloseRangeVisualObservationsOfAccessibleBladeSurfaces {
            perform action a0 { doc /* supplement field assessment @S147 */ }
            perform action a1 { doc /* do not replace required physical inspections @S147 */ }
        }
        part commands : Commands {
            perform action a0 { doc /* conflict with active protection conditions @S127 */ }
        }
        part communicationChannel : CommunicationChannel {
            exhibit state modes {
                state s0 { doc /* unavailable @S771 */ }
            }
        }
        part communications : Communications {
            perform action a0 { doc /* fail @S535 */ }
            perform action a1 { doc /* deteriorates @S659 */ }
            exhibit state modes {
                state s0 { doc /* unavailable @S413 */ }
            }
        }
        part competenceRecords : CompetenceRecords;
        part completionOfRequiredControls : CompletionOfRequiredControls;
        part concept : Concept {
            perform action a0 { doc /* defines the operational scope and principal interfaces for operating and maintaining the offshore wind farm @S001 */ }
            perform action a1 { doc /* supports safe isolation, removal planning, and transfer of residual operational records to the responsible organization @S019 */ }
            perform action a2 { doc /* also recognizes grid, emergency response, communications, and port support as external or enabling capabilities @S050 */ }
            perform action a3 { doc /* remains effective @S983 */ }
        }
        part condition : Condition {
            perform action a0 { doc /* could affect export capability or compliance with grid instructions @S362 */ }
            perform action a1 { doc /* threatens equipment limits, protection coordination, or safe operation @S560 */ }
            perform action a2 { doc /* could compromise safe movement @S883 */ }
            perform action a3 { doc /* could compromise safe movement @S907 */ }
        }
        part conditionData : ConditionData {
            perform action a0 { doc /* helps distinguish developing degradation from transient alarms @S250 */ }
        }
        part conditionEvidence : ConditionEvidence {
            perform action a0 { doc /* justify the required outage or vessel time @S249 */ }
        }
        part conditionInformation : ConditionInformation {
            perform action a0 { doc /* can help distinguish a developing equipment fault from a confirmed fire alarm @S793 */ }
        }
        part conditions : Conditions {
            perform action a0 { doc /* may affect the plan @S232 */ }
            perform action a1 { doc /* could invalidate a planned access period @S256 */ }
            perform action a2 { doc /* exceed the approved operating limits @S259 */ }
            perform action a3 { doc /* requiring work to stop @S330 */ }
            perform action a4 { doc /* require a reduced transfer level @S381 */ }
            perform action a5 { doc /* could affect structural integrity or safe turbine operation @S455 */ }
            perform action a6 { doc /* permit work to proceed @S500 */ }
            perform action a7 { doc /* could affect the planned sequence @S522 */ }
            perform action a8 { doc /* differ from the plan @S535 */ }
            perform action a9 { doc /* exceed the approved operating envelope @S634 */ }
            perform action a10 { doc /* could affect safe vessel handling @S641 */ }
            perform action a11 { doc /* would require a decision to pause or defer work @S669 */ }
        }
        part conditionsThatMayAffectMarineOperations : ConditionsThatMayAffectMarineOperations {
            perform action a0 { doc /* could affect access, lifting, or work at height @S765 */ }
        }
        part conditionsThatMayAffectVesselAccessOrTurbineWork : ConditionsThatMayAffectVesselAccessOrTurbineWork {
            perform action a0 { doc /* may affect vessel access or turbine work @S107 */ }
        }
        part confidence : Confidence {
            perform action a0 { doc /* falls below its configured threshold @S105 */ }
        }
        part configurationBaseline : ConfigurationBaseline {
            perform action a0 { doc /* records software versions, configuration parameters, dependencies, and applicable hardware revisions @S589 */ }
        }
        part configuredIdentityAndAuthorizationChecks : ConfiguredIdentityAndAuthorizationChecks {
            perform action a0 { doc /* pass @S819 */ }
        }
        part confirmedFaults : ConfirmedFaults {
            perform action a0 { doc /* threaten personnel safety @S248 */ }
            perform action a1 { doc /* cause substantial generation loss @S248 */ }
            perform action a2 { doc /* receive priority over routine inspections @S248 */ }
        }
        part confirmedFireCondition : ConfirmedFireCondition {
            perform action a0 { doc /* requires turbine protection @S789 */ }
        }
        part contextualConditions : ContextualConditions {
            perform action a0 { doc /* help reviewers distinguish environmental effects from equipment deterioration @S309 */ }
        }
        part contingencyProcess : ContingencyProcess {
            perform action a0 { doc /* requires a named approver and a recorded reason for any temporary access decision @S829 */ }
        }
        part continuedResponse : ContinuedResponse {
            perform action a0 { doc /* would expose rescuers to unacceptable risk @S633 */ }
        }
        part control : Control {
            perform action a0 { doc /* provides a consistent basis for admitting authorized personnel and explaining each access decision @S834 */ }
        }
        part controlEngineer : ControlEngineer {
            perform action a0 { doc /* uses the shore-based operational picture @S063 */ }
            perform action a1 { doc /* assess equipment status @S063 */ }
            perform action a2 { doc /* coordinate response @S063 */ }
            perform action a3 { doc /* reviews alarms and operating conditions @S135 */ }
            perform action a4 { doc /* issuing a remote command @S135 */ }
            perform action a5 { doc /* reviews persistent alarms @S193 */ }
            perform action a6 { doc /* coordinates electrical support with the Substation Operator @S193 */ }
            perform action a7 { doc /* verifies that dispatch changes are reflected in the applicable control settings before implementation @S217 */ }
            perform action a8 { doc /* reviews alarms alongside recent operating trends @S297 */ }
            perform action a9 { doc /* treating an isolated threshold crossing as a confirmed fault @S297 */ }
            perform action a10 { doc /* compares disputed readings with independent signals from the Turbine Controller and Nacelle Condition Monitor where available @S299 */ }
            perform action a11 { doc /* records the evidence considered and the basis for accepting, rejecting, or continuing to monitor an alert @S302 */ }
            perform action a12 { doc /* accepting @S302 */ }
            perform action a13 { doc /* rejecting @S302 */ }
            perform action a14 { doc /* continuing to monitor an alert @S302 */ }
            perform action a15 { doc /* follows the approved operating procedure @S305 */ }
            perform action a16 { doc /* confirms the resulting state through available indications @S305 */ }
            perform action a17 { doc /* requests an on-site inspection @S310 */ }
            perform action a18 { doc /* reassesses the alert @S316 */ }
            perform action a19 { doc /* reviews the restored equipment state @S338 */ }
            perform action a20 { doc /* confirms that required operational checks are complete @S338 */ }
            perform action a21 { doc /* investigates unexplained discrepancies @S349 */ }
            perform action a22 { doc /* reviews each instruction for consistency with current plant status @S368 */ }
            perform action a23 { doc /* applying it @S368 */ }
            perform action a24 { doc /* confirms that the control response follows the instruction and remains within the permitted ramp rate @S375 */ }
            perform action a25 { doc /* records the reason for any temporary deviation from the requested output and the action taken @S384 */ }
            perform action a26 { doc /* use individually assigned accounts rather than shared credentials for interactive work @S423 */ }
            perform action a27 { doc /* coordinate any operational changes with the relevant duty role before implementation @S434 */ }
            perform action a28 { doc /* checks the current network configuration @S516 */ }
            perform action a29 { doc /* confirms that the proposed sequence supports the approved work @S516 */ }
            perform action a30 { doc /* prepares clear switching instructions with one action per step and an explicit hold point where needed @S528 */ }
            perform action a31 { doc /* is issued @S533 */ }
            perform action a32 { doc /* monitors available indications @S534 */ }
            perform action a33 { doc /* confirms that each reported state change matches the approved sequence @S534 */ }
            perform action a34 { doc /* is paused @S535 */ }
            perform action a35 { doc /* is left in a safe state @S535 */ }
            perform action a36 { doc /* verifies the permitted level, its effective time, and any required ramp rate @S542 */ }
            perform action a37 { doc /* changing operating targets @S542 */ }
            perform action a38 { doc /* reduces active power in controlled steps @S544 */ }
            perform action a39 { doc /* checks that measured export follows the revised target @S544 */ }
            perform action a40 { doc /* compares actual export with the permitted level @S552 */ }
            perform action a41 { doc /* investigates any persistent mismatch @S552 */ }
            perform action a42 { doc /* escalates any condition that threatens equipment limits, protection coordination, or safe operation @S560 */ }
            perform action a43 { doc /* confirms authorization @S562 */ }
            perform action a44 { doc /* restores output gradually @S562 */ }
            perform action a45 { doc /* monitoring equipment response @S562 */ }
            perform action a46 { doc /* confirms that proposed changes have a clear operational purpose and defined scope @S594 */ }
            perform action a47 { doc /* supports remote shutdown actions @S630 */ }
            perform action a48 { doc /* provides technical guidance @S658 */ }
            perform action a49 { doc /* checks that remote indications agree with the approved switching state @S718 */ }
            perform action a50 { doc /* authorizing access @S718 */ }
            perform action a51 { doc /* verifies the restoration state @S734 */ }
            perform action a52 { doc /* communicates any remaining operational limitation to affected personnel @S734 */ }
            perform action a53 { doc /* checks that turbine operations can be managed safely while the substation work is in progress @S742 */ }
            perform action a54 { doc /* reviews alarms and operating trends with the SCADA Engineer @S768 */ }
            perform action a55 { doc /* verifies the equipment state @S799 */ }
            perform action a56 { doc /* checks that protection actions have completed @S799 */ }
            perform action a57 { doc /* authorizing any further operational action @S799 */ }
            perform action a58 { doc /* examines significant operational deviations @S920 */ }
            perform action a59 { doc /* records the technical findings for review @S920 */ }
            perform action a60 { doc /* suspends those commands @S938 */ }
            perform action a61 { doc /* uses approved local procedures @S938 */ }
            perform action a62 { doc /* coordinates technical recovery with the relevant field and shore roles @S951 */ }
            perform action a63 { doc /* reviews control-room practices @S964 */ }
            perform action a64 { doc /* confirms that operational procedures remain consistent with the concept @S964 */ }
        }
        part controlFunctions : ControlFunctions;
        part controlResponse : ControlResponse {
            perform action a0 { doc /* follows the instruction @S375 */ }
            perform action a1 { doc /* remains within the permitted ramp rate @S375 */ }
        }
        part controlRoomDecisions : ControlRoomDecisions {
            perform action a0 { doc /* affecting the farm interface @S214 */ }
        }
        part controlRoomStaff : ControlRoomStaff {
            perform action a0 { doc /* use the same revision @S729 */ }
            perform action a1 { doc /* confirming isolation status @S729 */ }
        }
        part controlTeam : ControlTeam;
        part controlledBoundary : ControlledBoundary {
            perform action a0 { doc /* permits only approved protocols, destinations, and service accounts @S112 */ }
        }
        part controlledLifecycle : ControlledLifecycle {
            perform action a0 { doc /* protects the integrity and availability of operational systems @S587 */ }
        }
        part controls : Controls {
            perform action a0 { doc /* respond correctly @S892 */ }
        }
        part converterCabinet : ConverterCabinet {
            perform action a0 { doc /* manages electrical conversion @S131 */ }
            perform action a1 { doc /* observing equipment limits and protective interlocks @S131 */ }
            perform action a2 { doc /* remains within its electrical and thermal ratings throughout the reduction @S547 */ }
        }
        part correctedSensorData : CorrectedSensorData {
            perform action a0 { doc /* become available @S316 */ }
        }
        part corrections : Corrections {
            perform action a0 { doc /* preserve the original entry @S777 */ }
            perform action a1 { doc /* identify the person making the change @S777 */ }
            perform action a2 { doc /* state the reason for the correction @S777 */ }
        }
        part credential : Credential {
            exhibit state modes {
                state s0 { doc /* active @S840 */ }
                state s1 { doc /* rejected @S823 */ }
            }
        }
        part credentialReaders : CredentialReaders {
            perform action a0 { doc /* operate as intended @S854 */ }
        }
        part crew : Crew {
            perform action a0 { doc /* starts work @S167 */ }
            perform action a1 { doc /* confirms that the marked limits match the current isolation points and the approved maintenance scope @S495 */ }
            perform action a2 { doc /* starting @S504 */ }
            perform action a3 { doc /* inspects personal protective equipment, communications equipment, and rescue equipment for serviceability @S504 */ }
            perform action a4 { doc /* tests the required radio channel with the Operations Radio Console @S506 */ }
            perform action a5 { doc /* separating into work teams @S506 */ }
            perform action a6 { doc /* maintains clear access to fire equipment, escape routes, and lifting areas throughout the task @S511 */ }
            perform action a7 { doc /* can maintain adequate visual awareness @S678 */ }
            perform action a8 { doc /* proceeding @S721 */ }
        }
        part crewAccountability : CrewAccountability {
            perform action a0 { doc /* covers personnel movement between shore facilities, vessels, offshore structures, and the return journey @S391 */ }
        }
        part crewChanges : CrewChanges {
            perform action a0 { doc /* occur during transit or between offshore locations @S403 */ }
        }
        part crewMember : CrewMember {
            perform action a0 { doc /* understands the limits of the approved work area @S726 */ }
        }
        part crewTransferVessel : CrewTransferVessel {
            perform action a0 { doc /* may support offshore work @S045 */ }
            perform action a1 { doc /* transports authorized personnel and routine tools between shore and offshore work locations @S087 */ }
            perform action a2 { doc /* reports its approach and departure status in accordance with the approved marine coordination procedure @S215 */ }
            perform action a3 { doc /* proceeds only when the Vessel Master considers the approach and transfer conditions acceptable @S279 */ }
            perform action a4 { doc /* uses the Harness Audit Card @S312 */ }
            perform action a5 { doc /* verify the applicable equipment checks @S312 */ }
            perform action a6 { doc /* operate in the same transfer sequence @S568 */ }
            perform action a7 { doc /* transports personnel and small equipment @S643 */ }
            perform action a8 { doc /* remain clear of a transfer location @S678 */ }
            perform action a9 { doc /* can maintain adequate visual awareness @S678 */ }
        }
        part currentStatus : CurrentStatus;
        part curtailment : Curtailment {
            perform action a0 { doc /* is stressing equipment @S556 */ }
        }
        part cybersecurity : Cybersecurity;
        part cybersecurityAnalyst : CybersecurityAnalyst {
            perform action a0 { doc /* monitors gateway events for unusual access patterns and configuration changes @S117 */ }
            perform action a1 { doc /* reviews alerts @S419 */ }
            perform action a2 { doc /* assesses their operational significance @S419 */ }
            perform action a3 { doc /* escalates urgent concerns to the on-duty operations lead @S419 */ }
            perform action a4 { doc /* produces the Firmware Hash Attestation for controlled software releases @S428 */ }
            perform action a5 { doc /* preserves relevant logs and technical evidence @S435 */ }
            perform action a6 { doc /* limiting access to personnel assigned to the investigation @S435 */ }
            perform action a7 { doc /* protects access logs and communication records against unauthorized alteration or disclosure @S781 */ }
            perform action a8 { doc /* reviews performance records for evidence that cybersecurity controls affect operational availability or recovery @S929 */ }
            perform action a9 { doc /* assesses changes that could affect access, communications, or the integrity of operational records @S969 */ }
        }
        part cybersecurityControls : CybersecurityControls {
            perform action a0 { doc /* affect operational availability or recovery @S929 */ }
        }
        part cybersecurityGateway : CybersecurityGateway {
            perform action a0 { doc /* provides a security boundary for connected operational services @S071 */ }
            perform action a1 { doc /* establishes a controlled boundary between authorized shore-side services and offshore operational networks @S111 */ }
            perform action a2 { doc /* blocks a route change @S287 */ }
            perform action a3 { doc /* uses the revocation receipt @S357 */ }
            perform action a4 { doc /* support access control during routine account and session reviews @S357 */ }
            perform action a5 { doc /* monitors traffic between operational networks and approved external connections @S416 */ }
        }
        part cybersecurityOperations : CybersecurityOperations {
            perform action a0 { doc /* protect the wind farm control environment @S415 */ }
            perform action a1 { doc /* supporting safe and reliable production @S415 */ }
        }
        part cybersecurityRelatedWorkItem : CybersecurityRelatedWorkItem;
        part damagedOrContaminatedItems : DamagedOrContaminatedItems {
            perform action a0 { doc /* cannot create hazards for personnel or other cargo @S653 */ }
        }
        part daughterCraft : DaughterCraft {
            perform action a0 { doc /* may support offshore work @S045 */ }
            perform action a1 { doc /* can support short-range transfers when the operating plan and conditions permit its use @S088 */ }
            perform action a2 { doc /* operate in the same transfer sequence @S568 */ }
            perform action a3 { doc /* may support a local response @S621 */ }
        }
        part daughterCraftOperation : DaughterCraftOperation;
        part decisionRecords : DecisionRecords {
            perform action a0 { doc /* capture the forecast basis, applicable limits, observed conditions, and the reason for proceeding, holding, or returning to port @S293 */ }
        }
        part decisions : Decisions {
            perform action a0 { doc /* remain traceable @S365 */ }
        }
        part defect : Defect {
            perform action a0 { doc /* affecting safe operation @S870 */ }
            perform action a1 { doc /* prevents release until the required repair and verification are complete @S870 */ }
        }
        part defectHistory : DefectHistory {
            perform action a0 { doc /* warrants it @S464 */ }
        }
        part defectRecords : DefectRecords {
            perform action a0 { doc /* describe location, dimensions, orientation, suspected cause, confidence, and any change from earlier observations @S453 */ }
        }
        part deferredTaskRationale : DeferredTaskRationale {
            perform action a0 { doc /* supports later reprioritization @S286 */ }
            perform action a1 { doc /* implying that the task is safe under the current conditions @S286 */ }
        }
        part delay : Delay {
            perform action a0 { doc /* changes resource demand @S292 */ }
            perform action a1 { doc /* threatens the agreed end time @S754 */ }
        }
        part deliveredEnergy : DeliveredEnergy;
        part deliveryLocation : DeliveryLocation;
        part denial : Denial {
            perform action a0 { doc /* directs the person to contact the Field Supervisor or the HSE Officer for review @S817 */ }
        }
        part deployment : Deployment {
            perform action a0 { doc /* begins @S608 */ }
        }
        part designatedApprover : DesignatedApprover {
            perform action a0 { doc /* confirms that comments are resolved or explicitly accepted before the revised baseline is released @S979 */ }
        }
        part designatedAuthorizingRole : DesignatedAuthorizingRole {
            perform action a0 { doc /* grants permission @S165 */ }
        }
        part designatedGridConnectionPoint : DesignatedGridConnectionPoint;
        part detectionCoverage : DetectionCoverage;
        part detectorSignal : DetectorSignal {
            perform action a0 { doc /* has returned to normal @S797 */ }
            exhibit state modes {
                state s0 { doc /* normal @S797 */ }
            }
        }
        part differenceBetweenTheExpectedAndObservedCount : DifferenceBetweenTheExpectedAndObservedCount {
            exhibit state modes {
                state s0 { doc /* unresolved @S575 */ }
            }
        }
        part differencesBetweenObservationTimesAndLocations : DifferencesBetweenObservationTimesAndLocations {
            perform action a0 { doc /* can leave uncertainty @S663 */ }
        }
        part discrepancy : Discrepancy {
            perform action a0 { doc /* prompts review of the observation age, location, and surrounding weather conditions @S666 */ }
            exhibit state modes {
                state s0 { doc /* unresolved @S583 */ }
            }
        }
        part dispatchRecord : DispatchRecord {
            perform action a0 { doc /* identifies the quantity, destination, handling conditions, and responsible receiving location @S708 */ }
        }
        part documentOwner : DocumentOwner {
            perform action a0 { doc /* schedules periodic review @S976 */ }
            perform action a1 { doc /* initiates an additional review after material operational, technical, or regulatory change @S976 */ }
        }
        part documentedImpactAssessment : DocumentedImpactAssessment {
            perform action a0 { doc /* considers effects on personnel safety, marine coordination, electrical safety, availability, cybersecurity, and regulatory obligations @S961 */ }
        }
        part door : Door {
            exhibit state modes {
                state s0 { doc /* open @S863 */ }
            }
        }
        part doorInterlocks : DoorInterlocks {
            exhibit state modes {
                state s0 { doc /* functional @S893 */ }
            }
        }
        part doors : Doors {
            exhibit state modes {
                state s0 { doc /* fully closed @S898 */ }
            }
        }
        part dueDate : DueDate {
            perform action a0 { doc /* justify the required outage or vessel time @S249 */ }
        }
        part durationOfGridRelatedRestrictions : DurationOfGridRelatedRestrictions;
        part dutyPlanner : DutyPlanner {
            perform action a0 { doc /* uses the Maintenance Planning Engine @S065 */ }
            perform action a1 { doc /* prepare @S065 */ }
            perform action a2 { doc /* review maintenance activities @S065 */ }
            perform action a3 { doc /* develops daily work priorities with input from the Field Supervisor and the Maintenance Planning Engine @S076 */ }
            perform action a4 { doc /* prepares the Transfer Manifest Addendum @S126 */ }
            perform action a5 { doc /* capture approved vessel deployment changes @S126 */ }
            perform action a6 { doc /* reviews the request for completeness @S153 */ }
            perform action a7 { doc /* assigns it to the appropriate planning queue @S153 */ }
            perform action a8 { doc /* resolves outstanding supply and scheduling issues @S164 */ }
            perform action a9 { doc /* submitting the request for authorization @S164 */ }
            perform action a10 { doc /* updates work priorities @S224 */ }
            perform action a11 { doc /* reviews the ranked queue @S247 */ }
            perform action a12 { doc /* confirms that urgent work has a clear technical basis and a feasible execution path @S247 */ }
            perform action a13 { doc /* considers Crew Transfer Vessel, Daughter Craft, Service Operations Vessel, and Helideck access @S258 */ }
            perform action a14 { doc /* selecting a mobilization method @S258 */ }
            perform action a15 { doc /* confirms the operating priority @S260 */ }
            perform action a16 { doc /* accounts for part availability, technician competence, and estimated task duration @S263 */ }
            perform action a17 { doc /* committing a work window @S263 */ }
            perform action a18 { doc /* revises priorities @S269 */ }
            perform action a19 { doc /* communicates the resulting plan to affected teams @S269 */ }
            perform action a20 { doc /* checks that the expected conditions remain within the limits for the task, transfer method, and vessel @S274 */ }
            perform action a21 { doc /* adjusts the executable plan @S292 */ }
            perform action a22 { doc /* reviews accepted alerts for immediate response needs and for effects on the executable maintenance plan @S304 */ }
            perform action a23 { doc /* submits a defined task scope, work location, crew, and requested operating window for review @S319 */ }
            perform action a24 { doc /* coordinates any revised work window with the relevant operational roles @S334 */ }
            perform action a25 { doc /* closes the work authorization @S340 */ }
            perform action a26 { doc /* considers active dispatch constraints @S388 */ }
            perform action a27 { doc /* scheduling work that would reduce generation or access to export equipment @S388 */ }
            perform action a28 { doc /* verifies that planned crew assignments match the approved work schedule @S396 */ }
            perform action a29 { doc /* confirms the inspection priority @S442 */ }
            perform action a30 { doc /* coordinates access with the Marine Coordinator or the Field Supervisor @S442 */ }
            perform action a31 { doc /* assigns a target repair window @S459 */ }
            perform action a32 { doc /* coordinates required personnel, equipment, and vessel capacity @S459 */ }
            perform action a33 { doc /* updates the maintenance record @S464 */ }
            perform action a34 { doc /* schedules follow-up inspection @S464 */ }
            perform action a35 { doc /* compares task readiness with the expected departure window @S469 */ }
            perform action a36 { doc /* committing crews and equipment to a marine campaign @S469 */ }
            perform action a37 { doc /* checks that the planned task matches the approved work authorization and that required personnel and equipment are available @S491 */ }
            perform action a38 { doc /* develops the proposed sequence with the Control Engineer @S515 */ }
            perform action a39 { doc /* identifies affected equipment and operating limits @S515 */ }
            perform action a40 { doc /* reassess the sequence @S519 */ }
            perform action a41 { doc /* obtain revised authorization @S519 */ }
            perform action a42 { doc /* records the proposed sequence, required approvals, execution roles, and planned communications in the operating record @S527 */ }
            perform action a43 { doc /* authorizes restoration or release of the work area @S536 */ }
            perform action a44 { doc /* records the final equipment state, approvals, deviations, and handover information for the incoming shift @S537 */ }
            perform action a45 { doc /* treats a confirmed restriction as a Grid Constraint @S539 */ }
            perform action a46 { doc /* records the revised operating basis @S553 */ }
            perform action a47 { doc /* coordinates updated targets @S553 */ }
            perform action a48 { doc /* maintains a clear record of the restriction, response actions, approvals, and outstanding checks for shift handover @S561 */ }
            perform action a49 { doc /* confirms that the recovery task does not conflict with other offshore work @S639 */ }
            perform action a50 { doc /* uses the Visibility Confidence Note @S669 */ }
            perform action a51 { doc /* considering task readiness and the conditions that would require a decision to pause or defer work @S669 */ }
            perform action a52 { doc /* reviews forecast demand against current stock @S695 */ }
            perform action a53 { doc /* confirming work readiness @S695 */ }
            perform action a54 { doc /* consolidates proposed work periods @S737 */ }
            perform action a55 { doc /* identifies tasks that require a change to substation configuration @S737 */ }
            perform action a56 { doc /* records actual start and finish times @S758 */ }
            perform action a57 { doc /* improve future estimates and coordination @S758 */ }
            perform action a58 { doc /* links relevant communications and work records to the applicable work package and operating plan @S779 */ }
            perform action a59 { doc /* confirms that the planned work can proceed within the lift capacity and operating limits @S872 */ }
            perform action a60 { doc /* uses reliability findings @S925 */ }
            perform action a61 { doc /* adjust work priorities and planned maintenance intervals when justified @S925 */ }
            perform action a62 { doc /* can prioritize urgent safety work and maintainable generation capacity @S947 */ }
            perform action a63 { doc /* updates operating priorities and deferred work @S955 */ }
            perform action a64 { doc /* checks that maintenance priorities, resource plans, and operational constraints are reflected in planned work @S965 */ }
        }
        part eastServiceLift : EastServiceLift {
            perform action a0 { doc /* runs a door-interlock and overload check @S859 */ }
            perform action a1 { doc /* accepting a movement request @S859 */ }
        }
        part electricalAbsenceOfVoltageChecks : ElectricalAbsenceOfVoltageChecks {
            perform action a0 { doc /* are performed at the work location using suitable, tested equipment @S724 */ }
            perform action a1 { doc /* using suitable, tested equipment @S724 */ }
        }
        part electricalEnclosures : ElectricalEnclosures;
        part electricalRecoveryWork : ElectricalRecoveryWork;
        part electricalTechnician : ElectricalTechnician {
            perform action a0 { doc /* verifies protective device settings and transfer interlocks during planned maintenance @S185 */ }
            perform action a1 { doc /* identifies the electrical sources, isolation points, and verification steps required by the approved scope @S325 */ }
            perform action a2 { doc /* verifies the relevant local isolation @S327 */ }
            perform action a3 { doc /* secures the equipment against unintended energization @S327 */ }
            perform action a4 { doc /* proves the test instrument @S331 */ }
            perform action a5 { doc /* tests for absence of voltage @S331 */ }
            perform action a6 { doc /* proves the instrument again @S331 */ }
            perform action a7 { doc /* checks that the work area is ready for restoration @S336 */ }
            perform action a8 { doc /* reports any outstanding defects or restrictions @S336 */ }
            perform action a9 { doc /* supports fault diagnosis and maintenance under the applicable work authorization and isolation controls @S363 */ }
            perform action a10 { doc /* coordinate any operational changes with the relevant duty role before implementation @S434 */ }
            perform action a11 { doc /* verifies electrical isolation at the work location @S496 */ }
            perform action a12 { doc /* verifies equipment labels @S529 */ }
            perform action a13 { doc /* confirms the intended switching points before execution @S529 */ }
            perform action a14 { doc /* isolates @S650 */ }
            perform action a15 { doc /* protects recovered electrical equipment @S650 */ }
            perform action a16 { doc /* uses the boundary sketch @S716 */ }
            perform action a17 { doc /* identify the approved isolation points @S716 */ }
            perform action a18 { doc /* starting the work @S716 */ }
            perform action a19 { doc /* confirms that the work scope and test requirements fit the approved duration @S750 */ }
            perform action a20 { doc /* confirmed by the responsible Substation Operator or Electrical Technician @S770 */ }
            perform action a21 { doc /* performs local inspection @S801 */ }
            perform action a22 { doc /* verifies that the lift supply and protective devices show no active fault indication @S867 */ }
        }
        part emergencyArrangements : EmergencyArrangements {
            perform action a0 { doc /* define who may direct an incident, who supports rescue, and who may authorize a return to work @S612 */ }
        }
        part emergencyDistributionBus : EmergencyDistributionBus;
        part emergencyEgress : EmergencyEgress {
            perform action a0 { doc /* remains available without requiring an access credential from the inside of the route @S857 */ }
            perform action a1 { doc /* without requiring an access credential from the inside of the route @S857 */ }
            exhibit state modes {
                state s0 { doc /* available @S857 */ }
            }
        }
        part emergencyGenerator : EmergencyGenerator {
            perform action a0 { doc /* supplies the designated emergency distribution bus @S180 */ }
            perform action a1 { doc /* support turbine export production @S180 */ }
            perform action a2 { doc /* does not start @S183 */ }
            perform action a3 { doc /* stabilize @S183 */ }
            perform action a4 { doc /* can start @S186 */ }
            perform action a5 { doc /* accept its expected load @S186 */ }
            perform action a6 { doc /* operate for the required test duration @S186 */ }
            perform action a7 { doc /* produces the Start Test Trace during its scheduled functional test @S353 */ }
            perform action a8 { doc /* fails to start or sustain its required load @S356 */ }
            perform action a9 { doc /* start @S356 */ }
            perform action a10 { doc /* sustain its required load @S356 */ }
            perform action a11 { doc /* supports essential functions @S803 */ }
            perform action a12 { doc /* remain essential services during degraded operation @S945 */ }
        }
        part emergencyResponseOrganizations : EmergencyResponseOrganizations;
        part emergencySource : EmergencySource {
            perform action a0 { doc /* can be unloaded safely @S196 */ }
        }
        part emergencyStop : EmergencyStop {
            exhibit state modes {
                state s0 { doc /* accessible @S892 */ }
            }
        }
        part enablingFunctions : EnablingFunctions {
            perform action a0 { doc /* support controlled and secure operations @S049 */ }
        }
        part endTime : EndTime;
        part energyProductionMeasures : EnergyProductionMeasures;
        part energySources : EnergySources {
            exhibit state modes {
                state s0 { doc /* safe @S711 */ }
            }
        }
        part entrant : Entrant {
            perform action a0 { doc /* presents an individually assigned credential for validation @S839 */ }
        }
        part entries : Entries {
            perform action a0 { doc /* distinguish observed facts from estimates, assumptions, and recommendations @S775 */ }
        }
        part entryPart : Entry {
            exhibit state modes {
                state s0 { doc /* denied @S845 */ }
                state s1 { doc /* permitted @S845 */ }
            }
        }
        part entryBarrier : EntryBarrier {
            perform action a0 { doc /* remains closed when validation fails or the scanner cannot complete a check @S846 */ }
            exhibit state modes {
                state s0 { doc /* closed @S846 */ }
            }
        }
        part environmentalLimits : EnvironmentalLimits {
            perform action a0 { doc /* make a planned movement or transfer unsafe @S233 */ }
        }
        part environmentalObservations : EnvironmentalObservations {
            perform action a0 { doc /* support safe farm operations @S100 */ }
        }
        part equipment : Equipment {
            perform action a0 { doc /* returns to service only when operating personnel accept the restored condition and any applicable restrictions are communicated @S341 */ }
            exhibit state modes {
                state s0 { doc /* Turbine Lockout @S328 */ }
                state s1 { doc /* available @S736 */ }
                state s2 { doc /* properly identified @S876 */ }
                state s3 { doc /* ready @S876 */ }
                state s4 { doc /* safe @S711 */ }
                state s5 { doc /* safe state @S535 */ }
                state s6 { doc /* service @S341 */ }
            }
        }
        part equipmentCondition : EquipmentCondition {
            perform action a0 { doc /* influence the timing and conduct of work @S028 */ }
        }
        part equipmentState : EquipmentState {
            perform action a0 { doc /* has been confirmed @S735 */ }
        }
        part equipmentStatus : EquipmentStatus {
            perform action a0 { doc /* makes flight unsafe @S146 */ }
            exhibit state modes {
                state s0 { doc /* uncertain @S348 */ }
            }
        }
        part estimate : Estimate {
            perform action a0 { doc /* represents conditions at the intended work location @S667 */ }
        }
        part eventPart : Event {
            perform action a0 { doc /* may affect electrical operation @S307 */ }
            perform action a1 { doc /* require coordination beyond the turbine @S307 */ }
        }
        part eventInvestigations : EventInvestigations;
        part evidence : Evidence {
            perform action a0 { doc /* indicates a developing hazard @S303 */ }
        }
        part expectedLoad : ExpectedLoad;
        part expectedOperatingState : ExpectedOperatingState;
        part expectedPersonnelCount : ExpectedPersonnelCount;
        part exportCable : ExportCable;
        part exportCableMonitor : ExportCableMonitor {
            perform action a0 { doc /* provides measurements that support assessment of the export path @S200 */ }
            perform action a1 { doc /* helps planners assess whether cable condition warrants inspection or corrective intervention @S252 */ }
        }
        part exportEquipment : ExportEquipment {
            perform action a0 { doc /* remains within its approved operating range @S549 */ }
        }
        part exportRestriction : ExportRestriction {
            perform action a0 { doc /* may arise from a grid instruction, a cable condition, or a substation operating limit @S538 */ }
            perform action a1 { doc /* changes @S553 */ }
            perform action a2 { doc /* affects planned work or equipment availability @S554 */ }
            exhibit state modes {
                state s0 { doc /* Grid Constraint @S539 */ }
            }
        }
        part exportSystem : ExportSystem;
        part externalInterfaces : ExternalInterfaces;
        part externalOrganizations : ExternalOrganizations;
        part externalTransmissionSystem : ExternalTransmissionSystem;
        part externalWork : ExternalWork {
            perform action a0 { doc /* affects the achievable start time @S748 */ }
        }
        part facility : Facility;
        part failureAnalyses : FailureAnalyses {
            perform action a0 { doc /* use available operating history, inspection findings, and maintenance records @S923 */ }
            perform action a1 { doc /* identify credible causes @S923 */ }
        }
        part farmMonitoringEnvironment : FarmMonitoringEnvironment;
        part fault : Fault {
            perform action a0 { doc /* causing unnecessary disconnection of healthy farm equipment @S208 */ }
        }
        part fieldFindings : FieldFindings {
            perform action a0 { doc /* become available @S316 */ }
        }
        part fieldSupervisor : FieldSupervisor {
            perform action a0 { doc /* coordinates task execution offshore @S096 */ }
            perform action a1 { doc /* keeps the Duty Planner informed of changes to work progress @S096 */ }
            perform action a2 { doc /* considers remote observations alongside site conditions @S145 */ }
            perform action a3 { doc /* recommending follow-up work @S145 */ }
            perform action a4 { doc /* verifies that the approved conditions remain valid @S167 */ }
            perform action a5 { doc /* checks reported faults against available evidence @S253 */ }
            perform action a6 { doc /* identifies work that requires an offshore visit @S253 */ }
            perform action a7 { doc /* confirms that the proposed method, access arrangements, and work party are suitable for the task @S320 */ }
            perform action a8 { doc /* confirms that the permit is active and the required isolations have been independently verified @S329 */ }
            perform action a9 { doc /* briefs the crew on the permit limits, isolation boundaries, communications, and conditions requiring work to stop @S330 */ }
            perform action a10 { doc /* pause work @S333 */ }
            perform action a11 { doc /* reassess the authorization @S333 */ }
            perform action a12 { doc /* confirms that tools, temporary connections, and personnel are clear @S335 */ }
            perform action a13 { doc /* requesting isolation removal @S335 */ }
            perform action a14 { doc /* confirms completion @S340 */ }
            perform action a15 { doc /* formally records any remaining work @S340 */ }
            perform action a16 { doc /* confirms the work party is complete @S405 */ }
            perform action a17 { doc /* escalates any unexplained absence or overdue check-in to Marine Coordinator without delay @S412 */ }
            perform action a18 { doc /* checks that cybersecurity requirements are included in the work briefing @S429 */ }
            perform action a19 { doc /* uses the Deferred Task Rationale @S430 */ }
            perform action a20 { doc /* confirms that close-access findings are documented @S457 */ }
            perform action a21 { doc /* reviews the worksite limits with the crew @S493 */ }
            perform action a22 { doc /* verifies each worker's authorization, competence, and fitness for the assigned task @S503 */ }
            perform action a23 { doc /* pauses the job @S509 */ }
            perform action a24 { doc /* confirms personnel are clear of affected equipment @S536 */ }
            perform action a25 { doc /* directs personnel at the affected work site @S615 */ }
            perform action a26 { doc /* maintains control of the work area @S649 */ }
            perform action a27 { doc /* stops handling @S649 */ }
            perform action a28 { doc /* reports remaining hazards @S660 */ }
            perform action a29 { doc /* confirms that temporary securing arrangements are adequate for transit @S660 */ }
            perform action a30 { doc /* briefs the crew on the boundary, access restrictions, and conditions that require work to stop @S717 */ }
            perform action a31 { doc /* confirms that every crew member understands the limits of the approved work area @S726 */ }
            perform action a32 { doc /* ensures that field observations and work outcomes are entered promptly while the details remain verifiable @S778 */ }
            perform action a33 { doc /* confirms work party status @S809 */ }
            perform action a34 { doc /* reports unresolved personnel or access concerns to the Shore Control Room @S809 */ }
            perform action a35 { doc /* reviews unusual denial patterns and unresolved access exceptions during the work shift @S826 */ }
            perform action a36 { doc /* coordinates the inspection before the first planned movement of each operating shift @S860 */ }
            perform action a37 { doc /* records the inspection result and any observed defects in the maintenance system @S869 */ }
            perform action a38 { doc /* confirms that no person is exposed to a suspended or shifting load during movement @S879 */ }
            perform action a39 { doc /* communicates the release status to the work party @S881 */ }
            perform action a40 { doc /* records the time that service is authorized @S881 */ }
            perform action a41 { doc /* confirms that the work authorization covers the intended landing and task @S886 */ }
            perform action a42 { doc /* verifies that the landing is accessible and that the route is clear of obstructions @S887 */ }
            perform action a43 { doc /* ensures that the lift is left secure and that any irregularity is reported through the established site process @S906 */ }
            perform action a44 { doc /* provides feedback on whether revised procedures and controls are practical during offshore work @S927 */ }
            perform action a45 { doc /* confirms that field execution practices and escalation routes are workable for offshore personnel @S970 */ }
        }
        part fieldTeam : FieldTeam {
            perform action a0 { doc /* use the same revision @S729 */ }
            perform action a1 { doc /* confirming isolation status @S729 */ }
        }
        part fieldWork : FieldWork {
            perform action a0 { doc /* begins @S711 */ }
        }
        part finalWindow : FinalWindow {
            perform action a0 { doc /* allows time for switching, work execution, testing, and restoration @S747 */ }
        }
        part fire : Fire {
            perform action a0 { doc /* threatens electrical equipment or personnel @S792 */ }
        }
        part fireDetectionPanel : FireDetectionPanel {
            perform action a0 { doc /* provides alarm indications @S629 */ }
            perform action a1 { doc /* supervises detection circuits @S786 */ }
            perform action a2 { doc /* annunciates alarms with location and fault information @S786 */ }
            perform action a3 { doc /* remain essential services during degraded operation @S945 */ }
            exhibit state modes {
                state s0 { doc /* active faults @S352 */ }
                state s1 { doc /* healthy status @S352 */ }
            }
        }
        part fireProtection : FireProtection {
            perform action a0 { doc /* detect smoke, heat, and flame @S785 */ }
            perform action a1 { doc /* support automatic equipment protection and a controlled personnel response @S785 */ }
        }
        part fleetDispatchConsole : FleetDispatchConsole {
            perform action a0 { doc /* supports the coordination of operational resources across the farm @S041 */ }
            perform action a1 { doc /* provides a fleet-level view of dispatch activity for operational coordination @S069 */ }
            perform action a2 { doc /* gives the Marine Coordinator a shared view of vessel assignments, planned movements, and dispatch status @S081 */ }
            perform action a3 { doc /* allocates requested farm output among available generating units @S203 */ }
            perform action a4 { doc /* uses the quality flag @S225 */ }
            perform action a5 { doc /* support movement planning @S225 */ }
            perform action a6 { doc /* assigns vessel and crew resources to approved work packages @S260 */ }
            perform action a7 { doc /* compares the requested output with available turbine capability and known operating restrictions @S370 */ }
            perform action a8 { doc /* retains the instruction history and the corresponding plant response for later review @S385 */ }
            perform action a9 { doc /* supports coordinated adjustment of turbine output across the affected operating area @S543 */ }
            perform action a10 { doc /* provides a fleet-level view of operating status and response to emerging constraints @S917 */ }
            perform action a11 { doc /* presents operational restrictions @S947 */ }
        }
        part fleetDispatchConsoleSchedules : FleetDispatchConsoleSchedules {
            perform action a0 { doc /* reflect confirmed changes to vessel availability and offshore task timing @S485 */ }
        }
        part fogBanks : FogBanks {
            perform action a0 { doc /* move through the area @S662 */ }
        }
        part forecast : Forecast {
            perform action a0 { doc /* does not by itself release a hold @S280 */ }
            perform action a1 { doc /* provides context for expected changes @S664 */ }
        }
        part forecastUpdates : ForecastUpdates {
            perform action a0 { doc /* support timing decisions for remote observation and field work @S128 */ }
        }
        part gate : Gate {
            exhibit state modes {
                state s0 { doc /* secured @S816 */ }
            }
        }
        part generationCapability : GenerationCapability {
            perform action a0 { doc /* changes @S942 */ }
        }
        part goOrNoGoDecision : GoOrNoGoDecision {
            perform action a0 { doc /* considers the task method, crew competence, vessel capability, and the confidence in the visibility assessment @S674 */ }
        }
        part grid : Grid {
            exhibit state modes {
                state s0 { doc /* approved grid operating state @S347 */ }
            }
        }
        part gridConstraint : GridConstraint {
            perform action a0 { doc /* may require reduced export, revised dispatch, or temporary disconnection @S210 */ }
            perform action a1 { doc /* requires the Duty Planner to reassess the sequence and obtain revised authorization before work proceeds @S519 */ }
            perform action a2 { doc /* may require the requested window to be shortened, moved, or divided into separate periods @S746 */ }
        }
        part gridDispatch : GridDispatch;
        part gridDispatcher : GridDispatcher {
            perform action a0 { doc /* sets external dispatch requirements within the applicable connection agreement @S202 */ }
            perform action a1 { doc /* issues active-power targets and ramp instructions through the established dispatch channel @S367 */ }
            perform action a2 { doc /* confirms applicable grid requirements and any restrictions on changing the connection state @S518 */ }
            perform action a3 { doc /* changing the connection state @S518 */ }
            perform action a4 { doc /* receives the Export Limit Advisory @S541 */ }
            perform action a5 { doc /* uses it to set the permitted export level @S541 */ }
            perform action a6 { doc /* set the permitted export level @S541 */ }
            perform action a7 { doc /* confirms that the requested period is compatible with export requirements and network operating limits @S739 */ }
            perform action a8 { doc /* communicates external operating requirements to the Grid Interface Relay and the responsible control personnel @S769 */ }
        }
        part gridInterfaceRelay : GridInterfaceRelay {
            perform action a0 { doc /* provides status indications that support assessment of the normal supply and its protective state @S190 */ }
            perform action a1 { doc /* defines the operational boundary between the offshore farm and the external transmission system @S197 */ }
            perform action a2 { doc /* exchanges authorized operating signals with the transmission system at the agreed interface @S201 */ }
            perform action a3 { doc /* maintains the farm's dispatch boundary @S221 */ }
            perform action a4 { doc /* allowing local systems to manage turbine-level operation @S221 */ }
            perform action a5 { doc /* produces an Export Limit Advisory when available export capability falls below the active dispatch target @S372 */ }
            perform action a6 { doc /* applies the accepted export ceiling to control outputs @S373 */ }
            perform action a7 { doc /* records its effective time for audit @S373 */ }
            perform action a8 { doc /* retains its protection settings unless an authorized switching plan requires a controlled change @S551 */ }
            perform action a9 { doc /* remains available for the required protection and control functions throughout the planned work @S743 */ }
            perform action a10 { doc /* applies the configured response to a Grid Constraint @S942 */ }
            exhibit state modes {
                state s0 { doc /* available @S743 */ }
            }
        }
        part gridRequirements : GridRequirements {
            perform action a0 { doc /* influence the timing and conduct of work @S028 */ }
        }
        part hSEOfficer : HSEOfficer {
            perform action a0 { doc /* verifies that work arrangements account for applicable safety controls and personnel responsibilities @S095 */ }
            perform action a1 { doc /* reviews the proposed controls @S157 */ }
            perform action a2 { doc /* produces the Harness Audit Card @S237 */ }
            perform action a3 { doc /* reviews hazards @S266 */ }
            perform action a4 { doc /* confirms that proposed controls match the task scope and site conditions @S266 */ }
            perform action a5 { doc /* reviews task hazards @S322 */ }
            perform action a6 { doc /* confirms that required controls are assigned @S322 */ }
            perform action a7 { doc /* verifies that personnel expected at the work site are accounted for during scheduled checks @S408 */ }
            perform action a8 { doc /* reviews the work method, exposure controls, and emergency arrangements @S451 */ }
            perform action a9 { doc /* checks that access controls, emergency arrangements, and handling precautions are suitable for the planned activity @S481 */ }
            perform action a10 { doc /* checks that emergency routes, muster points, and rescue arrangements are understood by everyone at the worksite @S505 */ }
            perform action a11 { doc /* reviews task hazards @S526 */ }
            perform action a12 { doc /* confirms that required controls are in place @S526 */ }
            perform action a13 { doc /* is authorized @S526 */ }
            perform action a14 { doc /* assesses any safety implications @S579 */ }
            perform action a15 { doc /* advises whether the affected activity can continue @S579 */ }
            perform action a16 { doc /* advises on personnel hazards, rescue procedures, and the use of emergency equipment @S617 */ }
            perform action a17 { doc /* reviews the handling method, lifting points, and exclusion zones @S647 */ }
            perform action a18 { doc /* advises on exposure, evacuation, and re-entry criteria in coordination with the incident response team @S808 */ }
            perform action a19 { doc /* can use the recorded entry history to support personnel accountability during an incident @S827 */ }
            perform action a20 { doc /* support personnel accountability during an incident @S827 */ }
            perform action a21 { doc /* reviews any proposed workaround that changes established access, isolation, or personnel-control arrangements @S949 */ }
            perform action a22 { doc /* evaluates safety controls, emergency arrangements, and lessons from reported events @S967 */ }
        }
        part handlingArrangement : HandlingArrangement {
            perform action a0 { doc /* keeps the load contained within the car @S877 */ }
        }
        part handsOnActivity : HandsOnActivity {
            perform action a0 { doc /* begins @S631 */ }
        }
        part handsOnWork : HandsOnWork {
            perform action a0 { doc /* begins @S725 */ }
        }
        part hazardousEnergySources : HazardousEnergySources {
            perform action a0 { doc /* are assessed @S725 */ }
        }
        part hazards : Hazards;
        part helideck : Helideck;
        part incidentLead : IncidentLead {
            perform action a0 { doc /* classifies each report @S432 */ }
            perform action a1 { doc /* assigns an owner @S432 */ }
            perform action a2 { doc /* records its time, scope, and current status @S432 */ }
            perform action a3 { doc /* confirms that the threat is contained and the affected system is suitable for return to service @S436 */ }
            perform action a4 { doc /* verifies headcounts with the teams involved @S619 */ }
        }
        part incomingSupervisor : IncomingSupervisor;
        part incomingTeam : IncomingTeam {
            perform action a0 { doc /* independently checks the boundary status @S731 */ }
            perform action a1 { doc /* accepting responsibility for ongoing work @S731 */ }
        }
        part indication : Indication {
            exhibit state modes {
                state s0 { doc /* ambiguous @S535 */ }
            }
        }
        part indicators : Indicators {
            perform action a0 { doc /* operate as intended @S854 */ }
        }
        part inspection : Inspection {
            perform action a0 { doc /* begins with a visual check of the car, landing doors, guide surfaces, and access barriers @S861 */ }
        }
        part inspectionRecord : InspectionRecord {
            perform action a0 { doc /* identifies the uncertainty @S456 */ }
            perform action a1 { doc /* specifies additional measurements or imagery needed @S456 */ }
        }
        part inspector : Inspector {
            perform action a0 { doc /* confirms that the car floor and landing thresholds are clear of loose material and standing water @S862 */ }
            perform action a1 { doc /* checks the operating controls for damage, legibility, and secure mounting @S865 */ }
            perform action a2 { doc /* confirms that the rated capacity and operating instructions remain legible at the car entrance @S868 */ }
        }
        part installationTeam : InstallationTeam {
            perform action a0 { doc /* verifies the scanner, barrier, and communications @S853 */ }
        }
        part instruction : Instruction {
            exhibit state modes {
                state s0 { doc /* understood @S773 */ }
            }
        }
        part instructions : Instructions {
            perform action a0 { doc /* affect electrical safety @S770 */ }
        }
        part interfacePart : Interface {
            exhibit state modes {
                state s0 { doc /* normal export @S220 */ }
            }
        }
        part inventory : Inventory;
        part inventoryRecord : InventoryRecord {
            perform action a0 { doc /* covers serviceable parts, consumables, repairable units, and their locations across shore and offshore stores @S686 */ }
        }
        part isolation : Isolation {
            perform action a0 { doc /* is removed @S732 */ }
        }
        part isolationBoundaries : IsolationBoundaries {
            exhibit state modes {
                state s0 { doc /* current @S350 */ }
            }
        }
        part isolationBoundary : IsolationBoundary {
            perform action a0 { doc /* defines the equipment and energy sources that must be made safe before field work begins @S711 */ }
        }
        part isolationDevice : IsolationDevice {
            perform action a0 { doc /* using the site-approved locking and tagging method @S722 */ }
            perform action a1 { doc /* is secured against unintended operation using the site-approved locking and tagging method @S722 */ }
        }
        part items : Items {
            perform action a0 { doc /* approaching their reorder point @S701 */ }
        }
        part itemsReservedForApprovedWork : ItemsReservedForApprovedWork;
        part label : Label {
            perform action a0 { doc /* is reviewed for alarms or restrictions that could affect export capability @S378 */ }
            perform action a1 { doc /* is included in the assessment of the available export path @S379 */ }
            perform action a2 { doc /* is monitored against its approved continuous and short-term limits @S380 */ }
            perform action a3 { doc /* are checked for conditions that require a reduced transfer level @S381 */ }
            perform action a4 { doc /* is notified when measured delivery differs materially from the instructed target or when an operating limit is approached @S383 */ }
            perform action a5 { doc /* is approached @S383 */ }
            perform action a6 { doc /* taken @S384 */ }
            perform action a7 { doc /* are interrupted @S386 */ }
            perform action a8 { doc /* is not treated as a means of maintaining export unless the approved electrical configuration explicitly supports it @S387 */ }
            perform action a9 { doc /* maintaining export @S387 */ }
            perform action a10 { doc /* assigned to offshore work @S392 */ }
            perform action a11 { doc /* is reconciled against the crew manifest @S399 */ }
            perform action a12 { doc /* reported vessel movements @S400 */ }
        }
        part landing : Landing {
            exhibit state modes {
                state s0 { doc /* accessible @S887 */ }
            }
        }
        part laterReviewers : LaterReviewers {
            perform action a0 { doc /* can assess their basis @S775 */ }
        }
        part lessonsLearned : LessonsLearned {
            perform action a0 { doc /* continue to reflect actual operating experience @S933 */ }
        }
        part lift : Lift {
            exhibit state modes {
                state s0 { doc /* in service @S893 */ }
                state s1 { doc /* removed from service @S883 */ }
                state s2 { doc /* secure @S906 */ }
            }
        }
        part liftSupply : LiftSupply {
            perform action a0 { doc /* show no active fault indication @S867 */ }
        }
        part lighting : Lighting;
        part localConditions : LocalConditions {
            perform action a0 { doc /* may develop sooner or differently than forecast @S664 */ }
        }
        part localIndication : LocalIndication;
        part localProtectionFunctions : LocalProtectionFunctions {
            perform action a0 { doc /* retain priority when remote requests conflict with safe operating limits @S137 */ }
        }
        part localReference : LocalReference {
            perform action a0 { doc /* can help identify differences between forecast conditions and conditions at sea @S665 */ }
        }
        part localSystems : LocalSystems {
            perform action a0 { doc /* manage turbine-level operation @S221 */ }
        }
        part localVisualIndicator : LocalVisualIndicator {
            perform action a0 { doc /* communicates whether entry is permitted or denied @S845 */ }
        }
        part location : Location {
            exhibit state modes {
                state s0 { doc /* uncertain @S580 */ }
            }
        }
        part lossOfCriticalMonitoring : LossOfCriticalMonitoring {
            perform action a0 { doc /* occurs @S360 */ }
        }
        part lowCloud : LowCloud {
            perform action a0 { doc /* move through the area @S662 */ }
        }
        part lowStockAlerts : LowStockAlerts {
            perform action a0 { doc /* identify items approaching their reorder point @S701 */ }
            perform action a1 { doc /* show open purchase commitments @S701 */ }
        }
        part machinerySpaces : MachinerySpaces;
        part mainTransformer : MainTransformer {
            perform action a0 { doc /* have been reviewed @S744 */ }
        }
        part maintenance : Maintenance {
            perform action a0 { doc /* begins @S490 */ }
        }
        part maintenanceActivities : MaintenanceActivities {
            perform action a0 { doc /* deliver safe electrical generation @S002 */ }
        }
        part maintenancePlanningEngine : MaintenancePlanningEngine {
            perform action a0 { doc /* supports the preparation and sequencing of maintenance activities @S042 */ }
            perform action a1 { doc /* supports work preparation @S054 */ }
            perform action a2 { doc /* organizing maintenance needs, resource considerations, and planning constraints @S054 */ }
            perform action a3 { doc /* supports planning decisions @S066 */ }
            perform action a4 { doc /* without replacing the judgment of the Duty Planner @S066 */ }
            perform action a5 { doc /* can use reviewed condition information @S148 */ }
            perform action a6 { doc /* prioritizing future maintenance activities @S148 */ }
            perform action a7 { doc /* can use reviewed condition information @S154 */ }
            perform action a8 { doc /* prioritizing future maintenance activities @S154 */ }
            perform action a9 { doc /* schedules inspections and corrective work using equipment condition and operating history @S188 */ }
            perform action a10 { doc /* using equipment condition and operating history @S188 */ }
            perform action a11 { doc /* schedules periodic reviews of standby electrical maintenance requirements and outstanding corrective work @S195 */ }
            perform action a12 { doc /* uses the Squall Window Bulletin @S213 */ }
            perform action a13 { doc /* reviewing the timing of planned work @S213 */ }
            perform action a14 { doc /* ranks planned and corrective work using asset condition, safety exposure, production impact, access feasibility, and resource availability @S246 */ }
            perform action a15 { doc /* produces the Deferred Task Rationale @S285 */ }
            perform action a16 { doc /* receives validated condition information for prioritization and scheduling of follow-up work @S308 */ }
            perform action a17 { doc /* combines inspection intervals, prior defect history, and turbine availability @S441 */ }
            perform action a18 { doc /* propose survey dates @S441 */ }
            perform action a19 { doc /* uses the assessed severity, defect growth rate, weather exposure, and production impact @S458 */ }
            perform action a20 { doc /* support repair prioritization @S458 */ }
            perform action a21 { doc /* supports this review @S470 */ }
            perform action a22 { doc /* presenting task duration, resource demand, and dependency status @S470 */ }
            perform action a23 { doc /* provides the planned work period @S520 */ }
            perform action a24 { doc /* identifies dependencies with other scheduled tasks @S520 */ }
            perform action a25 { doc /* can help identify tasks that may be rescheduled when visibility is uncertain @S670 */ }
            perform action a26 { doc /* uses planned work demand and part criticality @S694 */ }
            perform action a27 { doc /* support replenishment forecasts @S694 */ }
            perform action a28 { doc /* checks task durations, dependencies, and resource assumptions @S738 */ }
            perform action a29 { doc /* supports review of planned work, resource demand, and maintenance completion performance @S918 */ }
            perform action a30 { doc /* separates safety-critical work from tasks that can safely wait until normal access and support are available @S948 */ }
        }
        part maintenanceRecords : MaintenanceRecords;
        part maintenanceSystem : MaintenanceSystem;
        part manuallyPresentedCredentialImage : ManuallyPresentedCredentialImage {
            perform action a0 { doc /* overrides a scanner denial @S818 */ }
        }
        part marineAccess : MarineAccess {
            perform action a0 { doc /* affects the achievable start time @S748 */ }
        }
        part marineActivity : MarineActivity {
            exhibit state modes {
                state s0 { doc /* Vessel Standby @S943 */ }
            }
        }
        part marineCoordination : MarineCoordination {
            perform action a0 { doc /* aligns vessel movements, personnel transfers, and shore-side support with the approved work schedule @S222 */ }
        }
        part marineCoordinator : MarineCoordinator {
            perform action a0 { doc /* considers offshore conditions and vessel availability @S068 */ }
            perform action a1 { doc /* coordinating access to work sites @S068 */ }
            perform action a2 { doc /* aligns vessel availability with crew readiness, port access, and the planned work locations @S077 */ }
            perform action a3 { doc /* uses that view @S082 */ }
            perform action a4 { doc /* coordinate the Crew Transfer Vessel, the Service Operations Vessel, and the Daughter Craft @S082 */ }
            perform action a5 { doc /* uses the available traffic picture @S141 */ }
            perform action a6 { doc /* support coordination of offshore movements @S141 */ }
            perform action a7 { doc /* checks that the planned access method and timing are practical for the work location @S160 */ }
            perform action a8 { doc /* maintains the daily marine plan @S223 */ }
            perform action a9 { doc /* resolves conflicts between planned activities @S223 */ }
            perform action a10 { doc /* records changes to the movement plan @S245 */ }
            perform action a11 { doc /* ensures that affected teams receive the update @S245 */ }
            perform action a12 { doc /* compares expected access conditions with vessel capability, transit time, and worksite limits @S257 */ }
            perform action a13 { doc /* coordinates resource changes with the Vessel Master and affected work teams @S261 */ }
            perform action a14 { doc /* reviews access options and vessel availability @S277 */ }
            perform action a15 { doc /* reassesses the route @S283 */ }
            perform action a16 { doc /* seeks an updated forecast @S290 */ }
            perform action a17 { doc /* confirming a departure or transfer plan @S290 */ }
            perform action a18 { doc /* reviews the intended crew movement against vessel capacity and operating conditions @S397 */ }
            perform action a19 { doc /* monitors reported vessel movements during transit to offshore locations @S400 */ }
            perform action a20 { doc /* reviews return movements @S410 */ }
            perform action a21 { doc /* maintains a rolling view of berth occupancy, planned arrivals, departure estimates, and vessel service requirements @S466 */ }
            perform action a22 { doc /* uses the Berth Slot Confirmation @S473 */ }
            perform action a23 { doc /* align an approved vessel arrival with the assigned berth window @S473 */ }
            perform action a24 { doc /* resolves competing berth requests @S483 */ }
            perform action a25 { doc /* considering task urgency, vessel compatibility, and the consequences of delay @S483 */ }
            perform action a26 { doc /* reviews safe alternatives such as a later slot, a different suitable berth, or vessel standby @S488 */ }
            perform action a27 { doc /* suspends access @S499 */ }
            perform action a28 { doc /* aligns vessel movements with the approved access plan and operational constraints @S523 */ }
            perform action a29 { doc /* establishes the expected personnel count and destination for each movement @S565 */ }
            perform action a30 { doc /* pauses further personnel transfers @S576 */ }
            perform action a31 { doc /* informs the Shore Control Room of the discrepancy and the immediate control actions @S578 */ }
            perform action a32 { doc /* escalates any unresolved discrepancy to the Duty Planner @S583 */ }
            perform action a33 { doc /* records the time of escalation @S583 */ }
            perform action a34 { doc /* confirms that the count is reconciled or an authorized response is in place @S585 */ }
            perform action a35 { doc /* maintains awareness of vessel locations, access constraints, and available marine support @S618 */ }
            perform action a36 { doc /* assigns suitable vessels @S638 */ }
            perform action a37 { doc /* maintains a common plan for their approach and departure @S638 */ }
            perform action a38 { doc /* pauses the recovery @S659 */ }
            perform action a39 { doc /* agrees a safe holding position with the Vessel Master @S659 */ }
            perform action a40 { doc /* reviews how uncertainty affects the planned transit, transfer location, and available alternatives @S676 */ }
            perform action a41 { doc /* reassess the route and the suitability of continuing toward the work site @S682 */ }
            perform action a42 { doc /* checks vessel movements and crew transfer timing against the proposed period @S749 */ }
            perform action a43 { doc /* shares relevant marine and weather information with vessel personnel and the Duty Planner @S764 */ }
            perform action a44 { doc /* confirm that personnel and vessels can remain safely accounted for during an extended interruption @S944 */ }
            perform action a45 { doc /* reviews vessel coordination arrangements @S966 */ }
            perform action a46 { doc /* verifies that marine responsibilities are understood @S966 */ }
        }
        part measuredConditions : MeasuredConditions {
            perform action a0 { doc /* approach a limit @S291 */ }
        }
        part measuredDelivery : MeasuredDelivery {
            perform action a0 { doc /* differs materially from the instructed target @S383 */ }
        }
        part measuredExport : MeasuredExport {
            perform action a0 { doc /* follows the revised target @S544 */ }
        }
        part measurementIntervals : MeasurementIntervals {
            perform action a0 { doc /* support both trend analysis and timely operational decisions @S108 */ }
        }
        part measurements : Measurements {
            perform action a0 { doc /* support assessment of the export path @S200 */ }
        }
        part metoceanBuoy : MetoceanBuoy {
            perform action a0 { doc /* measures wind speed and direction, wave height and period, current, air temperature, and barometric pressure @S102 */ }
            perform action a1 { doc /* produces the Wave Burst Record at the configured sampling interval @S194 */ }
            perform action a2 { doc /* reports local sea conditions for use in access planning @S231 */ }
            perform action a3 { doc /* provide contextual conditions @S309 */ }
            perform action a4 { doc /* provide forecasts and measured conditions @S443 */ }
            perform action a5 { doc /* provides site measurements @S625 */ }
            perform action a6 { doc /* provides a local reference @S665 */ }
            perform action a7 { doc /* provide inputs @S766 */ }
        }
        part metoceanObservations : MetoceanObservations;
        part mismatch : Mismatch {
            perform action a0 { doc /* prevents the crew from proceeding until it is resolved @S721 */ }
        }
        part monitoringAndControlAssumptions : MonitoringAndControlAssumptions {
            perform action a0 { doc /* affect operational decisions @S968 */ }
        }
        part monitoringAndControlFunctions : MonitoringAndControlFunctions;
        part monitoringImpairment : MonitoringImpairment {
            perform action a0 { doc /* limits safe switching or export capability @S941 */ }
        }
        part monitoringProcess : MonitoringProcess {
            perform action a0 { doc /* retains the source, timestamp, and turbine identifier for each observation @S296 */ }
        }
        part monitoringRules : MonitoringRules {
            perform action a0 { doc /* identify unusual login patterns, unexpected configuration changes, and communications outside approved operating windows @S418 */ }
        }
        part nacelleConditionMonitor : NacelleConditionMonitor {
            perform action a0 { doc /* provides equipment measurements for ongoing assessment of turbine health @S132 */ }
            perform action a1 { doc /* provides condition data @S250 */ }
            perform action a2 { doc /* provides condition information @S793 */ }
            perform action a3 { doc /* supports assessment of equipment condition and emerging degradation @S915 */ }
        }
        part needDate : NeedDate;
        part networkSegmentation : NetworkSegmentation {
            perform action a0 { doc /* limits the effect of a compromised endpoint @S120 */ }
            perform action a1 { doc /* supports controlled restoration of service @S120 */ }
        }
        part normalElectricalSupplies : NormalElectricalSupplies {
            exhibit state modes {
                state s0 { doc /* unavailable @S803 */ }
            }
        }
        part normalMonitoringResponsibilities : NormalMonitoringResponsibilities {
            perform action a0 { doc /* resume @S437 */ }
        }
        part normalSupply : NormalSupply {
            perform action a0 { doc /* serves control systems, lighting, ventilation, communications, and equipment required for safe switching and maintenance @S174 */ }
            perform action a1 { doc /* is restored @S196 */ }
            exhibit state modes {
                state s0 { doc /* protective state @S190 */ }
            }
        }
        part normalWork : NormalWork {
            perform action a0 { doc /* resumes @S635 */ }
        }
        part northAccessScanner : NorthAccessScanner {
            perform action a0 { doc /* records authorized entry at the north access point @S235 */ }
            perform action a1 { doc /* records identity checks at the north shore access point @S394 */ }
            perform action a2 { doc /* records personnel access events at the north access point @S569 */ }
            perform action a3 { doc /* validates each presented credential against current access authorization @S810 */ }
            perform action a4 { doc /* enabling controlled entry @S810 */ }
            perform action a5 { doc /* accepts only credentials that can be read reliably and associated with an identifiable person @S811 */ }
        }
        part observations : Observations {
            perform action a0 { doc /* give the team a local reference for checking forecast trends and current sea state @S271 */ }
            perform action a1 { doc /* suggests a risk to personnel or equipment @S306 */ }
        }
        part observedCount : ObservedCount;
        part occupants : Occupants {
            perform action a0 { doc /* remain inside the car @S899 */ }
            perform action a1 { doc /* avoid interfering with the controls or doors @S899 */ }
            perform action a2 { doc /* use the designated alarm or communication method @S902 */ }
            perform action a3 { doc /* remain inside the car @S902 */ }
            perform action a4 { doc /* exit without crowding @S905 */ }
            exhibit state modes {
                state s0 { doc /* ready @S898 */ }
            }
        }
        part offshoreFarm : OffshoreFarm {
            perform action a0 { doc /* exports electrical power through the Offshore Substation, Main Transformer, and export cable to the designated grid connection point @S199 */ }
            perform action a1 { doc /* reports measured active power at the grid boundary for operational monitoring and settlement processes @S205 */ }
        }
        part offshoreGenerationAssets : OffshoreGenerationAssets;
        part offshorePersonnel : OffshorePersonnel {
            perform action a0 { doc /* follow posted escape routes @S804 */ }
            perform action a1 { doc /* muster at the designated assembly point @S804 */ }
        }
        part offshoreRecovery : OffshoreRecovery {
            perform action a0 { doc /* begins @S636 */ }
        }
        part offshoreRecoveryPlans : OffshoreRecoveryPlans {
            perform action a0 { doc /* identify the point at which continued response would expose rescuers to unacceptable risk @S633 */ }
        }
        part offshoreSubstation : OffshoreSubstation {
            perform action a0 { doc /* provides the farm's offshore electrical collection and switching environment @S037 */ }
            perform action a1 { doc /* maintains the designated emergency distribution bus within its approved operating limits @S189 */ }
            perform action a2 { doc /* sends a Transformer Tap Snapshot @S267 */ }
            perform action a3 { doc /* uses the Switching Window Acknowledgment @S752 */ }
            perform action a4 { doc /* confirm that the approved switching window is available for the planned work @S752 */ }
            perform action a5 { doc /* enters Substation Degraded @S941 */ }
            exhibit state modes {
                state s0 { doc /* Substation Degraded @S361,S941 */ }
            }
        }
        part offshoreSubstationOperator : OffshoreSubstationOperator {
            perform action a0 { doc /* confirms that export equipment remains within its approved operating range @S549 */ }
        }
        part offshoreSupportFacilities : OffshoreSupportFacilities;
        part offshoreTeams : OffshoreTeams;
        part offshoreWindFarm : OffshoreWindFarm {
            perform action a0 { doc /* operates in a variable marine environment @S028 */ }
        }
        part onDutyOperationsLead : OnDutyOperationsLead;
        part onboardLogger : OnboardLogger {
            perform action a0 { doc /* timestamps observations @S104 */ }
            perform action a1 { doc /* retains a local history during intermittent communications @S104 */ }
        }
        part operatingData : OperatingData {
            perform action a0 { doc /* helps distinguish persistent defects from transient changes in blade appearance @S447 */ }
        }
        part operatingInstructions : OperatingInstructions {
            exhibit state modes {
                state s0 { doc /* legible @S868 */ }
            }
        }
        part operatingLimits : OperatingLimits {
            perform action a0 { doc /* still govern whether work can proceed @S281 */ }
        }
        part operatingModel : OperatingModel {
            perform action a0 { doc /* assigns continuous monitoring and dispatch coordination to the Shore Control Room @S013 */ }
        }
        part operatingOrganization : OperatingOrganization {
            perform action a0 { doc /* combines shore-based planning, marine coordination, vessel crews, and technicians assigned to offshore work @S075 */ }
            perform action a1 { doc /* maintain an accurate view of personnel assigned to offshore activities @S094 */ }
            perform action a2 { doc /* uses defined handoffs @S098 */ }
        }
        part operatingPersonnel : OperatingPersonnel {
            perform action a0 { doc /* accept the restored condition @S341 */ }
            perform action a1 { doc /* rely on remote indications @S349 */ }
        }
        part operationalAssessment : OperationalAssessment {
            perform action a0 { doc /* records both the estimated visibility and the confidence that the estimate represents conditions at the intended work location @S667 */ }
        }
        part operationalBoundary : OperationalBoundary;
        part operationalCommunications : OperationalCommunications {
            perform action a0 { doc /* support safe decisions @S760 */ }
            perform action a1 { doc /* providing timely, clear, and traceable information to the people responsible for offshore work @S760 */ }
        }
        part operationalDecisions : OperationalDecisions {
            perform action a0 { doc /* account for observed local conditions @S624 */ }
        }
        part operationalHandoverRecords : OperationalHandoverRecords {
            perform action a0 { doc /* identify the deployed change, any outstanding limitations, and the responsible technical contact @S611 */ }
        }
        part operationalMonitoring : OperationalMonitoring {
            perform action a0 { doc /* used by protective functions and operational monitoring @S788 */ }
        }
        part operationalNotices : OperationalNotices {
            perform action a0 { doc /* affecting the farm interface @S214 */ }
        }
        part operationalPersonnel : OperationalPersonnel {
            perform action a0 { doc /* retain authority for decisions that require procedural, safety, or engineering judgment @S073 */ }
            perform action a1 { doc /* supports maintainable operations @S074 */ }
            perform action a2 { doc /* keeping supervisory functions distinct from planning and human coordination @S074 */ }
        }
        part operationalPlanningAndCoordination : OperationalPlanningAndCoordination;
        part operationalProcedures : OperationalProcedures {
            perform action a0 { doc /* identify the authority for approving access, responding to alarms, and returning affected services to normal operation @S122 */ }
        }
        part operationalRecords : OperationalRecords {
            perform action a0 { doc /* identify the originator, recipient, event time, recording time, relevant asset, and decision or action taken @S774 */ }
        }
        part operationalReports : OperationalReports {
            perform action a0 { doc /* indicate that blade condition requires review @S440 */ }
        }
        part operationalSystem : OperationalSystem;
        part operationalValue : OperationalValue {
            perform action a0 { doc /* justify the required outage or vessel time @S249 */ }
        }
        part operations : Operations {
            perform action a0 { doc /* can resume safely @S086 */ }
        }
        part operationsRadioConsole : OperationsRadioConsole {
            perform action a0 { doc /* supports routine communications and escalation during offshore activity @S239 */ }
            perform action a1 { doc /* supports communications between the Shore Control Room, vessels, and offshore work teams @S627 */ }
            perform action a2 { doc /* supports voice communication with the Crew Transfer Vessel, Service Operations Vessel, and Daughter Craft when they are within radio coverage @S762 */ }
            perform action a3 { doc /* provides a coordinated communications channel for response instructions and status reports @S806 */ }
        }
        part operationsTeam : OperationsTeam {
            perform action a0 { doc /* relies on them for control decisions @S558 */ }
        }
        part operator : Operator {
            perform action a0 { doc /* records test results @S356 */ }
            perform action a1 { doc /* raises a defect promptly @S356 */ }
            perform action a2 { doc /* operating a breaker or isolator @S359 */ }
            perform action a3 { doc /* verifies the required clearances @S359 */ }
            perform action a4 { doc /* confirms that affected parties are informed @S359 */ }
            perform action a5 { doc /* limits further switching @S360 */ }
            perform action a6 { doc /* escalates the condition @S360 */ }
            perform action a7 { doc /* places the Offshore Substation in Substation Degraded when required by operating procedures @S361 */ }
            perform action a8 { doc /* communicates the resulting restrictions @S361 */ }
            perform action a9 { doc /* records its scope, start time, and expected review point @S376 */ }
            perform action a10 { doc /* positions each load @S878 */ }
            perform action a11 { doc /* avoid obstructing doors, controls, and emergency access @S878 */ }
            perform action a12 { doc /* checks the lift identification, rated capacity, and current service status before each operating period @S888 */ }
            perform action a13 { doc /* confirms that the car floor is level with the boarding landing @S890 */ }
            perform action a14 { doc /* permitting entry or exit @S890 */ }
            perform action a15 { doc /* checks that the controls respond correctly and that the emergency stop is accessible @S892 */ }
            perform action a16 { doc /* confirms that the expected load, including tools and carried equipment, remains within the rated capacity @S895 */ }
            perform action a17 { doc /* confirms that all occupants are ready and that the doors are fully closed @S898 */ }
            perform action a18 { doc /* starting movement @S898 */ }
            perform action a19 { doc /* monitors lift movement for unusual noise, vibration, hesitation, or irregular stopping @S900 */ }
            perform action a20 { doc /* stop the lift at the nearest safe landing when practicable @S901 */ }
            perform action a21 { doc /* confirms that the car is level and stationary @S904 */ }
            perform action a22 { doc /* opening the doors @S904 */ }
            perform action a23 { doc /* checks that tools and equipment have been removed from the car @S905 */ }
            perform action a24 { doc /* periodically evaluates whether assurance arrangements provide sufficient evidence that the concept remains effective @S983 */ }
        }
        part operators : Operators {
            perform action a0 { doc /* use the approved recovery procedure @S184 */ }
            perform action a1 { doc /* assess the fault @S184 */ }
            perform action a2 { doc /* preserve essential services @S184 */ }
            perform action a3 { doc /* restore the normal supply when it is safe to do so @S184 */ }
            perform action a4 { doc /* verify the scanner clock and connectivity during routine readiness checks @S832 */ }
            perform action a5 { doc /* can assess the scope and duration of the impairment @S935 */ }
        }
        part organization : Organization {
            perform action a0 { doc /* retains voice recordings, system logs, and work records according to the approved retention schedule and applicable legal obligations @S782 */ }
        }
        part otherAreasIdentifiedByTheSiteFireRiskAssessment : OtherAreasIdentifiedByTheSiteFireRiskAssessment;
        part outgoingSupervisor : OutgoingSupervisor {
            perform action a0 { doc /* briefs the incoming supervisor on site conditions, access status, and outstanding hazards @S512 */ }
        }
        part overheating : Overheating {
            perform action a0 { doc /* threatens electrical equipment or personnel @S792 */ }
        }
        part parts : Parts {
            perform action a0 { doc /* supporting scheduled maintenance @S697 */ }
            perform action a1 { doc /* receive priority when their delivery date is necessary to protect an approved work window @S697 */ }
        }
        part passengers : Passengers {
            perform action a0 { doc /* distribute themselves and their equipment @S896 */ }
            perform action a1 { doc /* avoid obstructing the doors or control panel @S896 */ }
        }
        part people : People {
            perform action a0 { doc /* entering @S502 */ }
            perform action a1 { doc /* leaving the site @S502 */ }
        }
        part peopleResponsibleForOffshoreWork : PeopleResponsibleForOffshoreWork;
        part performanceDefinitions : PerformanceDefinitions {
            perform action a0 { doc /* identify the source data, calculation method, reporting interval, and accountable owner for each measure @S913 */ }
        }
        part performanceMeasures : PerformanceMeasures {
            perform action a0 { doc /* continue to reflect actual operating experience @S933 */ }
        }
        part permit : Permit {
            perform action a0 { doc /* has been updated @S735 */ }
            exhibit state modes {
                state s0 { doc /* active @S329 */ }
            }
        }
        part permitControls : PermitControls {
            perform action a0 { doc /* coordinate approved work scope, electrical isolation, field execution, and return to service @S318 */ }
            perform action a1 { doc /* treating authorization as proof of a safe electrical state @S318 */ }
        }
        part permitReviewers : PermitReviewers;
        part permits : Permits {
            exhibit state modes {
                state s0 { doc /* ready @S525 */ }
            }
        }
        part permittedFunctions : PermittedFunctions {
            perform action a0 { doc /* remain available @S121 */ }
        }
        part person : Person {
            perform action a0 { doc /* changes duties @S425 */ }
            perform action a1 { doc /* leaves the operation @S425 */ }
            perform action a2 { doc /* presents the credential at the controlled entry point @S812 */ }
            perform action a3 { doc /* waits for the scanner response @S812 */ }
            perform action a4 { doc /* contact the Field Supervisor or the HSE Officer for review @S817 */ }
            perform action a5 { doc /* presenting it @S840 */ }
        }
        part personIssuingTheInstruction : PersonIssuingTheInstruction {
            perform action a0 { doc /* issuing the instruction @S772 */ }
        }
        part personMakingTheChange : PersonMakingTheChange {
            perform action a0 { doc /* making the change @S777 */ }
        }
        part personRemovingEachControl : PersonRemovingEachControl {
            perform action a0 { doc /* removing each control @S733 */ }
            perform action a1 { doc /* confirms that the associated work party is clear of the hazard area @S733 */ }
        }
        part personResponsibleForApplyingTheControl : PersonResponsibleForApplyingTheControl {
            perform action a0 { doc /* applying the control @S714 */ }
        }
        part personalProtection : PersonalProtection {
            perform action a0 { doc /* is applied in accordance with the permit and local electrical safety rules @S723 */ }
        }
        part personnel : Personnel {
            perform action a0 { doc /* perform controlled work offshore @S243 */ }
            perform action a1 { doc /* confirm their identity @S393 */ }
            perform action a2 { doc /* entering controlled shore access areas @S393 */ }
            perform action a3 { doc /* report any change in destination or transfer plan to the Vessel Master as soon as practicable @S402 */ }
            perform action a4 { doc /* enter the work area @S405 */ }
            perform action a5 { doc /* report their arrival and departure at each active work location @S406 */ }
            perform action a6 { doc /* using the approved site process @S406 */ }
            perform action a7 { doc /* disembark at shore @S411 */ }
            perform action a8 { doc /* report suspected compromise, lost credentials, and unexplained equipment behavior promptly through the established operations channel @S431 */ }
            perform action a9 { doc /* approach the rotor @S451 */ }
            perform action a10 { doc /* leave the work area @S457 */ }
            perform action a11 { doc /* board a vessel @S482 */ }
            perform action a12 { doc /* use the North Access Scanner or South Access Scanner at the designated entry point @S501 */ }
            perform action a13 { doc /* supervise the work @S607 */ }
            perform action a14 { doc /* have returned to a safe location @S648 */ }
            perform action a15 { doc /* enter a restricted zone @S649 */ }
            perform action a16 { doc /* are accounted for @S732 */ }
            perform action a17 { doc /* use the approved fallback method @S771 */ }
            perform action a18 { doc /* report the outage as soon as practicable @S771 */ }
            perform action a19 { doc /* investigate a fire alarm @S802 */ }
            perform action a20 { doc /* complete post-event checks @S802 */ }
            perform action a21 { doc /* follow the approved contingency process rather than bypassing the gate @S828 */ }
            perform action a22 { doc /* bypassing the gate @S828 */ }
            perform action a23 { doc /* arriving through the south-side access point @S836 */ }
            perform action a24 { doc /* must not hold the barrier open for another entrant @S847 */ }
            perform action a25 { doc /* use an approved alternative entry process rather than an uncontrolled bypass @S856 */ }
            perform action a26 { doc /* boarding @S873 */ }
            perform action a27 { doc /* entering @S874 */ }
            perform action a28 { doc /* leaving the route @S874 */ }
            perform action a29 { doc /* do not attempt to open doors or climb out of a stopped car without direction from the response team @S903 */ }
            perform action a30 { doc /* open doors @S903 */ }
            perform action a31 { doc /* climb out of a stopped car without direction from the response team @S903 */ }
            perform action a32 { doc /* receive appropriate communication or training @S981 */ }
            exhibit state modes {
                state s0 { doc /* aboard the vessel @S409 */ }
                state s1 { doc /* clear @S335 */ }
                state s2 { doc /* clear of affected equipment @S536 */ }
                state s3 { doc /* ready @S525 */ }
            }
        }
        part personnelMovements : PersonnelMovements {
            perform action a0 { doc /* do not resume until the Marine Coordinator confirms that the count is reconciled or an authorized response is in place @S585 */ }
        }
        part personnelTrackingConsole : PersonnelTrackingConsole {
            perform action a0 { doc /* helps the organization maintain an accurate view of personnel assigned to offshore activities @S094 */ }
            perform action a1 { doc /* maintains the offshore personnel roster and expected return times @S234 */ }
            perform action a2 { doc /* supports confirmation that personnel assigned to the task are accounted for at the work location @S332 */ }
            perform action a3 { doc /* maintains the current accountability status for personnel assigned to offshore work @S392 */ }
            perform action a4 { doc /* maintains the operational count for active marine movements @S571 */ }
            perform action a5 { doc /* is used by the Personnel Tracking Console @S573 */ }
            perform action a6 { doc /* update a verified personnel total @S573 */ }
            perform action a7 { doc /* supports personnel accounting @S619 */ }
            perform action a8 { doc /* supports confirmation that all assigned personnel have returned to a safe location @S648 */ }
            perform action a9 { doc /* supports accountability checks for personnel assigned to the affected work area @S805 */ }
            perform action a10 { doc /* maintain an accurate record of personnel entering and leaving the route @S874 */ }
        }
        part personsStillUnaccountedFor : PersonsStillUnaccountedFor {
            exhibit state modes {
                state s0 { doc /* unaccounted for @S584 */ }
            }
        }
        part physicalBoundary : PhysicalBoundary;
        part pitchSystem : PitchSystem {
            perform action a0 { doc /* changes blade angle in response to turbine control commands and local protection logic @S130 */ }
            perform action a1 { doc /* adjusts blade angle within its operating envelope @S546 */ }
            perform action a2 { doc /* does not override local protection limits @S546 */ }
            perform action a3 { doc /* retain its approved control behavior @S601 */ }
            perform action a4 { doc /* moves the blades to the defined safe position @S790 */ }
        }
        part plannedCrewAssignments : PlannedCrewAssignments {
            perform action a0 { doc /* match the approved work schedule @S396 */ }
        }
        part plannedOutage : PlannedOutage {
            perform action a0 { doc /* could restrict power transfer @S745 */ }
        }
        part plannedRestorationChecks : PlannedRestorationChecks {
            perform action a0 { doc /* have completed @S532 */ }
        }
        part plannedTask : PlannedTask {
            perform action a0 { doc /* proceeding @S285 */ }
            perform action a1 { doc /* matches the approved work authorization @S491 */ }
        }
        part plannedTests : PlannedTests {
            perform action a0 { doc /* conflicting with dispatch obligations or active maintenance work @S219 */ }
        }
        part plannedWork : PlannedWork {
            perform action a0 { doc /* can proceed within the lift capacity and operating limits @S872 */ }
        }
        part planners : Planners {
            perform action a0 { doc /* assess whether cable condition warrants inspection or corrective intervention @S252 */ }
        }
        part portAgent : PortAgent {
            perform action a0 { doc /* supports shore-side arrangements for vessel calls, crew access, and staged cargo @S093 */ }
            perform action a1 { doc /* coordinates port services @S240 */ }
            perform action a2 { doc /* confirms that planned departures can be supported @S240 */ }
            perform action a3 { doc /* issues the Berth Slot Confirmation for the planned work period @S324 */ }
        }
        part portAndBerthCoordination : PortAndBerthCoordination {
            perform action a0 { doc /* aligns vessel access with the readiness of offshore work, people, equipment, and permits @S465 */ }
        }
        part portConditions : PortConditions {
            perform action a0 { doc /* can delay loading @S471 */ }
            perform action a1 { doc /* restrict vessel movement @S471 */ }
        }
        part portSchedule : PortSchedule {
            perform action a0 { doc /* includes time for arrival checks, passenger movements, cargo handling, refueling, and routine vessel servicing @S468 */ }
        }
        part portSupport : PortSupport;
        part positionIntegrityChecks : PositionIntegrityChecks {
            perform action a0 { doc /* fail @S105 */ }
        }
        part procedure : Procedure {
            perform action a0 { doc /* requires it @S331 */ }
        }
        part production : Production;
        part prohibitedPaths : ProhibitedPaths {
            perform action a0 { doc /* remain blocked @S121 */ }
        }
        part proposedControls : ProposedControls {
            perform action a0 { doc /* match the task scope and site conditions @S266 */ }
        }
        part proposedSequence : ProposedSequence {
            perform action a0 { doc /* supports the approved work @S516 */ }
            exhibit state modes {
                state s0 { doc /* paused @S535 */ }
            }
        }
        part proposedWorkaround : ProposedWorkaround {
            perform action a0 { doc /* changes established access, isolation, or personnel-control arrangements @S949 */ }
        }
        part protectedOperationalNetworks : ProtectedOperationalNetworks {
            perform action a0 { doc /* support safe farm operations @S100 */ }
        }
        part protectionActions : ProtectionActions {
            perform action a0 { doc /* have completed @S799 */ }
        }
        part protectionAlarm : ProtectionAlarm {
            perform action a0 { doc /* occurs @S360 */ }
        }
        part protectionCoordination : ProtectionCoordination {
            perform action a0 { doc /* prevents a fault on the external system from causing unnecessary disconnection of healthy farm equipment @S208 */ }
        }
        part protectiveDevices : ProtectiveDevices {
            perform action a0 { doc /* show no active fault indication @S867 */ }
            exhibit state modes {
                state s0 { doc /* functional @S893 */ }
            }
        }
        part protectiveFunctions : ProtectiveFunctions {
            perform action a0 { doc /* used by protective functions and operational monitoring @S788 */ }
        }
        part qualifiedTechnician : QualifiedTechnician {
            perform action a0 { doc /* checks the device at the point of isolation @S719 */ }
        }
        part quantitiesAlreadyCommittedToTransfer : QuantitiesAlreadyCommittedToTransfer;
        part quantitiesOnHand : QuantitiesOnHand;
        part rain : Rain {
            perform action a0 { doc /* move through the area @S662 */ }
        }
        part ramping : Ramping {
            perform action a0 { doc /* is stressing equipment @S556 */ }
        }
        part ratedCapacity : RatedCapacity {
            exhibit state modes {
                state s0 { doc /* legible @S868 */ }
            }
        }
        part receiver : Receiver {
            perform action a0 { doc /* repeats critical details @S773 */ }
        }
        part reconciliation : Reconciliation {
            perform action a0 { doc /* applies to each movement between shore, a vessel, and an offshore work location @S564 */ }
        }
        part record : Record {
            perform action a0 { doc /* supports routine review of access activity and investigation of anomalies @S844 */ }
        }
        part records : Records {
            perform action a0 { doc /* use synchronized time sources where available @S776 */ }
        }
        part recoveredComponents : RecoveredComponents {
            perform action a0 { doc /* support repair planning @S656 */ }
        }
        part recovery : Recovery {
            perform action a0 { doc /* begins @S436 */ }
            perform action a1 { doc /* begins @S952 */ }
        }
        part recoveryHandling : RecoveryHandling {
            perform action a0 { doc /* could affect turbine systems or restart readiness @S658 */ }
        }
        part recoveryTask : RecoveryTask {
            perform action a0 { doc /* does not conflict with other offshore work @S639 */ }
        }
        part reducedVisibility : ReducedVisibility {
            perform action a0 { doc /* could compromise separation from other vessels or structures @S679 */ }
        }
        part releasedRevisions : ReleasedRevisions {
            perform action a0 { doc /* identify the change, rationale, approval, effective date, and superseded baseline @S980 */ }
        }
        part reliabilityReviews : ReliabilityReviews {
            perform action a0 { doc /* consider failure frequency, failure duration, recurrence, and the operational consequences of each event @S921 */ }
        }
        part remoteAdministrativeFunctions : RemoteAdministrativeFunctions {
            exhibit state modes {
                state s0 { doc /* restricted state @S118 */ }
            }
        }
        part remoteEvidence : RemoteEvidence {
            perform action a0 { doc /* cannot resolve a material uncertainty @S310 */ }
        }
        part remoteIndications : RemoteIndications {
            perform action a0 { doc /* agree with the approved switching state @S718 */ }
        }
        part remoteOperation : RemoteOperation {
            perform action a0 { doc /* begins @S138 */ }
        }
        part remoteRequests : RemoteRequests {
            perform action a0 { doc /* conflict with safe operating limits @S137 */ }
        }
        part remoteSessions : RemoteSessions {
            perform action a0 { doc /* require approved connection paths, strong authentication, and active supervision @S427 */ }
            perform action a1 { doc /* can affect live operations @S427 */ }
        }
        part remoteSurveys : RemoteSurveys {
            perform action a0 { doc /* use the Blade Inspection Drone @S444 */ }
        }
        part repairPlans : RepairPlans {
            perform action a0 { doc /* identify surface preparation, material application, cure requirements, inspection hold points, and acceptance criteria @S462 */ }
        }
        part repairedArea : RepairedArea {
            perform action a0 { doc /* meets the applicable acceptance criteria @S463 */ }
        }
        part replenishmentCoordination : ReplenishmentCoordination;
        part replenishmentRequests : ReplenishmentRequests {
            perform action a0 { doc /* include the required quantity, need date, delivery location, and applicable handling requirements @S699 */ }
        }
        part reportedEvents : ReportedEvents;
        part reportedStateChange : ReportedStateChange {
            perform action a0 { doc /* matches the approved sequence @S534 */ }
        }
        part requester : Requester {
            perform action a0 { doc /* identifies the equipment affected @S152 */ }
            perform action a1 { doc /* describes the intended work in terms that can be checked against operating constraints @S152 */ }
        }
        part requiredElectricalIsolations : RequiredElectricalIsolations {
            exhibit state modes {
                state s0 { doc /* in place @S801 */ }
            }
        }
        part requiredOperatingConditions : RequiredOperatingConditions {
            perform action a0 { doc /* can be maintained @S736 */ }
        }
        part requiredOperationalChecks : RequiredOperationalChecks {
            exhibit state modes {
                state s0 { doc /* complete @S338 */ }
            }
        }
        part requiredQuantity : RequiredQuantity;
        part rescueCoordinator : RescueCoordinator {
            perform action a0 { doc /* maintains the response arrangements for incidents involving vessels or personnel @S244 */ }
            perform action a1 { doc /* leads rescue planning @S614 */ }
            perform action a2 { doc /* coordinates requests for external assistance @S614 */ }
            perform action a3 { doc /* revises the response plan @S634 */ }
            perform action a4 { doc /* establishes the recovery objective @S637 */ }
            perform action a5 { doc /* confirms who has authority to suspend the operation @S637 */ }
            perform action a6 { doc /* uses the load sheet @S646 */ }
            perform action a7 { doc /* confirm that recovery baskets are secured and their contents are accounted for before transfer @S646 */ }
        }
        part reservations : Reservations {
            perform action a0 { doc /* prevent the same available quantity from being assigned to multiple work packages @S693 */ }
        }
        part residualUncertainty : ResidualUncertainty {
            perform action a0 { doc /* warrants it @S464 */ }
        }
        part resourceAvailability : ResourceAvailability {
            perform action a0 { doc /* change @S224 */ }
        }
        part responders : Responders {
            perform action a0 { doc /* use alongside direct reports from personnel on site @S629 */ }
        }
        part response : Response {
            perform action a0 { doc /* prioritizes safe operation @S306 */ }
            perform action a1 { doc /* restricts work until the condition is understood @S306 */ }
            perform action a2 { doc /* requires additional deck space or lifting capability @S645 */ }
            perform action a3 { doc /* does not conceal a remaining restriction elsewhere @S956 */ }
        }
        part responsibleAuthority : ResponsibleAuthority {
            perform action a0 { doc /* approves restoration @S732 */ }
        }
        part responsibleControlPersonnel : ResponsibleControlPersonnel;
        part responsibleManager : ResponsibleManager {
            perform action a0 { doc /* reviews record completeness after significant events @S784 */ }
            perform action a1 { doc /* assigns correction or follow-up actions where evidence is missing @S784 */ }
        }
        part responsibleOperationalAuthority : ResponsibleOperationalAuthority {
            perform action a0 { doc /* confirms that conditions permit work to proceed @S500 */ }
        }
        part responsibleOperationsStaff : ResponsibleOperationsStaff {
            perform action a0 { doc /* review @S754 */ }
        }
        part responsibleOperator : ResponsibleOperator {
            perform action a0 { doc /* has confirmed that the equipment is stable @S952 */ }
        }
        part responsibleOrganization : ResponsibleOrganization;
        part responsiblePersonnel : ResponsiblePersonnel {
            perform action a0 { doc /* confirm that operations can resume safely @S086 */ }
        }
        part responsibleSupervisor : ResponsibleSupervisor {
            perform action a0 { doc /* keeps a local record @S413 */ }
            perform action a1 { doc /* reports it when service is restored @S413 */ }
        }
        part responsibleTeam : ResponsibleTeam {
            perform action a0 { doc /* reports completion status and outstanding issues @S170 */ }
            perform action a1 { doc /* verifies turbine isolation, rotor restraint, access arrangements, and rescue provisions @S450 */ }
        }
        part restorationChecks : RestorationChecks {
            exhibit state modes {
                state s0 { doc /* complete @S759 */ }
            }
        }
        part restrictions : Restrictions {
            perform action a0 { doc /* could affect export capability @S378 */ }
            perform action a1 { doc /* remain in force @S730 */ }
            exhibit state modes {
                state s0 { doc /* in force @S730 */ }
            }
        }
        part review : Review {
            perform action a0 { doc /* identifies hazards, required controls, access arrangements, and any operating coordination needed @S156 */ }
        }
        part reviewTeams : ReviewTeams {
            perform action a0 { doc /* distinguish equipment faults from external causes such as access limitations, weather conditions, and grid restrictions @S922 */ }
        }
        part reviewers : Reviewers {
            perform action a0 { doc /* distinguish environmental effects from equipment deterioration @S309 */ }
            perform action a1 { doc /* assess safety effects, cybersecurity risks, interfaces, and the impact on ongoing maintenance activities @S596 */ }
        }
        part reviews : Reviews {
            perform action a0 { doc /* distinguish verified evidence from assumptions, unresolved actions, and proposals that have not yet been approved @S974 */ }
        }
        part riskAssessments : RiskAssessments;
        part rotorBrakeUnit : RotorBrakeUnit {
            perform action a0 { doc /* applies braking only in accordance with the turbine protection sequence and operating limits @S791 */ }
        }
        part route : Route {
            perform action a0 { doc /* does not provide an alternate way to bypass work authorization or site restrictions @S842 */ }
            exhibit state modes {
                state s0 { doc /* clear of obstructions @S887 */ }
                state s1 { doc /* in service @S853 */ }
                state s2 { doc /* out of service @S855 */ }
            }
        }
        part routineChecks : RoutineChecks {
            perform action a0 { doc /* confirm that credential readers, indicators, and barrier controls operate as intended @S854 */ }
        }
        part routineRounds : RoutineRounds {
            perform action a0 { doc /* cover room temperature, ventilation, water ingress, lighting, access control, and visible signs of damage @S344 */ }
        }
        part routineTools : RoutineTools {
            exhibit state modes {
                state s0 { doc /* clear @S335 */ }
            }
        }
        part rule : Rule {
            perform action a0 { doc /* determined the outcome @S822 */ }
        }
        part sCADAEngineer : SCADAEngineer {
            perform action a0 { doc /* maintains the configuration and technical integrity of supervisory interfaces @S062 */ }
            perform action a1 { doc /* use individually assigned accounts rather than shared credentials for interactive work @S423 */ }
            perform action a2 { doc /* validates restored configurations and communications @S437 */ }
            perform action a3 { doc /* investigates telemetry gaps or inconsistent measurements @S558 */ }
            perform action a4 { doc /* uses the Firmware Hash Attestation @S593 */ }
            perform action a5 { doc /* verify the approved image @S593 */ }
            perform action a6 { doc /* loading a release @S593 */ }
            perform action a7 { doc /* investigates missing or inconsistent indications @S946 */ }
            perform action a8 { doc /* verifies that status, alarms, and command feedback are consistent across the available control views @S954 */ }
            perform action a9 { doc /* reviews monitoring and control assumptions that affect operational decisions @S968 */ }
        }
        part sCADAGateway : SCADAGateway {
            perform action a0 { doc /* provides a controlled boundary for supervisory data exchange between offshore assets and shore-based operations @S052 */ }
            perform action a1 { doc /* mediates supervisory exchanges @S059 */ }
            perform action a2 { doc /* supports consistent access to operational information @S059 */ }
            perform action a3 { doc /* presents turbine status and control availability to authorized shore personnel @S133 */ }
            perform action a4 { doc /* uses the deviation notice @S159 */ }
            perform action a5 { doc /* flag work packages that may require technical review @S159 */ }
            perform action a6 { doc /* shall provide current operational status to permit reviewers @S171 */ }
            perform action a7 { doc /* presents supply alarms and generator status to the Shore Control Room for remote awareness @S192 */ }
            perform action a8 { doc /* provides relay status and interface measurements to the farm monitoring environment @S211 */ }
            perform action a9 { doc /* produces the Session Revocation Receipt @S212 */ }
            perform action a10 { doc /* forwards time-stamped observations to the Shore Control Room for review against configured operating limits @S295 */ }
            perform action a11 { doc /* provides the operational measurements used to track delivered power and instruction response @S369 */ }
            perform action a12 { doc /* records security-relevant access and control events for review @S417 */ }
            perform action a13 { doc /* provides operating data @S447 */ }
            perform action a14 { doc /* presents current generation, export, and equipment status to the operations team @S540 */ }
            perform action a15 { doc /* carries operational data to the Shore Control Room @S767 */ }
            perform action a16 { doc /* preserves source timestamps where available @S767 */ }
            perform action a17 { doc /* supports alarm visibility at the shore operating position @S800 */ }
            perform action a18 { doc /* without replacing local emergency controls @S800 */ }
            perform action a19 { doc /* provides operational records used to assess turbine availability and production trends @S914 */ }
            perform action a20 { doc /* preserves available status and alarm information @S946 */ }
        }
        part safetyFunctions : SafetyFunctions {
            perform action a0 { doc /* take priority over energy production, maintenance throughput, and schedule recovery in every degraded mode @S936 */ }
        }
        part safetyPerformanceMeasures : SafetyPerformanceMeasures {
            perform action a0 { doc /* include reported events, completion of required controls, and timely closure of corrective actions @S912 */ }
        }
        part scanner : Scanner {
            perform action a0 { doc /* checks that the credential is active and belongs to the person presenting it @S840 */ }
            perform action a1 { doc /* records each successful entry and each denied attempt with a time reference @S843 */ }
            perform action a2 { doc /* cannot complete a check @S846 */ }
            exhibit state modes {
                state s0 { doc /* unavailable @S856 */ }
            }
        }
        part scheduledExercising : ScheduledExercising {
            perform action a0 { doc /* confirms that the Emergency Generator can start, accept its expected load, and operate for the required test duration @S186 */ }
        }
        part scheduledSurveillance : ScheduledSurveillance {
            perform action a0 { doc /* indicate that blade condition requires review @S440 */ }
        }
        part seaOrWeatherConditions : SeaOrWeatherConditions {
            perform action a0 { doc /* make transfer unsafe @S499 */ }
        }
        part section : Section {
            perform action a0 { doc /* describes turbine control and remote observation during offshore operations @S123 */ }
            perform action a1 { doc /* defines how personnel counts are reconciled during marine operations and how discrepancies are escalated @S563 */ }
        }
        part securityMonitoring : SecurityMonitoring {
            exhibit state modes {
                state s0 { doc /* continuous @S421 */ }
            }
        }
        part sender : Sender {
            perform action a0 { doc /* confirms that the read-back is accurate @S773 */ }
        }
        part sensors : Sensors {
            perform action a0 { doc /* limit exposure to spray, icing, vibration, and corrosion @S103 */ }
        }
        part serialControlledParts : SerialControlledParts {
            perform action a0 { doc /* retain traceability from receipt through installation, repair, return, or disposal @S692 */ }
        }
        part service : Service {
            exhibit state modes {
                state s0 { doc /* restored @S413 */ }
            }
        }
        part serviceOperationsVessel : ServiceOperationsVessel {
            perform action a0 { doc /* may support offshore work @S045 */ }
            perform action a1 { doc /* provides a platform for work that needs longer offshore presence or broader onboard support @S089 */ }
            perform action a2 { doc /* provides a stable offshore base @S228 */ }
            perform action a3 { doc /* may provide a more stable work platform @S281 */ }
            perform action a4 { doc /* prepares the Recovery Basket Load Sheet for the planned work activity @S461 */ }
            perform action a5 { doc /* may provide accommodation, medical support, and a stable platform @S622 */ }
            perform action a6 { doc /* provides a stable working platform @S645 */ }
            perform action a7 { doc /* may maintain a safe stand-off @S680 */ }
        }
        part severity : Severity {
            perform action a0 { doc /* exceeds the operating threshold @S303 */ }
        }
        part shiftHandover : ShiftHandover {
            perform action a0 { doc /* records outstanding isolations, affected equipment, and any restrictions that remain in force @S730 */ }
        }
        part shiftRecords : ShiftRecords {
            perform action a0 { doc /* capture inspections, alarms, tests, switching actions, defects, and handover items @S365 */ }
            perform action a1 { doc /* capture dispatch instructions, constraint decisions, measured response, and unresolved follow-up actions @S389 */ }
        }
        part shoreBasedPersonnel : ShoreBasedPersonnel;
        part shoreBasedPlanning : ShoreBasedPlanning;
        part shoreControlRoom : ShoreControlRoom {
            perform action a0 { doc /* provides a shore-based operating location for authorized personnel @S040 */ }
            perform action a1 { doc /* provides a shared operational context for personnel responsible for offshore assets @S064 */ }
            perform action a2 { doc /* maintains operational oversight @S097 */ }
            perform action a3 { doc /* provides a point of coordination for shore-based personnel @S097 */ }
            perform action a4 { doc /* maintains operational oversight @S099 */ }
            perform action a5 { doc /* provides a point of coordination for shore-based personnel @S099 */ }
            perform action a6 { doc /* provides a staffed location for supervisory control and operational review @S134 */ }
            perform action a7 { doc /* coordinates operational notices and control-room decisions affecting the farm interface @S214 */ }
            perform action a8 { doc /* maintains an overview of active marine operations and operational restrictions @S238 */ }
            perform action a9 { doc /* escalates an alert @S303 */ }
            perform action a10 { doc /* retains the decision record, supporting observations, and response outcome for operational review @S317 */ }
            perform action a11 { doc /* retains the permit status, isolation history, test results, and restoration decision for operational review @S339 */ }
            perform action a12 { doc /* receives concise status updates, including operating limitations and the expected time of the next review @S364 */ }
            perform action a13 { doc /* maintains the current dispatch target, ramp rate, and next review time in the shift record @S371 */ }
            perform action a14 { doc /* uses the tap snapshot @S374 */ }
            perform action a15 { doc /* check the recorded transformer position during export reviews @S374 */ }
            perform action a16 { doc /* maintains the last validated operating limit @S386 */ }
            perform action a17 { doc /* seeking clarification through the approved channel @S386 */ }
            perform action a18 { doc /* maintains an operational view of affected systems @S420 */ }
            perform action a19 { doc /* coordinates immediate protective actions @S420 */ }
            perform action a20 { doc /* monitors turbine status @S448 */ }
            perform action a21 { doc /* records any operating restrictions required during the remote survey @S448 */ }
            perform action a22 { doc /* sends the Switching Window Acknowledgment @S531 */ }
            perform action a23 { doc /* confirms that monitoring and operator procedures remain suitable for the revised configuration @S606 */ }
            perform action a24 { doc /* maintains the incident log @S613 */ }
            perform action a25 { doc /* provides a single operational point of contact for offshore teams @S613 */ }
            perform action a26 { doc /* maintains awareness of the decision and the operational restrictions associated with the assessment @S683 */ }
            perform action a27 { doc /* assesses incoming alarms @S798 */ }
            perform action a28 { doc /* confirms the affected asset @S798 */ }
            perform action a29 { doc /* initiates the response appropriate to the reported severity @S798 */ }
            perform action a30 { doc /* monitors the loss of visibility @S937 */ }
            perform action a31 { doc /* applies the approved operating concept during routine operations and abnormal conditions @S963 */ }
        }
        part shorePersonnel : ShorePersonnel {
            perform action a0 { doc /* can anticipate vessel arrivals @S410 */ }
        }
        part shortLivedFluctuations : ShortLivedFluctuations {
            perform action a0 { doc /* fall within the agreed control tolerance @S555 */ }
        }
        part shortage : Shortage {
            perform action a0 { doc /* threatens a work window @S702 */ }
        }
        part signs : Signs {
            perform action a0 { doc /* identify the permitted approach @S852 */ }
            perform action a1 { doc /* direct personnel to the controlled entry point @S852 */ }
        }
        part siteFireRiskAssessment : SiteFireRiskAssessment {
            perform action a0 { doc /* identified by the site fire risk assessment @S787 */ }
        }
        part siteMeasurements : SiteMeasurements {
            perform action a0 { doc /* help assess whether a planned response remains feasible @S625 */ }
        }
        part siteSpecificDetectionAndTripSettings : SiteSpecificDetectionAndTripSettings {
            perform action a0 { doc /* account for its design and operating conditions @S795 */ }
        }
        part softwareChanges : SoftwareChanges {
            perform action a0 { doc /* affecting protection functions or control behavior @S597 */ }
            perform action a1 { doc /* receive additional engineering scrutiny @S597 */ }
            perform action a2 { doc /* affecting the Offshore Substation @S603 */ }
        }
        part southAccessScanner : SouthAccessScanner {
            perform action a0 { doc /* records authorized entry at the south access point @S236 */ }
            perform action a1 { doc /* records identity checks at the south shore access point @S395 */ }
            perform action a2 { doc /* records personnel access events at the south access point @S570 */ }
            perform action a3 { doc /* checks that the authorization is active for the scheduled work period @S813 */ }
            perform action a4 { doc /* checks that the requested access area is within the person's approved scope @S814 */ }
            perform action a5 { doc /* cannot verify a credential @S816 */ }
            perform action a6 { doc /* retrieve the required authorization information @S816 */ }
            perform action a7 { doc /* displays a clear outcome without exposing unnecessary personal information to people nearby @S831 */ }
            perform action a8 { doc /* exposing unnecessary personal information to people nearby @S831 */ }
            perform action a9 { doc /* serves the designated southern entry route to the offshore wind farm @S835 */ }
            perform action a10 { doc /* applies the same identity verification standard used at other controlled entry points @S838 */ }
            exhibit state modes {
                state s0 { doc /* unavailable @S828 */ }
            }
        }
        part sparesHub : SparesHub {
            perform action a0 { doc /* provides a separate view of stock held for regional replenishment and emergency support @S689 */ }
        }
        part spray : Spray {
            perform action a0 { doc /* move through the area @S662 */ }
        }
        part stableConditions : StableConditions {
            perform action a0 { doc /* are confirmed @S196 */ }
        }
        part staleOrImplausibleValue : StaleOrImplausibleValue {
            exhibit state modes {
                state s0 { doc /* unverified @S300 */ }
            }
        }
        part startTime : StartTime;
        part stationServiceTransformers : StationServiceTransformers {
            perform action a0 { doc /* supply the facility's auxiliary electrical loads from the medium-voltage collection system @S173 */ }
        }
        part statusIndications : StatusIndications {
            perform action a0 { doc /* support assessment of the normal supply and its protective state @S190 */ }
        }
        part step : Step {
            perform action a0 { doc /* can be performed within the available interval @S741 */ }
        }
        part stockVisibility : StockVisibility;
        part storekeeper : Storekeeper {
            perform action a0 { doc /* checks requested materials against available stock @S092 */ }
            perform action a1 { doc /* coordinates replenishment with the Spares Hub @S092 */ }
            perform action a2 { doc /* prepares requested equipment for dispatch in accordance with the approved work plan @S242 */ }
            perform action a3 { doc /* uses the exception slip @S262 */ }
            perform action a4 { doc /* validate an unavailable part @S262 */ }
            perform action a5 { doc /* checks repair materials and tooling against the approved repair method @S460 */ }
            perform action a6 { doc /* checks that critical spares are available and that packaging is suitable for marine transport @S479 */ }
            perform action a7 { doc /* reconciles physical counts with recorded balances @S690 */ }
            perform action a8 { doc /* records adjustments with a reason and timestamp @S690 */ }
            perform action a9 { doc /* records unavailable quantities and the expected date of the next supply @S703 */ }
            perform action a10 { doc /* presenting them as available stock @S703 */ }
            perform action a11 { doc /* confirms that equipment intended for the lift is ready and properly identified for the work party @S876 */ }
        }
        part substationLimitation : SubstationLimitation {
            perform action a0 { doc /* could require a lower export target or local equipment action @S559 */ }
        }
        part substationOperator : SubstationOperator {
            perform action a0 { doc /* confirms that switching actions affecting the export path are within the authorized work scope @S216 */ }
            perform action a1 { doc /* confirms local operating constraints @S268 */ }
            perform action a2 { doc /* applies authorized switching actions @S326 */ }
            perform action a3 { doc /* records the resulting equipment state @S326 */ }
            perform action a4 { doc /* removes isolations only under the approved switching process @S337 */ }
            perform action a5 { doc /* records each restoration action @S337 */ }
            perform action a6 { doc /* maintains the Offshore Substation within approved operating limits @S342 */ }
            perform action a7 { doc /* follows current switching instructions @S342 */ }
            perform action a8 { doc /* reviews alarms, active restrictions, equipment status, and handover notes @S343 */ }
            perform action a9 { doc /* checks Main Transformer temperatures, cooling equipment, oil indications, and abnormal noise against established limits @S345 */ }
            perform action a10 { doc /* verifies that personnel access records are consistent with the planned work and current site occupancy @S351 */ }
            perform action a11 { doc /* confirms fuel level, starting battery condition, ventilation, and readiness of the Emergency Generator for loss of normal supply @S354 */ }
            perform action a12 { doc /* coordinates switching activity that could alter the available export configuration @S382 */ }
            perform action a13 { doc /* confirms that switching conditions affecting the worksite are understood by the relevant personnel @S497 */ }
            perform action a14 { doc /* verifies equipment status and switching points at the Offshore Substation @S517 */ }
            perform action a15 { doc /* accepts the instructions @S530 */ }
            perform action a16 { doc /* checking the equipment state @S530 */ }
            perform action a17 { doc /* confirming authorization with the Control Engineer @S530 */ }
            perform action a18 { doc /* is entered in the operating log @S531 */ }
            perform action a19 { doc /* uses the test trace @S532 */ }
            perform action a20 { doc /* verify that the planned restoration checks have completed @S532 */ }
            perform action a21 { doc /* requesting the next switching step @S532 */ }
            perform action a22 { doc /* reports any substation limitation that could require a lower export target or local equipment action @S559 */ }
            perform action a23 { doc /* reviews the switching sequence @S741 */ }
            perform action a24 { doc /* confirms that each step can be performed within the available interval @S741 */ }
            perform action a25 { doc /* does not begin switching until the window is active and operational authority has been confirmed @S753 */ }
            perform action a26 { doc /* confirmed by the responsible Substation Operator or Electrical Technician @S770 */ }
            perform action a27 { doc /* reviews responsibilities and coordination arrangements for substation activities @S971 */ }
        }
        part substationSwitchingWindows : SubstationSwitchingWindows {
            perform action a0 { doc /* are coordinated with planned maintenance @S736 */ }
        }
        part substationWork : SubstationWork {
            exhibit state modes {
                state s0 { doc /* in progress @S742 */ }
            }
        }
        part substitutions : Substitutions;
        part supersededVersions : SupersededVersions {
            exhibit state modes {
                state s0 { doc /* unavailable for active work @S728 */ }
            }
        }
        part supervisoryFaults : SupervisoryFaults {
            perform action a0 { doc /* require assessment @S796 */ }
            perform action a1 { doc /* do not indicate an active fire @S796 */ }
        }
        part supplyInterfaces : SupplyInterfaces;
        part supportingMarineAndShoreFacilities : SupportingMarineAndShoreFacilities;
        part switchingActions : SwitchingActions {
            perform action a0 { doc /* affecting the export path @S216 */ }
        }
        part switchingActivity : SwitchingActivity {
            perform action a0 { doc /* could alter the available export configuration @S382 */ }
        }
        part switchingCoordination : SwitchingCoordination {
            perform action a0 { doc /* begins with a defined operational need, a safe sequence, and an agreed period for execution @S514 */ }
        }
        part switchingOperator : SwitchingOperator {
            perform action a0 { doc /* performs each authorized action @S533 */ }
            perform action a1 { doc /* reports completion @S533 */ }
        }
        part systemPart : System {
            perform action a0 { doc /* transition from construction control to operations control through documented handover and verification @S015 */ }
            perform action a1 { doc /* raises an alarm @S183 */ }
            perform action a2 { doc /* maintains any available uninterruptible control power @S183 */ }
            perform action a3 { doc /* retains successful and unsuccessful attempts under the site's access record retention policy @S824 */ }
            perform action a4 { doc /* measures operational performance against approved service objectives and documented fleet baselines @S908 */ }
            perform action a5 { doc /* records the affected function, the detected condition, and the time of transition @S935 */ }
            perform action a6 { doc /* retains the event record and recovery decisions for review, trend analysis, and improvement of operating procedures @S957 */ }
            exhibit state modes {
                state s0 { doc /* construction control @S015 */ }
                state s1 { doc /* normal service @S956 */ }
                state s2 { doc /* operations control @S015 */ }
            }
        }
        part systemArchitecture : SystemArchitecture {
            perform action a0 { doc /* separates offshore equipment, operational services, and shore-based decision functions @S051 */ }
            perform action a1 { doc /* preserving defined interfaces between them @S051 */ }
        }
        part task : Task {
            perform action a0 { doc /* presents a material personnel or environmental risk @S157 */ }
            perform action a1 { doc /* require a change to substation configuration @S737 */ }
        }
        part taskSelection : TaskSelection {
            perform action a0 { doc /* favors work that can be performed safely under the assessed conditions without relying on precise visual identification or close-range observation @S671 */ }
        }
        part tasks : Tasks {
            perform action a0 { doc /* can safely wait until normal access and support are available @S948 */ }
        }
        part team : Team {
            perform action a0 { doc /* checking forecast trends and current sea state @S271 */ }
            perform action a1 { doc /* also checks current observations and the task-specific limits @S280 */ }
            perform action a2 { doc /* considers forecast uncertainty @S289 */ }
            perform action a3 { doc /* deciding whether to commit crews, fuel, and vessel time to a remote work site @S289 */ }
            perform action a4 { doc /* commit crews, fuel, and vessel time to a remote work site @S289 */ }
            perform action a5 { doc /* demonstrating that the transfer or task can be completed within safe limits @S684 */ }
        }
        part technicalReviewers : TechnicalReviewers {
            perform action a0 { doc /* confirm that the work scope is compatible with equipment condition and the planned maintenance method @S158 */ }
        }
        part technicalTeams : TechnicalTeams {
            perform action a0 { doc /* isolate only the affected connection or service @S433 */ }
            perform action a1 { doc /* creating an unsafe operating condition @S433 */ }
            perform action a2 { doc /* review causes, response effectiveness, and corrective actions with operations management @S439 */ }
        }
        part technicians : Technicians {
            perform action a0 { doc /* begin affected tasks @S429 */ }
        }
        part temporaryConnections : TemporaryConnections {
            exhibit state modes {
                state s0 { doc /* clear @S335 */ }
            }
        }
        part temporaryPersonnel : TemporaryPersonnel {
            perform action a0 { doc /* follow the same identity checks as other entrants @S849 */ }
        }
        part testRequirements : TestRequirements {
            perform action a0 { doc /* fit the approved duration @S750 */ }
        }
        part timelyClosureOfCorrectiveActions : TimelyClosureOfCorrectiveActions;
        part tools : Tools;
        part transaction : Transaction {
            perform action a0 { doc /* records the credential identifier, decision time, access point, and decision outcome @S821 */ }
            perform action a1 { doc /* records the authorization version and the rule that determined the outcome @S822 */ }
        }
        part transfer : Transfer {
            perform action a0 { doc /* can proceed @S079 */ }
            perform action a1 { doc /* is permitted only after stable conditions are confirmed and the emergency source can be unloaded safely @S196 */ }
            perform action a2 { doc /* begins @S404 */ }
            perform action a3 { doc /* begins @S565 */ }
        }
        part transferArrangement : TransferArrangement {
            perform action a0 { doc /* prevents the normal and emergency sources from being connected in parallel unless an approved synchronizing function is provided @S179 */ }
        }
        part turbine : Turbine {
            exhibit state modes {
                state s0 { doc /* Turbine Lockout @S940 */ }
                state s1 { doc /* approved operating state @S444 */ }
            }
        }
        part turbineAlarms : TurbineAlarms {
            perform action a0 { doc /* indicate that blade condition requires review @S440 */ }
        }
        part turbineController : TurbineController {
            perform action a0 { doc /* performs local turbine control functions within the offshore equipment environment @S060 */ }
            perform action a1 { doc /* produces the Pitch Deviation Notice for operational handling @S061 */ }
            perform action a2 { doc /* adjusts turbine output within approved operating limits @S127 */ }
            perform action a3 { doc /* blocks commands that conflict with active protection conditions @S127 */ }
            perform action a4 { doc /* executes authorized control actions @S129 */ }
            perform action a5 { doc /* reports its operating state through established control interfaces @S129 */ }
            perform action a6 { doc /* enters its configured safe operating mode when required auxiliary services are unavailable @S191 */ }
            perform action a7 { doc /* adjusts output in accordance with validated plant commands and local equipment protections @S377 */ }
            perform action a8 { doc /* applies the accepted output target @S545 */ }
            perform action a9 { doc /* retaining its protective control functions @S545 */ }
            perform action a10 { doc /* initiates the configured shutdown response @S789 */ }
            perform action a11 { doc /* retains protective control locally @S937 */ }
            exhibit state modes {
                state s0 { doc /* safe operating mode @S191 */ }
            }
        }
        part turbineLockout : TurbineLockout {
            perform action a0 { doc /* remains in force until the responsible authority confirms that the equipment and work area are safe for subsequent activity @S657 */ }
            perform action a1 { doc /* prevents remote restart @S802 */ }
        }
        part turbineOperations : TurbineOperations {
            perform action a0 { doc /* can be managed safely @S742 */ }
        }
        part turbineResponse : TurbineResponse;
        part turbineSensorBus : TurbineSensorBus {
            perform action a0 { doc /* provides operating measurements @S251 */ }
            perform action a1 { doc /* collects operating measurements from the Turbine Controller, Pitch System, Converter Cabinet, and Nacelle Condition Monitor @S294 */ }
            perform action a2 { doc /* carries equipment status used by protective functions and operational monitoring @S788 */ }
        }
        part turbineStructures : TurbineStructures;
        part turbines : Turbines;
        part uncertainty : Uncertainty {
            perform action a0 { doc /* affects the planned transit, transfer location, and available alternatives @S676 */ }
            perform action a1 { doc /* increases during transit @S682 */ }
            perform action a2 { doc /* prevents the team from demonstrating that the transfer or task can be completed within safe limits @S684 */ }
        }
        part unnamed : Unnamed {
            perform action a0 { doc /* is entered with its location, scope, planned duration, and responsible team @S151 */ }
            perform action a1 { doc /* can be checked against operating constraints @S152 */ }
            perform action a2 { doc /* identified @S162 */ }
            perform action a3 { doc /* cannot be supplied by the planned issue date @S163 */ }
            perform action a4 { doc /* are recorded in the portal @S165 */ }
            perform action a5 { doc /* is limited to the stated scope, work location, time window, and assigned personnel @S166 */ }
            perform action a6 { doc /* requires reassessment @S168 */ }
            perform action a7 { doc /* may suspend the current authorization @S168 */ }
            perform action a8 { doc /* is closed @S170 */ }
            perform action a9 { doc /* requested as part of the authorization check @S171 */ }
        }
        part unplannedMaintenance : UnplannedMaintenance {
            perform action a0 { doc /* use prioritized fault assessment and controlled mobilization appropriate to the severity of the failure @S018 */ }
        }
        part urgentMessages : UrgentMessages {
            perform action a0 { doc /* identify the affected asset, the hazard or condition, the required action, and the person issuing the instruction @S772 */ }
        }
        part urgentPurchases : UrgentPurchases {
            perform action a0 { doc /* retain the same traceability and inspection controls as routine receipts @S707 */ }
        }
        part users : Users {
            perform action a0 { doc /* report unusual noise, vibration, door behavior, or control response immediately @S882 */ }
        }
        part validation : Validation {
            perform action a0 { doc /* fails @S846 */ }
        }
        part validationChecks : ValidationChecks {
            perform action a0 { doc /* cover sensor range, signal freshness, timestamp alignment, and consistency with related measurements @S298 */ }
        }
        part verbalRequest : VerbalRequest {
            perform action a0 { doc /* overrides a scanner denial @S818 */ }
        }
        part verification : Verification {
            perform action a0 { doc /* fails @S609 */ }
        }
        part verifiedHeadcount : VerifiedHeadcount {
            perform action a0 { doc /* differs from the departure record @S390 */ }
        }
        part vessel : Vessel {
            perform action a0 { doc /* leaves port @S398 */ }
            perform action a1 { doc /* gets underway @S399 */ }
            perform action a2 { doc /* occupies the berth @S478 */ }
            perform action a3 { doc /* can meet the agreed timing @S524 */ }
            perform action a4 { doc /* maintain safe operating margins @S524 */ }
            perform action a5 { doc /* departs the work location @S582 */ }
            perform action a6 { doc /* acts on them @S763 */ }
            exhibit state modes {
                state s0 { doc /* vessel standby @S488 */ }
            }
        }
        part vesselAISReceiver : VesselAISReceiver {
            perform action a0 { doc /* produces a Position Quality Flag @S105 */ }
            perform action a1 { doc /* collects vessel position broadcasts @S139 */ }
            perform action a2 { doc /* support marine traffic awareness @S139 */ }
            perform action a3 { doc /* maintains a time-stamped view of nearby vessel movements when broadcast coverage is available @S140 */ }
            perform action a4 { doc /* provides vessel position information for review against the planned route and operating area @S288 */ }
            perform action a5 { doc /* provides vessel position information for movement monitoring @S401 */ }
        }
        part vesselCapability : VesselCapability {
            perform action a0 { doc /* deteriorates @S659 */ }
        }
        part vesselCrews : VesselCrews;
        part vesselMaster : VesselMaster {
            perform action a0 { doc /* retains authority for navigation, vessel safety, and decisions about whether a transfer can proceed @S079 */ }
            perform action a1 { doc /* evaluates local conditions before departure @S085 */ }
            perform action a2 { doc /* continues to reassess them during the voyage @S085 */ }
            perform action a3 { doc /* confirms that the vessel plan can support the approved personnel and equipment transfer @S161 */ }
            perform action a4 { doc /* confirms departure readiness @S226 */ }
            perform action a5 { doc /* reports any change that could affect the passage @S226 */ }
            perform action a6 { doc /* receives the Transfer Manifest Addendum before departure @S278 */ }
            perform action a7 { doc /* considers the approach and transfer conditions acceptable @S279 */ }
            perform action a8 { doc /* can pause @S284 */ }
            perform action a9 { doc /* abort an approach @S284 */ }
            perform action a10 { doc /* produces the Crew Count Correction @S390 */ }
            perform action a11 { doc /* confirms the departure roster @S398 */ }
            perform action a12 { doc /* records crew changes that occur during transit or between offshore locations @S403 */ }
            perform action a13 { doc /* maintains an onboard count @S409 */ }
            perform action a14 { doc /* confirms practical arrival and departure estimates against the vessel's operating limits @S476 */ }
            perform action a15 { doc /* confirms that the vessel is safely positioned and that transfer conditions remain acceptable @S498 */ }
            perform action a16 { doc /* confirms that the vessel can meet the agreed timing and maintain safe operating margins @S524 */ }
            perform action a17 { doc /* are checked @S525 */ }
            perform action a18 { doc /* confirm that assigned personnel and permits are ready @S525 */ }
            perform action a19 { doc /* verifies the number of people physically aboard before departure @S567 */ }
            perform action a20 { doc /* maintains a safe operating position @S577 */ }
            perform action a21 { doc /* retains authority over vessel safety, navigation, and decisions to approach or withdraw from a casualty @S616 */ }
            perform action a22 { doc /* may withdraw @S634 */ }
            perform action a23 { doc /* retains authority over vessel movements @S642 */ }
            perform action a24 { doc /* may decline a task that cannot be completed safely @S642 */ }
            perform action a25 { doc /* retains authority to proceed, slow, alter course, or hold position based on actual conditions and vessel limits @S677 */ }
            perform action a26 { doc /* proceed @S677 */ }
            perform action a27 { doc /* slow @S677 */ }
            perform action a28 { doc /* alter course @S677 */ }
            perform action a29 { doc /* hold position @S677 */ }
            perform action a30 { doc /* reassess the route and the suitability of continuing toward the work site @S682 */ }
            perform action a31 { doc /* confirms safety-critical instructions using the agreed read-back procedure @S763 */ }
            perform action a32 { doc /* using the agreed read-back procedure @S763 */ }
            perform action a33 { doc /* maintains a safe position and readiness to support personnel recovery @S807 */ }
            perform action a34 { doc /* support personnel recovery @S807 */ }
            perform action a35 { doc /* confirm that personnel and vessels can remain safely accounted for during an extended interruption @S944 */ }
        }
        part vesselMovements : VesselMovements {
            perform action a0 { doc /* account for reduced speed, increased separation, and the possibility of returning to a safe holding area @S681 */ }
        }
        part vesselOperatingProcedures : VesselOperatingProcedures;
        part vesselPersonnel : VesselPersonnel;
        part vesselPlan : VesselPlan {
            perform action a0 { doc /* can support the approved personnel and equipment transfer @S161 */ }
        }
        part vesselRecoverySupport : VesselRecoverySupport {
            perform action a0 { doc /* coordinates people, vessels, and handling equipment @S636 */ }
        }
        part vessels : Vessels;
        part visibility : Visibility {
            perform action a0 { doc /* makes flight unsafe @S146 */ }
            perform action a1 { doc /* can vary across the wind farm @S662 */ }
            perform action a2 { doc /* could prevent reliable control or interpretation of inspection imagery @S673 */ }
        }
        part visitors : Visitors {
            perform action a0 { doc /* remain under escort @S508 */ }
            perform action a1 { doc /* follow the same identity checks as other entrants @S849 */ }
        }
        part warehouseSystem : WarehouseSystem {
            perform action a0 { doc /* records stock status @S091 */ }
            perform action a1 { doc /* supports preparation of equipment and consumables for scheduled work @S091 */ }
            perform action a2 { doc /* produces a Backorder Exception Slip @S163 */ }
            perform action a3 { doc /* records stock movements @S241 */ }
            perform action a4 { doc /* makes current inventory information available for logistics planning @S241 */ }
            perform action a5 { doc /* supports cargo preparation @S478 */ }
            perform action a6 { doc /* maintains the authoritative item catalogue, stock balances, and storage locations @S687 */ }
            perform action a7 { doc /* uses recurring failure and repair information @S928 */ }
            perform action a8 { doc /* inform review of critical spares and replenishment assumptions @S928 */ }
        }
        part weather : Weather {
            perform action a0 { doc /* makes flight unsafe @S146 */ }
            perform action a1 { doc /* prevents a planned task from proceeding @S285 */ }
            perform action a2 { doc /* deteriorates @S659 */ }
        }
        part weatherAnalyst : WeatherAnalyst {
            perform action a0 { doc /* reviews available forecasts @S084 */ }
            perform action a1 { doc /* advises the Marine Coordinator on conditions that may affect marine operations @S084 */ }
            perform action a2 { doc /* reviews forecast limitations @S107 */ }
            perform action a3 { doc /* identifies conditions that may affect vessel access or turbine work @S107 */ }
            perform action a4 { doc /* reviews forecast changes @S232 */ }
            perform action a5 { doc /* advises the Marine Coordinator @S232 */ }
            perform action a6 { doc /* reviews forecast confidence @S256 */ }
            perform action a7 { doc /* highlights conditions that could invalidate a planned access period @S256 */ }
            perform action a8 { doc /* compares forecast data with recent observations @S272 */ }
            perform action a9 { doc /* advising on the reliability of a work window @S272 */ }
            perform action a10 { doc /* uses the Wave Burst Record @S323 */ }
            perform action a11 { doc /* assess whether the planned access period remains suitable @S323 */ }
            perform action a12 { doc /* produces the Visibility Confidence Note @S472 */ }
            perform action a13 { doc /* summarize confidence in visibility conditions for near-term port and offshore planning @S472 */ }
            perform action a14 { doc /* reviews the forecast @S522 */ }
            perform action a15 { doc /* advises the Duty Planner if conditions could affect the planned sequence @S522 */ }
            perform action a16 { doc /* interprets forecast uncertainty @S626 */ }
            perform action a17 { doc /* communicates material changes to the Rescue Coordinator @S626 */ }
            perform action a18 { doc /* interprets forecast uncertainty @S641 */ }
            perform action a19 { doc /* identifies conditions that could affect safe vessel handling @S641 */ }
            perform action a20 { doc /* assesses forecast uncertainty @S765 */ }
            perform action a21 { doc /* communicates conditions that could affect access, lifting, or work at height @S765 */ }
            perform action a22 { doc /* support entry into Weather Hold @S939 */ }
        }
        part weatherConditions : WeatherConditions {
            perform action a0 { doc /* may affect operating margins or access decisions @S557 */ }
        }
        part weatherHold : WeatherHold {
            perform action a0 { doc /* pauses affected marine activity @S086 */ }
            perform action a1 { doc /* prevents mobilization @S259 */ }
        }
        part weatherService : WeatherService {
            perform action a0 { doc /* contributes environmental information to operational planning and coordination @S067 */ }
            perform action a1 { doc /* produces the Squall Window Bulletin for operational awareness @S083 */ }
            perform action a2 { doc /* uses validated environmental observations in forecast products for offshore planning @S106 */ }
            perform action a3 { doc /* issues forecast updates that support timing decisions for remote observation and field work @S128 */ }
            perform action a4 { doc /* provides forecast information for marine planning @S230 */ }
            perform action a5 { doc /* supplies forecast information @S255 */ }
            perform action a6 { doc /* provides forecast conditions and confidence information for planned work areas and vessel routes @S270 */ }
            perform action a7 { doc /* provide contextual conditions @S309 */ }
            perform action a8 { doc /* provide forecasts and measured conditions @S443 */ }
            perform action a9 { doc /* supplies forecast conditions relevant to access and safe execution @S521 */ }
            perform action a10 { doc /* provides forecast information for planning @S624 */ }
            perform action a11 { doc /* provides current forecasts for the recovery area and the planned transit route @S640 */ }
            perform action a12 { doc /* provide inputs @S766 */ }
            perform action a13 { doc /* support entry into Weather Hold @S939 */ }
        }
        part weatherServices : WeatherServices;
        part westServiceLift : WestServiceLift {
            perform action a0 { doc /* provides vertical access along the west route between the designated service landings @S884 */ }
            exhibit state modes {
                state s0 { doc /* removed from service @S907 */ }
            }
        }
        part windFarmAssets : WindFarmAssets;
        part window : Window {
            perform action a0 { doc /* is proposed @S738 */ }
        }
        part work : Work {
            perform action a0 { doc /* can proceed @S156 */ }
            perform action a1 { doc /* depends on recent machine behavior @S251 */ }
            perform action a2 { doc /* requires an offshore visit @S253 */ }
            perform action a3 { doc /* requiring controlled access or electrical isolation @S265 */ }
            perform action a4 { doc /* can proceed @S281 */ }
            perform action a5 { doc /* already in progress @S291 */ }
            perform action a6 { doc /* begins @S329 */ }
            perform action a7 { doc /* stop @S330 */ }
            perform action a8 { doc /* would reduce generation or access to export equipment @S388 */ }
            perform action a9 { doc /* begins @S496 */ }
            perform action a10 { doc /* proceed @S500 */ }
            perform action a11 { doc /* proceeds @S519 */ }
            perform action a12 { doc /* proceeds @S581 */ }
            perform action a13 { doc /* requiring visual alignment, external inspection, or unobstructed observation @S672 */ }
            perform action a14 { doc /* resumes @S685 */ }
            perform action a15 { doc /* stop @S717 */ }
            perform action a16 { doc /* continues @S727 */ }
            exhibit state modes {
                state s0 { doc /* complete @S426,S732 */ }
            }
        }
        part workArea : WorkArea {
            exhibit state modes {
                state s0 { doc /* ready for restoration @S336 */ }
            }
        }
        part workArrangements : WorkArrangements {
            perform action a0 { doc /* account for applicable safety controls and personnel responsibilities @S095 */ }
        }
        part workOnTheMainTransformer : WorkOnTheMainTransformer {
            perform action a0 { doc /* is scheduled @S744 */ }
        }
        part workPackages : WorkPackages {
            perform action a0 { doc /* may require technical review @S159 */ }
        }
        part workParty : WorkParty {
            perform action a0 { doc /* confirms equipment identity using permanent labels and the current site designation @S720 */ }
            perform action a1 { doc /* using permanent labels and the current site designation @S720 */ }
            exhibit state modes {
                state s0 { doc /* clear of the hazard area @S733 */ }
                state s1 { doc /* complete @S405 */ }
            }
        }
        part workPermitPortal : WorkPermitPortal {
            perform action a0 { doc /* supports authorization processes @S070 */ }
            perform action a1 { doc /* planning @S149 */ }
            perform action a2 { doc /* reviewing @S149 */ }
            perform action a3 { doc /* approving @S149 */ }
            perform action a4 { doc /* closing maintenance work @S149 */ }
            perform action a5 { doc /* maintains the request record and its revision history throughout review and execution @S155 */ }
            perform action a6 { doc /* records review decisions @S162 */ }
            perform action a7 { doc /* returns incomplete requests to the requester with the required corrections identified @S162 */ }
            perform action a8 { doc /* records the start, pause, resumption, and completion of authorized work against the permit record @S169 */ }
            perform action a9 { doc /* supports readiness checks for work requiring controlled access or electrical isolation @S265 */ }
            perform action a10 { doc /* block permit release @S321 */ }
            perform action a11 { doc /* produces the Isolation Boundary Sketch @S492 */ }
            perform action a12 { doc /* makes the approved boundary available to the work party and the control team @S713 */ }
            perform action a13 { doc /* retains the current approval @S728 */ }
            perform action a14 { doc /* makes superseded versions unavailable for active work @S728 */ }
            perform action a15 { doc /* reflect the agreed timing and work boundaries @S751 */ }
            perform action a16 { doc /* retains permit decisions and associated approvals in a form that can be retrieved for review @S780 */ }
        }
        part workPlan : WorkPlan {
            perform action a0 { doc /* requires extended support @S228 */ }
        }
        part workScope : WorkScope {
            perform action a0 { doc /* fit the approved duration @S750 */ }
        }
        part workforceInterfaces : WorkforceInterfaces;
        flow f0 of EnvironmentalInformationItem from weatherService to operationalPlanningAndCoordination { doc /* @S067 */ }
        flow f1 of InputItem from fieldSupervisor to dutyPlanner { doc /* @S076 */ }
        flow f2 of InputItem from maintenancePlanningEngine to dutyPlanner { doc /* @S076 */ }
        flow f3 of SharedViewOfVesselAssignmentsPlannedMovementsAndDispatchStatusItem from fleetDispatchConsole to marineCoordinator { doc /* @S081 */ }
        flow f5 of ConditionsThatMayAffectMarineOperationsItem from weatherAnalyst to marineCoordinator { doc /* @S084 */ }
        flow f6 of ChangesToWorkProgressItem from fieldSupervisor to dutyPlanner { doc /* @S096 */ }
        flow f7 of PointOfCoordinationItem from shoreControlRoom to shoreBasedPersonnel { doc /* @S097 */ }
        flow f9 of TurbineControlCommandsItem from turbineController to pitchSystem { doc /* @S130 */ }
        flow f10 of TurbineStatusItem from sCADAGateway to authorizedShorePersonnel { doc /* @S133 */ }
        flow f11 of ControlAvailabilityItem from sCADAGateway to authorizedShorePersonnel { doc /* @S133 */ }
        flow f12 of TimeStampedViewOfNearbyVesselMovementsItem from vesselAISReceiver to marineCoordinator { doc /* @S141 */ }
        flow f13 of CloseRangeVisualObservationsOfAccessibleBladeSurfacesItem from bladeInspectionDrone to fieldSupervisor { doc /* @S145 */ }
        flow f14 of IncompleteRequestsItem from workPermitPortal to requester { doc /* @S162 */ }
        flow f15 of CompletionStatusItem from responsibleTeam to unnamed { doc /* @S170 */ }
        flow f16 of OutstandingIssuesItem from responsibleTeam to unnamed { doc /* @S170 */ }
        flow f17 of CurrentOperationalStatusItem from sCADAGateway to permitReviewers { doc /* @S171 */ }
        flow f18 of SupplyAlarmsItem from sCADAGateway to shoreControlRoom { doc /* @S192 */ }
        flow f19 of GeneratorStatusItem from sCADAGateway to shoreControlRoom { doc /* @S192 */ }
        flow f20 of ElectricalPowerItem from offshoreFarm to offshoreSubstation { doc /* @S199 */ }
        flow f21 of ElectricalPowerItem from offshoreSubstation to mainTransformer { doc /* @S199 */ }
        flow f22 of ElectricalPowerItem from mainTransformer to exportCable { doc /* @S199 */ }
        flow f23 of ElectricalPowerItem from exportCable to designatedGridConnectionPoint { doc /* @S199 */ }
        flow f24 of AuthorizedOperatingSignalsItem from gridInterfaceRelay to externalTransmissionSystem { doc /* @S201 */ }
        flow f25 of AuthorizedOperatingSignalsItem from externalTransmissionSystem to gridInterfaceRelay { doc /* @S201 */ }
        flow f26 of RelayStatusItem from sCADAGateway to farmMonitoringEnvironment { doc /* @S211 */ }
        flow f27 of InterfaceMeasurementsItem from sCADAGateway to farmMonitoringEnvironment { doc /* @S211 */ }
        flow f28 of SquallWindowBulletinItem from weatherService to maintenancePlanningEngine { doc /* @S213 */ }
        flow f29 of ConditionsItem from weatherAnalyst to marineCoordinator { doc /* @S232 */ }
        flow f30 of UpdateItem from marineCoordinator to affectedTeams { doc /* @S245 */ }
        flow f31 of PlanItem from dutyPlanner to affectedTeams { doc /* @S269 */ }
        flow f32 of ObservationsItem from metoceanBuoy to team { doc /* @S271 */ }
        flow f33 of OperatingMeasurementsItem from turbineController to turbineSensorBus { doc /* @S294 */ }
        flow f34 of OperatingMeasurementsItem from pitchSystem to turbineSensorBus { doc /* @S294 */ }
        flow f35 of OperatingMeasurementsItem from converterCabinet to turbineSensorBus { doc /* @S294 */ }
        flow f36 of OperatingMeasurementsItem from nacelleConditionMonitor to turbineSensorBus { doc /* @S294 */ }
        flow f37 of TimeStampedObservationsItem from sCADAGateway to shoreControlRoom { doc /* @S295 */ }
        flow f38 of IndependentSignalsItem from turbineController to controlEngineer { doc /* @S299 */ }
        flow f39 of IndependentSignalsItem from nacelleConditionMonitor to controlEngineer { doc /* @S299 */ }
        flow f40 of ContextualConditionsItem from weatherService to reviewers { doc /* @S309 */ }
        flow f41 of ContextualConditionsItem from metoceanBuoy to reviewers { doc /* @S309 */ }
        flow f42 of ObservationsItem from metoceanBuoy to shoreControlRoom { doc /* @S317 */ }
        flow f43 of ActivePowerTargetsItem from gridDispatcher to controlEngineer { doc /* @S368 */ }
        flow f44 of RampInstructionsItem from gridDispatcher to controlEngineer { doc /* @S368 */ }
        flow f45 of TransformerTapSnapshotItem from offshoreSubstation to shoreControlRoom { doc /* @S374 */ }
        flow f46 of VesselPositionInformationItem from vesselAISReceiver to marineCoordinator { doc /* @S400 */ }
        flow f48 of ChangeInDestinationOrTransferPlanItem from personnel to vesselMaster { doc /* @S402 */ }
        flow f49 of UnexplainedAbsenceItem from fieldSupervisor to marineCoordinator { doc /* @S412 */ }
        flow f50 of OverdueCheckInItem from fieldSupervisor to marineCoordinator { doc /* @S412 */ }
        flow f51 of AlertItem from shoreControlRoom to cybersecurityAnalyst { doc /* @S419 */ }
        flow f52 of UrgentConcernsItem from cybersecurityAnalyst to onDutyOperationsLead { doc /* @S419 */ }
        flow f53 of TurbineStatusItem from sCADAGateway to shoreControlRoom { doc /* @S448 */ }
        flow f54 of BerthSlotConfirmationItem from portAgent to marineCoordinator { doc /* @S473 */ }
        flow f55 of ConditionsItem from weatherAnalyst to responsibleOperationalAuthority { doc /* @S500 */ }
        flow f56 of SiteConditionsItem from outgoingSupervisor to incomingSupervisor { doc /* @S512 */ }
        flow f57 of AccessStatusItem from outgoingSupervisor to incomingSupervisor { doc /* @S512 */ }
        flow f58 of OutstandingHazardsItem from outgoingSupervisor to incomingSupervisor { doc /* @S512 */ }
        flow f59 of PlannedWorkPeriodItem from maintenancePlanningEngine to dutyPlanner { doc /* @S520 */ }
        flow f60 of ForecastConditionsItem from weatherService to weatherAnalyst { doc /* @S521 */ }
        flow f62 of SwitchingInstructionsItem from controlEngineer to substationOperator { doc /* @S530 */ }
        flow f63 of SwitchingWindowAcknowledgmentItem from shoreControlRoom to substationOperator { doc /* @S531 */ }
        flow f64 of StartTestTraceItem from emergencyGenerator to substationOperator { doc /* @S532 */ }
        flow f65 of CompletionItem from switchingOperator to controlEngineer { doc /* @S533 */ }
        flow f66 of CurrentGenerationItem from sCADAGateway to operationsTeam { doc /* @S540 */ }
        flow f67 of ExportItem from sCADAGateway to operationsTeam { doc /* @S540 */ }
        flow f68 of EquipmentStatusItem from sCADAGateway to operationsTeam { doc /* @S540 */ }
        flow f69 of DiscrepancyItem from marineCoordinator to shoreControlRoom { doc /* @S578 */ }
        flow f70 of ImmediateControlActionsItem from marineCoordinator to shoreControlRoom { doc /* @S578 */ }
        flow f71 of DiscrepancyItem from marineCoordinator to dutyPlanner { doc /* @S583 */ }
        flow f72 of OperationalPointOfContactItem from shoreControlRoom to offshoreTeams { doc /* @S613 */ }
        flow f73 of MaterialChangesItem from weatherAnalyst to rescueCoordinator { doc /* @S626 */ }
        flow f74 of AlarmIndicationsItem from fireDetectionPanel to responders { doc /* @S629 */ }
        flow f75 of DirectReportsItem from personnel to responders { doc /* @S629 */ }
        flow f76 of EquipmentStatusItem from sCADAGateway to controlEngineer { doc /* @S630 */ }
        flow f77 of IsolationBoundaryItem from workPermitPortal to workParty { doc /* @S713 */ }
        flow f78 of IsolationBoundaryItem from workPermitPortal to controlTeam { doc /* @S713 */ }
        flow f79 of IsolationBoundaryItem from fieldSupervisor to crew { doc /* @S717 */ }
        flow f80 of AccessRestrictionsItem from fieldSupervisor to crew { doc /* @S717 */ }
        flow f81 of ConditionsItem from fieldSupervisor to crew { doc /* @S717 */ }
        flow f82 of RemainingOperationalLimitationItem from controlEngineer to personnel { doc /* @S734 */ }
        flow f84 of SwitchingWindowAcknowledgmentItem from shoreControlRoom to offshoreSubstation { doc /* @S752 */ }
        flow f85 of TimelyClearAndTraceableInformationItem from operationalCommunications to peopleResponsibleForOffshoreWork { doc /* @S760 */ }
        flow f86 of RelevantMarineAndWeatherInformationItem from marineCoordinator to vesselPersonnel { doc /* @S764 */ }
        flow f87 of RelevantMarineAndWeatherInformationItem from marineCoordinator to dutyPlanner { doc /* @S764 */ }
        flow f88 of OperationalDataItem from sCADAGateway to shoreControlRoom { doc /* @S767 */ }
        flow f89 of ExternalOperatingRequirementsItem from gridDispatcher to gridInterfaceRelay { doc /* @S769 */ }
        flow f90 of ExternalOperatingRequirementsItem from gridDispatcher to responsibleControlPersonnel { doc /* @S769 */ }
        flow f91 of EquipmentStatusItem from sCADAGateway to turbineSensorBus { doc /* @S788 */ }
        flow f92 of EquipmentStatusItem from turbineSensorBus to protectiveFunctions { doc /* @S788 */ }
        flow f93 of EquipmentStatusItem from turbineSensorBus to operationalMonitoring { doc /* @S788 */ }
        flow f94 of AlarmsItem from fireDetectionPanel to shoreControlRoom { doc /* @S798 */ }
        flow f95 of UnresolvedPersonnelOrAccessConcernsItem from fieldSupervisor to shoreControlRoom { doc /* @S809 */ }
        flow f96 of CredentialItem from entrant to scanner { doc /* @S839 */ }
        flow f97 of ActiveFaultIndicationItem from liftSupply to electricalTechnician { doc /* @S867 */ }
        flow f98 of ActiveFaultIndicationItem from protectiveDevices to electricalTechnician { doc /* @S867 */ }
        flow f99 of InspectionResultItem from fieldSupervisor to maintenanceSystem { doc /* @S869 */ }
        flow f100 of DefectsItem from fieldSupervisor to maintenanceSystem { doc /* @S869 */ }
        flow f101 of ReleaseStatusItem from fieldSupervisor to workParty { doc /* @S881 */ }
        flow f102 of AlarmItem from systemPart to occupants { doc /* @S902 */ }
        flow f104 of OperationalRestrictionsItem from fleetDispatchConsole to dutyPlanner { doc /* @S947 */ }
        flow f105 of ThePitchDeviationNoticeItem from turbineController to sCADAGateway { doc /* joined @S061,S159 */ }
        flow f106 of APositionQualityFlagItem from vesselAISReceiver to fleetDispatchConsole { doc /* joined @S105,S225 */ }
        flow f107 of ABackorderExceptionSlipItem from warehouseSystem to storekeeper { doc /* joined @S163,S262 */ }
        flow f108 of TheTransferManifestAddendumItem from dutyPlanner to vesselMaster { doc /* joined @S126,S278 */ }
        flow f109 of TheHarnessAuditCardItem from hSEOfficer to crewTransferVessel { doc /* joined @S237,S312 */ }
        flow f110 of TheWaveBurstRecordItem from metoceanBuoy to weatherAnalyst { doc /* joined @S194,S323 */ }
        flow f111 of TheSessionRevocationReceiptItem from sCADAGateway to cybersecurityGateway { doc /* joined @S212,S357 */ }
        flow f112 of TheDeferredTaskRationaleItem from maintenancePlanningEngine to fieldSupervisor { doc /* joined @S285,S430 */ }
        flow f113 of TheLeadingEdgeTileImageItem from bladeInspectionDrone to bladeSpecialist { doc /* joined @S313,S445 */ }
        flow f114 of AnExportLimitAdvisoryItem from gridInterfaceRelay to gridDispatcher { doc /* joined @S372,S541 */ }
        flow f115 of TheCrewCountCorrectionItem from vesselMaster to personnelTrackingConsole { doc /* joined @S390,S573 */ }
        flow f116 of TheFirmwareHashAttestationItem from cybersecurityAnalyst to sCADAEngineer { doc /* joined @S428,S593 */ }
        flow f117 of TheRecoveryBasketLoadSheetItem from serviceOperationsVessel to rescueCoordinator { doc /* joined @S461,S646 */ }
        flow f118 of TheVisibilityConfidenceNoteItem from weatherAnalyst to dutyPlanner { doc /* joined @S472,S669 */ }
        flow f119 of TheIsolationBoundarySketchItem from workPermitPortal to electricalTechnician { doc /* joined @S492,S716 */ }
    }
    requirement def R0 { doc /* Safety objectives require work to be authorized, hazards to be controlled, and personnel and vessels to be accounted for throughout each operation. @S011 */ subject s : Work; }
    requirement def R1 { doc /* Safety objectives require work to be authorized, hazards to be controlled, and personnel and vessels to be accounted for throughout each operation. @S011 */ subject s : Hazards; }
    requirement def R2 { doc /* Safety objectives require work to be authorized, hazards to be controlled, and personnel and vessels to be accounted for throughout each operation. @S011 */ subject s : Personnel; }
    requirement def R3 { doc /* Safety objectives require work to be authorized, hazards to be controlled, and personnel and vessels to be accounted for throughout each operation. @S011 */ subject s : Vessels; }
    requirement def R4 { doc /* Administrative access requires authenticated individual accounts and role-based authorization. @S115 */ subject s : AdministrativeAccess; }
    requirement def R5 { doc /* Any material change to scope, conditions, or timing requires reassessment and may suspend the current authorization. @S168 */ subject s : Authorization; }
    requirement def R6 { doc /* Juniper Vale shall provide current operational status to permit reviewers when requested as part of the authorization check. @S171 */ subject s : SCADAGateway; }
    requirement def R7 { doc /* a turbine response is required @S305 */ subject s : TurbineResponse; }
    requirement def R8 { doc /* Larkspur shall repeat a close-range pass when image coverage is insufficient to assess the suspected surface condition. @S314 */ subject s : BladeInspectionDrone; }
    requirement def R9 { doc /* Redoubt shall block permit release until required risk reviews and isolation references are complete. @S321 */ subject s : WorkPermitPortal; }
    requirement def R10 { doc /* A change in equipment condition, task scope, or operating constraint requires the Field Supervisor to pause work and reassess the authorization. @S333 */ subject s : FieldSupervisor; }
    requirement def R11 { doc /* Remote sessions require approved connection paths, strong authentication, and active supervision when they can affect live operations. @S427 */ subject s : RemoteSessions; }
    requirement def R12 { doc /* a cybersecurity-related work item must be postponed @S430 */ subject s : CybersecurityRelatedWorkItem; }
    requirement def R13 { doc /* equipment that must be inspected, secured, or transferred before sailing @S477 */ subject s : Equipment; }
    requirement def R14 { doc /* Any change to the work scope requires a renewed safety review before affected work resumes. @S510 */ subject s : ChangeToTheWorkScope; }
    requirement def R15 { doc /* A Grid Constraint requires the Duty Planner to reassess the sequence and obtain revised authorization before work proceeds. @S519 */ subject s : DutyPlanner; }
    requirement def R16 { doc /* Electrical recovery work requires qualified personnel, verified isolation, and a safe means of access before hands-on activity begins. @S631 */ subject s : ElectricalRecoveryWork; }
    requirement def R17 { doc /* A Daughter Craft operation requires particular caution where reduced visibility could compromise separation from other vessels or structures. @S679 */ subject s : DaughterCraftOperation; }
    requirement def R18 { doc /* Substitutions require engineering acceptance and confirmation that the alternative meets the required interface and operating limits. @S704 */ subject s : Substitutions; }
    requirement def R19 { doc /* Urgent purchases require documented authorization and retain the same traceability and inspection controls as routine receipts. @S707 */ subject s : UrgentPurchases; }
    requirement def R20 { doc /* equipment and energy sources that must be made safe before field work begins @S711 */ subject s : Equipment; }
    requirement def R21 { doc /* equipment and energy sources that must be made safe before field work begins @S711 */ subject s : EnergySources; }
    requirement def R22 { doc /* adjacent equipment that must remain energized or available for service @S715 */ subject s : AdjacentEquipment; }
    requirement def R23 { doc /* conditions that require work to stop @S717 */ subject s : Work; }
    requirement def R24 { doc /* Where local indication is required, a qualified technician checks the device at the point of isolation. @S719 */ subject s : LocalIndication; }
    requirement def R25 { doc /* Changes to the task, equipment state, or work location require a review of the boundary before work continues. @S727 */ subject s : ChangesToTheTaskEquipmentStateOrWorkLocation; }
    requirement def R26 { doc /* The contingency process requires a named approver and a recorded reason for any temporary access decision. @S829 */ subject s : ContingencyProcess; }
    requirement def R27 { doc /* Personnel must not hold the barrier open for another entrant. @S847 */ subject s : Personnel; }
    requirement def R28 { doc /* Lighting inside the car and at each landing must be adequate for safe movement and inspection. @S891 */ subject s : Lighting; }
    requirement def R29 { doc /* Door interlocks and other protective devices must be functional before the lift is placed in service. @S893 */ subject s : DoorInterlocks; }
    requirement def R30 { doc /* Door interlocks and other protective devices must be functional before the lift is placed in service. @S893 */ subject s : ProtectiveDevices; }
    requirement def R31 { doc /* Protective devices must not be bypassed to maintain access or avoid delay. @S894 */ subject s : ProtectiveDevices; }
    requirement def R32 { doc /* Any unexpected movement or control response requires the operator to stop the lift at the nearest safe landing when practicable. @S901 */ subject s : Operator; }
    requirement def R33 { doc /* Personnel do not attempt to open doors or climb out of a stopped car without direction from the response team. @S903 */ subject s : Personnel; }
}
