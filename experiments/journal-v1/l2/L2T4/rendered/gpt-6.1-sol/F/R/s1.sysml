package L2Model {
    item def AlarmAcknowledgementSlipItem { doc /* @S152 */ }
    item def ArchivedEventSequencesItem { doc /* @S107 */ }
    item def AvailableStationAndBayIndicationsItem { doc /* @S027 */ }
    item def BatteryLoadTestRecordItem { doc /* @S207 */ }
    item def BayControlStatusItem { doc /* @S135 */ }
    item def BayLevelOutputsItem { doc /* @S176 */ }
    item def BayLevelStatusIndicationsItem { doc /* @S155 */ }
    item def BayStatusDigestItem { doc /* @S139 */ }
    item def BreakerInspectionTagItem { doc /* @S089,S179 */ }
    item def BreakerOperationsItem { doc /* @S012 */ }
    item def ClearanceHandoffMemoItem { doc /* @S235 */ }
    item def ClockDriftSnapshotItem { doc /* @S140 */ }
    item def ControlIndicationsAndCommandResultsItem { doc /* @S226 */ }
    item def ControlPowerItem { doc /* @S021 */ }
    item def CurrentOperatingIndicationsItem { doc /* @S106 */ }
    item def EquipmentIndicationsItem { doc /* @S090 */ }
    item def IndicationsFromTheNorthProtectionPanelItem { doc /* @S159 */ }
    item def IsolationBoundaryCardItem { doc /* @S233 */ }
    item def LocalIndicationOfTransformerProtectionOperationItem { doc /* @S161 */ }
    item def OperatingConditionsAndCommunicationQualityItem { doc /* @S028 */ }
    item def OperatingPowerItem { doc /* @S046 */ }
    item def OutputCommandsItem { doc /* @S177 */ }
    item def PositionAndCircuitHealthIndicationsItem { doc /* @S177 */ }
    item def ProtocolRetrySummaryItem { doc /* @S208 */ }
    item def RelayDiagnosticNoteItem { doc /* @S109 */ }
    item def RelayIndicationsItem { doc /* @S108 */ }
    item def ReportedFieldConditionsItem { doc /* @S093 */ }
    item def ReturnedIndicationsItem { doc /* @S178 */ }
    item def SettingsReviewReceiptItem { doc /* @S206 */ }
    item def StateChangingRequestsItem { doc /* @S175 */ }
    item def StationTimeReferenceItem { doc /* @S017,S039,S040,S144,S183 */ }
    item def StationTrafficItem { doc /* @S172 */ }
    item def SupervisoryCommunicationsItem { doc /* @S029 */ }
    item def SupervisoryDisplaysItem { doc /* @S032 */ }
    item def SwitchingRequestsItem { doc /* @S125 */ }
    item def TimeOrderedEvidenceItem { doc /* @S157 */ }
    item def UpdatedIndicationsItem { doc /* @S180 */ }
    part def AffectedPoints { doc /* @S184 */ }
    part def AlarmResponse { doc /* @S167 */ }
    part def Alarms { doc /* @S149 */ }
    part def AlderCreekElectricalDistributionSubstation { doc /* @S001,S017,S090,S119,S144,S183,S193 */ }
    part def ApprovedSwitchingSequences { doc /* @S128 */ }
    part def ArchiveReceiptTime { doc /* @S101 */ }
    part def AutomationAndProtectionEquipment { doc /* @S021 */ }
    part def BayAutomationController { doc /* @S005,S006,S012,S089,S091,S121,S135,S139,S155,S175,S176,S177,S178,S179,S184,S207,S223 */ }
    part def BayBoundary { doc /* @S133 */ }
    part def BayLevelStatusIndications { doc /* @S155 */ }
    part def BayNetworks { doc /* @S172 */ }
    part def BreakerControlUnit { doc /* @S011,S012,S136,S176,S177,S178,S232 */ }
    part def BreakerStatusDiscrepancy { doc /* @S163 */ }
    part def ControlRoom { doc /* @S080 */ }
    part def ControlRoomNetworks { doc /* @S172 */ }
    part def ControlRoomOperator { doc /* @S022,S027,S028,S032,S077,S083,S090,S093,S106,S107,S125,S148,S149,S150,S151,S152,S153,S155,S157,S159,S161,S162,S168,S170,S175,S199,S215,S222,S226,S235,S238 */ }
    part def CoordinationChecks { doc /* @S062 */ }
    part def Discrepancy { doc /* @S072,S087 */ }
    part def DistributionCircuits { doc /* @S001 */ }
    part def EngineeringWorkstation { doc /* @S019,S056,S057,S064,S110,S191,S206,S228 */ }
    part def EquipmentIndications { doc /* @S083 */ }
    part def EquipmentStatus { doc /* @S214 */ }
    part def EventRecords { doc /* @S101,S221 */ }
    part def EventTime { doc /* @S101 */ }
    part def ExportedEvidence { doc /* @S112 */ }
    part def FeederProtectionRelay { doc /* @S008,S009,S052,S053,S108,S109,S186,S224 */ }
    part def FieldPersonnel { doc /* @S085 */ }
    part def LocalInterlocks { doc /* @S130 */ }
    part def MaintenanceRemoteTerminal { doc /* @S020,S206,S240 */ }
    part def MaintenanceSession { doc /* @S240 */ }
    part def NorthBay { doc /* @S130 */ }
    part def NorthBayController { doc /* @S007,S129,S130,S132,S189,S241 */ }
    part def NorthProtectionPanel { doc /* @S137,S158,S159,S187,S243 */ }
    part def PeriodicOperationalReviews { doc /* @S245 */ }
    part def Permissives { doc /* @S214 */ }
    part def Personnel { doc /* @S080,S202 */ }
    part def ProposedChange { doc /* @S058 */ }
    part def ProtectionEquipment { doc /* @S158 */ }
    part def ProtectionFunctions { doc /* @S212 */ }
    part def ProtectionRelayEngineer { doc /* @S023,S054,S055,S059,S066,S108,S109,S143,S165,S194,S203,S225,S239 */ }
    part def QualityIndications { doc /* @S101 */ }
    part def RecoveryTesting { doc /* @S118 */ }
    part def RemoteCommands { doc /* @S214 */ }
    part def RemoteIndications { doc /* @S215 */ }
    part def RemoteOperationsInterfaces { doc /* @S029 */ }
    part def ResponsibleAuthority { doc /* @S116 */ }
    part def ReviewQueries { doc /* @S111 */ }
    part def SatelliteTimeReceiver { doc /* @S017,S038,S039,S040,S044,S103,S140,S144,S183,S229 */ }
    part def SecondQualifiedReviewer { doc /* @S060 */ }
    part def SequenceEventArchive { doc /* @S018,S100,S102,S105,S106,S107,S115,S140,S157,S182,S210,S227 */ }
    part def SourceIdentity { doc /* @S101 */ }
    part def SouthBayController { doc /* @S007,S131,S132,S190,S242 */ }
    part def StateChangeEvidence { doc /* @S146 */ }
    part def StationAutomationEquipment { doc /* @S046 */ }
    part def StationCommunicationsDesign { doc /* @S171 */ }
    part def StationDCSystem { doc /* @S021,S046,S120,S193,S207,S231 */ }
    part def StationEquipment { doc /* @S039,S040 */ }
    part def StationGateway { doc /* @S016,S029,S142,S172,S173,S180,S185,S208,S230 */ }
    part def StationLevelFunctions { doc /* @S029 */ }
    part def StationSupervisoryControlSystem { doc /* @S015,S027,S028,S032,S048,S090,S106,S135,S139,S152,S156,S174,S180,S181,S208,S226 */ }
    part def SubstationFieldCrew { doc /* @S024,S069,S075,S079,S084,S088,S089,S093,S095,S145,S166,S179,S196,S201,S209,S216,S233,S234 */ }
    part def SubstationSupervisor { doc /* @S049,S073,S078,S127,S195,S198,S220,S237 */ }
    part def SupervisoryArchitecture { doc /* @S025 */ }
    part def SupervisoryCommunications { doc /* @S215 */ }
    part def SupervisoryLayer { doc /* @S031 */ }
    part def SwitchingDeskCoordinator { doc /* @S082,S097,S122,S124,S125,S126,S141,S146,S169,S200,S233,S235,S236 */ }
    part def TimeQualityConcerns { doc /* @S229 */ }
    part def TimeQualityIndications { doc /* @S045 */ }
    part def TransformerProtectionPanel { doc /* @S138,S161,S188,S244 */ }
    part def WorkArea { doc /* @S096 */ }
    part system {
        part affectedPoints : AffectedPoints {
            exhibit state modes {
                state s0 { doc /* degraded state @S184 */ }
            }
        }
        part alarmResponse : AlarmResponse {
            perform action a0 { doc /* requires escalation beyond routine operator actions @S167 */ }
        }
        part alarms : Alarms {
            exhibit state modes {
                state s0 { doc /* new alarm @S149 */ }
            }
        }
        part alderCreekElectricalDistributionSubstation : AlderCreekElectricalDistributionSubstation {
            perform action a0 { doc /* supplies distribution circuits through transformer and feeder bays @S001 */ }
            perform action a1 { doc /* preserves an additional protected copy of essential event evidence in accordance with approved backup procedures @S119 */ }
            exhibit state modes {
                state s0 { doc /* abnormal station condition @S193 */ }
                state s1 { doc /* normal operation @S090 */ }
            }
        }
        part approvedSwitchingSequences : ApprovedSwitchingSequences {
            perform action a0 { doc /* identify the required order of actions, hold points, and conditions for stopping work @S128 */ }
        }
        part archiveReceiptTime : ArchiveReceiptTime;
        part automationAndProtectionEquipment : AutomationAndProtectionEquipment;
        part bayAutomationController : BayAutomationController {
            perform action a0 { doc /* performs bay-level sequencing, status evaluation, and control permissive checks @S005 */ }
            perform action a1 { doc /* produces a Bay Status Digest for operational awareness @S006 */ }
            perform action a2 { doc /* requests breaker operations only when the applicable operating mode and permissives allow them @S012 */ }
            perform action a3 { doc /* applies configured permissives and interlocks to supported automated operations @S091 */ }
            perform action a4 { doc /* timestamps locally generated state changes for later correlation @S121 */ }
            perform action a5 { doc /* presents bay control status @S135 */ }
            perform action a6 { doc /* preserving the separate operating scopes of the two controllers @S135 */ }
            perform action a7 { doc /* provides bay-level status indications that support the operator’s assessment of the alarm @S155 */ }
            perform action a8 { doc /* validates each received request against local mode, interlocks, command authority, and equipment availability @S176 */ }
            perform action a9 { doc /* issuing bay-level outputs @S176 */ }
            perform action a10 { doc /* compares returned indications with the requested state @S178 */ }
            perform action a11 { doc /* identifies incomplete or contradictory operation @S178 */ }
            perform action a12 { doc /* uses the inspection tag @S179 */ }
            perform action a13 { doc /* associate the applicable equipment context with an authorized record @S179 */ }
            perform action a14 { doc /* monitors communication health @S184 */ }
            perform action a15 { doc /* places affected points in a defined degraded state @S184 */ }
            perform action a16 { doc /* uses the load test record @S207 */ }
            perform action a17 { doc /* support maintenance review @S207 */ }
            perform action a18 { doc /* shall execute only commands permitted by its approved logic and configured interlocks @S223 */ }
            exhibit state modes {
                state s0 { doc /* local mode @S176 */ }
            }
        }
        part bayBoundary : BayBoundary {
            perform action a0 { doc /* defines which controller may operate each device and which indications are used to confirm its state @S133 */ }
        }
        part bayLevelStatusIndications : BayLevelStatusIndications {
            perform action a0 { doc /* support the operator’s assessment of the alarm @S155 */ }
        }
        part bayNetworks : BayNetworks;
        part breakerControlUnit : BreakerControlUnit {
            perform action a0 { doc /* executes authorized breaker operations @S011 */ }
            perform action a1 { doc /* enforces its local electrical and mechanical interlocks @S011 */ }
            perform action a2 { doc /* executes permitted breaker commands only when the applicable control conditions are satisfied @S136 */ }
            perform action a3 { doc /* applies accepted output commands at the breaker interface @S177 */ }
            perform action a4 { doc /* returns the resulting position and circuit-health indications @S177 */ }
            perform action a5 { doc /* shall reject commands that do not satisfy its configured permissive conditions @S232 */ }
        }
        part breakerStatusDiscrepancy : BreakerStatusDiscrepancy {
            exhibit state modes {
                state s0 { doc /* abnormal condition @S163 */ }
            }
        }
        part controlRoom : ControlRoom {
            perform action a0 { doc /* can account for field staff @S080 */ }
        }
        part controlRoomNetworks : ControlRoomNetworks;
        part controlRoomOperator : ControlRoomOperator {
            perform action a0 { doc /* directs routine station operation @S022 */ }
            perform action a1 { doc /* verifies that commanded equipment states are appropriate @S022 */ }
            perform action a2 { doc /* uses the supervisory displays @S032 */ }
            perform action a3 { doc /* assess station conditions @S032 */ }
            perform action a4 { doc /* coordinate operating actions @S032 */ }
            perform action a5 { doc /* coordinates operational access with the Switching Desk Coordinator @S077 */ }
            perform action a6 { doc /* retains authority to suspend work when operating conditions change or indications become uncertain @S083 */ }
            perform action a7 { doc /* suspend work @S083 */ }
            perform action a8 { doc /* evaluates reported field conditions @S093 */ }
            perform action a9 { doc /* authorizing a return to automated operation @S093 */ }
            perform action a10 { doc /* reviews archived event sequences @S107 */ }
            perform action a11 { doc /* establish the order of alarms, status changes, and operator actions @S107 */ }
            perform action a12 { doc /* submits switching requests with the affected equipment, intended state changes, and requested timing @S125 */ }
            perform action a13 { doc /* reviews the alarm priority, source, time, and associated bay indications @S148 */ }
            perform action a14 { doc /* deciding on a response @S148 */ }
            perform action a15 { doc /* distinguishes a new alarm from a standing condition @S149 */ }
            perform action a16 { doc /* checks whether related indications support the same assessment @S149 */ }
            perform action a17 { doc /* treats the condition as requiring prompt investigation @S150 */ }
            perform action a18 { doc /* acknowledges alarms @S151 */ }
            perform action a19 { doc /* reviewing the indication @S151 */ }
            perform action a20 { doc /* retains awareness of any condition that remains unresolved @S151 */ }
            perform action a21 { doc /* uses the acknowledgement slip @S152 */ }
            perform action a22 { doc /* record the alarm response and any outstanding action @S152 */ }
            perform action a23 { doc /* checks available device status and sequence information @S153 */ }
            perform action a24 { doc /* treating a cleared indication as proof that the underlying cause has been corrected @S153 */ }
            perform action a25 { doc /* uses indications from the North Protection Panel @S159 */ }
            perform action a26 { doc /* assess feeder protection operations and related alarms @S159 */ }
            perform action a27 { doc /* considers the condition of the Station DC System @S162 */ }
            perform action a28 { doc /* produces the Clearance Handoff Memo @S168 */ }
            perform action a29 { doc /* verifies that alarm status, equipment status, and recorded evidence are consistent @S170 */ }
            perform action a30 { doc /* closing the response @S170 */ }
            perform action a31 { doc /* issues state-changing requests only through approved operating procedures and the configured supervisory interface @S175 */ }
            perform action a32 { doc /* reviews the equipment affected by each work package @S199 */ }
            perform action a33 { doc /* identifies any required operating restrictions @S199 */ }
            perform action a34 { doc /* treats remote indications as unavailable @S215 */ }
            perform action a35 { doc /* deciding whether an automation request is appropriate for current operating conditions @S222 */ }
            perform action a36 { doc /* confirms indications locally @S238 */ }
        }
        part coordinationChecks : CoordinationChecks {
            perform action a0 { doc /* consider upstream and downstream protection behavior across the expected operating range @S062 */ }
        }
        part discrepancy : Discrepancy {
            perform action a0 { doc /* stops release of the configuration @S072 */ }
            exhibit state modes {
                state s0 { doc /* unsafe condition @S087 */ }
            }
        }
        part distributionCircuits : DistributionCircuits;
        part engineeringWorkstation : EngineeringWorkstation {
            perform action a0 { doc /* supports authorized configuration and maintenance activities under controlled access @S019 */ }
            perform action a1 { doc /* maintains the working configuration under revision control @S056 */ }
            perform action a2 { doc /* produces the Settings Review Receipt @S057 */ }
            perform action a3 { doc /* retains the approved configuration and its revision history for controlled access @S064 */ }
            perform action a4 { doc /* provides approved tools for searching, filtering, and exporting event records @S110 */ }
            perform action a5 { doc /* supports approved configuration review @S191 */ }
            perform action a6 { doc /* does not serve as a routine source of operating commands @S191 */ }
        }
        part equipmentIndications : EquipmentIndications {
            exhibit state modes {
                state s0 { doc /* uncertain @S083 */ }
            }
        }
        part equipmentStatus : EquipmentStatus {
            exhibit state modes {
                state s0 { doc /* uncertain @S214 */ }
            }
        }
        part eventRecords : EventRecords {
            perform action a0 { doc /* support later review @S221 */ }
        }
        part eventTime : EventTime;
        part exportedEvidence : ExportedEvidence {
            perform action a0 { doc /* retains original timestamps and quality flags @S112 */ }
        }
        part feederProtectionRelay : FeederProtectionRelay {
            perform action a0 { doc /* detects feeder faults @S008 */ }
            perform action a1 { doc /* initiates protection actions within its configured protection zone @S008 */ }
            perform action a2 { doc /* produces a Relay Diagnostic Note @S009 */ }
            perform action a3 { doc /* identifies a condition requiring engineering attention @S009 */ }
            perform action a4 { doc /* provides local protection for its assigned feeder @S052 */ }
            perform action a5 { doc /* operates independently of supervisory control availability @S052 */ }
            perform action a6 { doc /* defines the pickup levels, time delays, and logic required for the feeder protection scheme @S053 */ }
            perform action a7 { doc /* evaluates electrical quantities against approved settings @S186 */ }
            perform action a8 { doc /* issues protective trip outputs @S186 */ }
            perform action a9 { doc /* relying on supervisory communications @S186 */ }
            perform action a10 { doc /* shall retain its protective function independently of supervisory communications @S224 */ }
        }
        part fieldPersonnel : FieldPersonnel {
            perform action a0 { doc /* do not rely on screen indications alone @S085 */ }
            perform action a1 { doc /* establish that equipment is safe to approach or handle @S085 */ }
            perform action a2 { doc /* approach or handle @S085 */ }
        }
        part localInterlocks : LocalInterlocks {
            perform action a0 { doc /* indicate that the bay is not ready @S130 */ }
        }
        part maintenanceRemoteTerminal : MaintenanceRemoteTerminal {
            perform action a0 { doc /* does not replace local operating authority @S020 */ }
            perform action a1 { doc /* uses the review receipt @S206 */ }
            perform action a2 { doc /* support controlled maintenance review @S206 */ }
            perform action a3 { doc /* shall use controlled access @S240 */ }
        }
        part maintenanceSession : MaintenanceSession;
        part northBay : NorthBay {
            exhibit state modes {
                state s0 { doc /* not ready @S130 */ }
            }
        }
        part northBayController : NorthBayController {
            perform action a0 { doc /* provide bay-specific automation for their respective portions of the station @S007 */ }
            perform action a1 { doc /* manages control and interlocking functions assigned to the north bay under the approved sequence @S129 */ }
            perform action a2 { doc /* blocks a close command @S130 */ }
            perform action a3 { doc /* do not substitute for one another when executing a switching sequence @S132 */ }
            perform action a4 { doc /* executing a switching sequence @S132 */ }
            perform action a5 { doc /* maintains local bay control within the approved operating mode @S189 */ }
        }
        part northProtectionPanel : NorthProtectionPanel {
            perform action a0 { doc /* supports protection functions for the north-side equipment within its assigned scope @S137 */ }
            perform action a1 { doc /* applies its assigned zone logic @S187 */ }
            perform action a2 { doc /* maintains trip paths independently of supervisory network availability @S187 */ }
            exhibit state modes {
                state s0 { doc /* available @S243 */ }
            }
        }
        part periodicOperationalReviews : PeriodicOperationalReviews {
            perform action a0 { doc /* shall examine command outcomes, event records, exceptions, and corrective actions @S245 */ }
        }
        part permissives : Permissives {
            exhibit state modes {
                state s0 { doc /* unavailable @S214 */ }
            }
        }
        part personnel : Personnel {
            perform action a0 { doc /* use the site access process @S080 */ }
            perform action a1 { doc /* record arrival and departure @S080 */ }
            perform action a2 { doc /* approach exposed conductors @S202 */ }
            perform action a3 { doc /* operate equipment under maintenance @S202 */ }
        }
        part proposedChange : ProposedChange {
            perform action a0 { doc /* receives a unique revision identifier @S058 */ }
        }
        part protectionEquipment : ProtectionEquipment;
        part protectionFunctions : ProtectionFunctions {
            exhibit state modes {
                state s0 { doc /* out of service @S212 */ }
            }
        }
        part protectionRelayEngineer : ProtectionRelayEngineer {
            perform action a0 { doc /* maintains protection settings @S023 */ }
            perform action a1 { doc /* evaluates relay performance within the approved change process @S023 */ }
            perform action a2 { doc /* develops setting changes against the approved protection study and the current equipment data @S054 */ }
            perform action a3 { doc /* documents the engineering basis and expected operational effect for each proposed change @S055 */ }
            perform action a4 { doc /* verifies that proposed values agree with the approved coordination objectives @S059 */ }
            perform action a5 { doc /* records the approval status @S066 */ }
            perform action a6 { doc /* compares event times and relay indications during disturbance analysis @S108 */ }
            perform action a7 { doc /* uses the Relay Diagnostic Note during fault analysis @S109 */ }
            perform action a8 { doc /* reviews protection coordination questions that could affect the planned switching sequence @S143 */ }
            perform action a9 { doc /* supports investigation @S165 */ }
            perform action a10 { doc /* reviews protection event records @S194 */ }
            perform action a11 { doc /* verifies that approved settings remain consistent with coordination requirements @S194 */ }
            perform action a12 { doc /* reviews test scope, approved settings, and restoration criteria @S203 */ }
            perform action a13 { doc /* reviews protection behavior after material changes @S225 */ }
            perform action a14 { doc /* records any unresolved concerns for operational follow-up @S225 */ }
            perform action a15 { doc /* assesses unexplained trips and abnormal protection indications @S239 */ }
        }
        part qualityIndications : QualityIndications;
        part recoveryTesting : RecoveryTesting {
            perform action a0 { doc /* verifies that retained records remain readable and that timestamps and quality indications survive restoration @S118 */ }
        }
        part remoteCommands : RemoteCommands {
            exhibit state modes {
                state s0 { doc /* inhibited @S214 */ }
            }
        }
        part remoteIndications : RemoteIndications {
            exhibit state modes {
                state s0 { doc /* unavailable @S215 */ }
            }
        }
        part remoteOperationsInterfaces : RemoteOperationsInterfaces;
        part responsibleAuthority : ResponsibleAuthority {
            perform action a0 { doc /* is released by the responsible authority @S116 */ }
        }
        part reviewQueries : ReviewQueries;
        part satelliteTimeReceiver : SatelliteTimeReceiver {
            perform action a0 { doc /* provides the station with a reference for time synchronization @S017 */ }
            perform action a1 { doc /* acquires a reference from supported satellite timing signals @S038 */ }
            perform action a2 { doc /* distributes time to station equipment over the configured time-distribution network @S039 */ }
            perform action a3 { doc /* produces the Clock Drift Snapshot @S044 */ }
            perform action a4 { doc /* supports station time alignment @S103 */ }
            perform action a5 { doc /* provides the station time reference used to align recorded event times @S144 */ }
            perform action a6 { doc /* supplies the station time reference used to align event timestamps, subject to configured quality checks @S183 */ }
            perform action a7 { doc /* supports consistent event timing @S229 */ }
        }
        part secondQualifiedReviewer : SecondQualifiedReviewer {
            perform action a0 { doc /* independently checks calculations, logic changes, and device applicability @S060 */ }
        }
        part sequenceEventArchive : SequenceEventArchive {
            perform action a0 { doc /* retains operational event information for later review @S018 */ }
            perform action a1 { doc /* preserves event records in their received form @S100 */ }
            perform action a2 { doc /* preserves original event ordering @S102 */ }
            perform action a3 { doc /* marks records whose time quality or sequence continuity is uncertain @S102 */ }
            perform action a4 { doc /* retains configuration and access history associated with archive administration @S105 */ }
            perform action a5 { doc /* held by the archive @S106 */ }
            perform action a6 { doc /* retains records under the station records schedule and applicable utility retention requirements @S115 */ }
            perform action a7 { doc /* receives the Clock Drift Snapshot for event-time correlation @S140 */ }
            perform action a8 { doc /* provides time-ordered evidence for later operational review @S157 */ }
            perform action a9 { doc /* retains time-tagged changes and control outcomes for event reconstruction and operational review @S182 */ }
            perform action a10 { doc /* retains event information needed to review testing and restoration activity @S210 */ }
            perform action a11 { doc /* retains time-ordered records needed to reconstruct significant control and protection events @S227 */ }
        }
        part sourceIdentity : SourceIdentity;
        part southBayController : SouthBayController {
            perform action a0 { doc /* provide bay-specific automation for their respective portions of the station @S007 */ }
            perform action a1 { doc /* manages the corresponding control and interlocking functions assigned to the south bay @S131 */ }
            perform action a2 { doc /* do not substitute for one another when executing a switching sequence @S132 */ }
            perform action a3 { doc /* executing a switching sequence @S132 */ }
            perform action a4 { doc /* reports local mode and control availability through its configured bay interface @S190 */ }
            exhibit state modes {
                state s0 { doc /* local mode @S190 */ }
            }
        }
        part stateChangeEvidence : StateChangeEvidence {
            exhibit state modes {
                state s0 { doc /* available for authorized engineering review @S146 */ }
            }
        }
        part stationAutomationEquipment : StationAutomationEquipment;
        part stationCommunicationsDesign : StationCommunicationsDesign {
            perform action a0 { doc /* separates supervisory requests, bay-level execution, and protection action @S171 */ }
        }
        part stationDCSystem : StationDCSystem {
            perform action a0 { doc /* supplies control power to automation and protection equipment within its design capacity @S021 */ }
            perform action a1 { doc /* supplies operating power to station automation equipment within its designed capacity @S046 */ }
            perform action a2 { doc /* produces a Battery Load Test Record for retention with station engineering records @S120 */ }
            perform action a3 { doc /* supports control and protection functions through monitored station supply circuits @S193 */ }
            exhibit state modes {
                state s0 { doc /* available @S231 */ }
            }
        }
        part stationEquipment : StationEquipment {
            perform action a0 { doc /* receives and applies the reference @S040 */ }
        }
        part stationGateway : StationGateway {
            perform action a0 { doc /* defines the communications boundary for authorized connections beyond the station automation network @S016 */ }
            perform action a1 { doc /* carries supervisory communications between station-level functions and remote operations interfaces @S029 */ }
            perform action a2 { doc /* produces the Protocol Retry Summary for communication review @S142 */ }
            perform action a3 { doc /* brokers authorized station traffic across control-room and bay networks @S172 */ }
            perform action a4 { doc /* applying configured protocol mappings, addressing, and access controls @S172 */ }
            perform action a5 { doc /* rejects malformed, stale, or unauthorized requests @S173 */ }
            perform action a6 { doc /* records each rejection with enough context for operations review @S173 */ }
            perform action a7 { doc /* carries updated indications through the station interface using configured quality and timestamp attributes @S180 */ }
            perform action a8 { doc /* using configured quality and timestamp attributes @S180 */ }
            perform action a9 { doc /* reports link condition and protocol errors @S185 */ }
            perform action a10 { doc /* converting a communication failure into an equipment-state change @S185 */ }
            perform action a11 { doc /* shall maintain the defined boundary between station automation and external communications @S230 */ }
        }
        part stationLevelFunctions : StationLevelFunctions;
        part stationSupervisoryControlSystem : StationSupervisoryControlSystem {
            perform action a0 { doc /* provides the station-level operating interface and supervisory coordination @S015 */ }
            perform action a1 { doc /* presents available station and bay indications through a consolidated operator interface @S027 */ }
            perform action a2 { doc /* show operating conditions and communication quality @S028 */ }
            perform action a3 { doc /* replacing local equipment indications @S028 */ }
            perform action a4 { doc /* produces the Alarm Acknowledgement Slip for supervisory recordkeeping @S048 */ }
            perform action a5 { doc /* presents available equipment indications for operator review during normal operation @S090 */ }
            perform action a6 { doc /* presents current operating indications separately from the long-term evidence held by the archive @S106 */ }
            perform action a7 { doc /* uses the status digest @S139 */ }
            perform action a8 { doc /* review current station operating conditions @S139 */ }
            perform action a9 { doc /* shall retain alarm state and event information for operator review @S156 */ }
            perform action a10 { doc /* presents available controls and indications to authorized operating personnel @S174 */ }
            perform action a11 { doc /* displays indication quality and stale-data status @S181 */ }
            perform action a12 { doc /* receives the Protocol Retry Summary for operational review @S208 */ }
            perform action a13 { doc /* presents control indications and command results for operator assessment @S226 */ }
        }
        part substationFieldCrew : SubstationFieldCrew {
            perform action a0 { doc /* performs field checks and equipment work under the applicable switching instructions and clearances @S024 */ }
            perform action a1 { doc /* follows the authorized work instructions during device access and setting transfer @S069 */ }
            perform action a2 { doc /* performs inspections, maintenance, and switching support within the boundaries of approved work @S075 */ }
            perform action a3 { doc /* reviews the work scope, access route, known hazards, and communication arrangements @S079 */ }
            perform action a4 { doc /* entering the yard @S079 */ }
            perform action a5 { doc /* verifies equipment identity at the point of work against the approved work documentation @S084 */ }
            perform action a6 { doc /* promptly reports uncertain equipment conditions through the designated operational communication channel @S088 */ }
            perform action a7 { doc /* completes and sends the Breaker Inspection Tag @S089 */ }
            perform action a8 { doc /* recording the observed breaker condition and inspection time @S089 */ }
            perform action a9 { doc /* stops affected work @S095 */ }
            perform action a10 { doc /* follows the approved hold and escalation procedure @S095 */ }
            perform action a11 { doc /* confirms device identity and local conditions @S145 */ }
            perform action a12 { doc /* carrying out an authorized operation @S145 */ }
            perform action a13 { doc /* confirms device identity and local conditions @S166 */ }
            perform action a14 { doc /* carrying out an authorized operation @S166 */ }
            perform action a15 { doc /* verifies equipment indications locally @S196 */ }
            perform action a16 { doc /* reports discrepancies through established operating channels @S196 */ }
            perform action a17 { doc /* performs work @S201 */ }
            perform action a18 { doc /* verifies that field work remains within the approved work boundary @S209 */ }
            perform action a19 { doc /* reports any unsafe condition through established channels @S209 */ }
            perform action a20 { doc /* verifies equipment indications locally @S216 */ }
            perform action a21 { doc /* reports discrepancies through established operating channels @S216 */ }
            perform action a22 { doc /* uses the Isolation Boundary Card @S233 */ }
            perform action a23 { doc /* verify the approved work boundary @S233 */ }
            perform action a24 { doc /* entering the controlled area @S233 */ }
            perform action a25 { doc /* reports unexpected equipment conditions promptly @S234 */ }
            perform action a26 { doc /* pauses work @S234 */ }
        }
        part substationSupervisor : SubstationSupervisor {
            perform action a0 { doc /* oversees operational use of the supervisory system and escalation of unresolved availability concerns @S049 */ }
            perform action a1 { doc /* ensures that engineering changes follow the established authorization and operational control process @S073 */ }
            perform action a2 { doc /* confirms that the requested work is consistent with current operating conditions and approved procedures @S078 */ }
            perform action a3 { doc /* resolves priority conflicts @S127 */ }
            perform action a4 { doc /* confirms the operational authority for exceptional switching conditions @S127 */ }
            perform action a5 { doc /* ensures communication changes, point mapping changes, and control logic changes are managed through station change control @S195 */ }
            perform action a6 { doc /* coordinates work timing with the Switching Desk Coordinator @S198 */ }
            perform action a7 { doc /* confirms that operating responsibilities are understood @S198 */ }
            perform action a8 { doc /* confirms that required records are complete and that operating restrictions are formally cleared @S220 */ }
            perform action a9 { doc /* returning equipment to normal service @S220 */ }
            perform action a10 { doc /* verifies that unresolved risks have an assigned owner and an agreed disposition @S237 */ }
        }
        part supervisoryArchitecture : SupervisoryArchitecture {
            perform action a0 { doc /* separates station-wide observation from local bay and protection functions @S025 */ }
        }
        part supervisoryCommunications : SupervisoryCommunications {
            exhibit state modes {
                state s0 { doc /* degraded @S215 */ }
            }
        }
        part supervisoryLayer : SupervisoryLayer {
            perform action a0 { doc /* does not perform the protective functions assigned to dedicated protection equipment @S031 */ }
        }
        part switchingDeskCoordinator : SwitchingDeskCoordinator {
            perform action a0 { doc /* confirms the applicable switching and clearance arrangements @S082 */ }
            perform action a1 { doc /* confirms the operational handback arrangements @S097 */ }
            perform action a2 { doc /* confirms operational handback @S122 */ }
            perform action a3 { doc /* maintains the station-wide switching plan @S124 */ }
            perform action a4 { doc /* coordinates work across the two bay boundaries @S124 */ }
            perform action a5 { doc /* checks each request for conflicts with active clearances and other approved work @S126 */ }
            perform action a6 { doc /* produces the Isolation Boundary Card for the planned work @S141 */ }
            perform action a7 { doc /* confirms operational handback @S146 */ }
            perform action a8 { doc /* confirms operational handback @S169 */ }
            perform action a9 { doc /* confirms switching prerequisites @S200 */ }
            perform action a10 { doc /* keeps the approved switching sequence current @S200 */ }
            perform action a11 { doc /* receives the Clearance Handoff Memo @S235 */ }
            perform action a12 { doc /* confirms that its clearance status agrees with the active switching record @S235 */ }
            perform action a13 { doc /* shall confirm that switching authority, equipment state, and communication limits are understood @S236 */ }
            perform action a14 { doc /* coordinating any automation-enabled action @S236 */ }
        }
        part timeQualityConcerns : TimeQualityConcerns;
        part timeQualityIndications : TimeQualityIndications {
            perform action a0 { doc /* allow operators to distinguish synchronized operation from degraded or unavailable timing @S045 */ }
        }
        part transformerProtectionPanel : TransformerProtectionPanel {
            perform action a0 { doc /* retains its protection authority independently of the bay switching sequence @S138 */ }
            perform action a1 { doc /* provides local indication of transformer protection operation for assessment during an alarm response @S161 */ }
            perform action a2 { doc /* applies its assigned protective logic @S188 */ }
            perform action a3 { doc /* reports abnormal protection conditions through its configured interface @S188 */ }
        }
        part workArea : WorkArea {
            exhibit state modes {
                state s0 { doc /* safe state @S096 */ }
            }
        }
        flow f0 of BreakerOperationsItem from bayAutomationController to breakerControlUnit { doc /* @S012 */ }
        flow f1 of StationTimeReferenceItem from satelliteTimeReceiver to alderCreekElectricalDistributionSubstation { doc /* @S017 */ }
        flow f2 of ControlPowerItem from stationDCSystem to automationAndProtectionEquipment { doc /* @S021 */ }
        flow f3 of AvailableStationAndBayIndicationsItem from stationSupervisoryControlSystem to controlRoomOperator { doc /* @S027 */ }
        flow f4 of OperatingConditionsAndCommunicationQualityItem from stationSupervisoryControlSystem to controlRoomOperator { doc /* @S028 */ }
        flow f5 of SupervisoryCommunicationsItem from stationLevelFunctions to stationGateway { doc /* @S029 */ }
        flow f6 of SupervisoryCommunicationsItem from stationGateway to remoteOperationsInterfaces { doc /* @S029 */ }
        flow f7 of SupervisoryDisplaysItem from stationSupervisoryControlSystem to controlRoomOperator { doc /* @S032 */ }
        flow f8 of StationTimeReferenceItem from satelliteTimeReceiver to stationEquipment { doc /* @S039 */ }
        flow f10 of OperatingPowerItem from stationDCSystem to stationAutomationEquipment { doc /* @S046 */ }
        flow f11 of BreakerInspectionTagItem from substationFieldCrew to bayAutomationController { doc /* @S089 */ }
        flow f12 of EquipmentIndicationsItem from stationSupervisoryControlSystem to controlRoomOperator { doc /* @S090 */ }
        flow f13 of ReportedFieldConditionsItem from substationFieldCrew to controlRoomOperator { doc /* @S093 */ }
        flow f14 of CurrentOperatingIndicationsItem from stationSupervisoryControlSystem to controlRoomOperator { doc /* @S106 */ }
        flow f15 of ArchivedEventSequencesItem from sequenceEventArchive to controlRoomOperator { doc /* @S107 */ }
        flow f16 of RelayIndicationsItem from feederProtectionRelay to protectionRelayEngineer { doc /* @S108 */ }
        flow f17 of RelayDiagnosticNoteItem from feederProtectionRelay to protectionRelayEngineer { doc /* @S109 */ }
        flow f18 of SwitchingRequestsItem from controlRoomOperator to switchingDeskCoordinator { doc /* @S125 */ }
        flow f19 of BayControlStatusItem from bayAutomationController to stationSupervisoryControlSystem { doc /* @S135 */ }
        flow f20 of BayStatusDigestItem from bayAutomationController to stationSupervisoryControlSystem { doc /* @S139 */ }
        flow f21 of ClockDriftSnapshotItem from satelliteTimeReceiver to sequenceEventArchive { doc /* @S140 */ }
        flow f23 of AlarmAcknowledgementSlipItem from stationSupervisoryControlSystem to controlRoomOperator { doc /* @S152 */ }
        flow f24 of BayLevelStatusIndicationsItem from bayAutomationController to controlRoomOperator { doc /* @S155 */ }
        flow f25 of TimeOrderedEvidenceItem from sequenceEventArchive to controlRoomOperator { doc /* @S157 */ }
        flow f26 of IndicationsFromTheNorthProtectionPanelItem from northProtectionPanel to controlRoomOperator { doc /* @S159 */ }
        flow f27 of LocalIndicationOfTransformerProtectionOperationItem from transformerProtectionPanel to controlRoomOperator { doc /* @S161 */ }
        flow f28 of StationTrafficItem from stationGateway to controlRoomNetworks { doc /* @S172 */ }
        flow f29 of StationTrafficItem from stationGateway to bayNetworks { doc /* @S172 */ }
        flow f30 of StateChangingRequestsItem from controlRoomOperator to bayAutomationController { doc /* @S175 */ }
        flow f31 of BayLevelOutputsItem from bayAutomationController to breakerControlUnit { doc /* @S176 */ }
        flow f32 of OutputCommandsItem from bayAutomationController to breakerControlUnit { doc /* @S177 */ }
        flow f33 of PositionAndCircuitHealthIndicationsItem from breakerControlUnit to bayAutomationController { doc /* @S177 */ }
        flow f34 of ReturnedIndicationsItem from breakerControlUnit to bayAutomationController { doc /* @S178 */ }
        flow f36 of UpdatedIndicationsItem from stationGateway to stationSupervisoryControlSystem { doc /* @S180 */ }
        flow f38 of SettingsReviewReceiptItem from engineeringWorkstation to maintenanceRemoteTerminal { doc /* @S206 */ }
        flow f39 of BatteryLoadTestRecordItem from stationDCSystem to bayAutomationController { doc /* @S207 */ }
        flow f40 of ProtocolRetrySummaryItem from stationGateway to stationSupervisoryControlSystem { doc /* @S208 */ }
        flow f41 of ControlIndicationsAndCommandResultsItem from stationSupervisoryControlSystem to controlRoomOperator { doc /* @S226 */ }
        flow f42 of IsolationBoundaryCardItem from switchingDeskCoordinator to substationFieldCrew { doc /* @S233 */ }
        flow f43 of ClearanceHandoffMemoItem from controlRoomOperator to switchingDeskCoordinator { doc /* @S235 */ }
    }
    requirement def R0 { doc /* Review queries should be bounded by station, equipment identifier, and time interval to keep results reproducible. @S111 */ subject s : ReviewQueries; }
    requirement def R1 { doc /* Glasswing shall retain alarm state and event information for operator review after an indication has cleared. @S156 */ subject s : StationSupervisoryControlSystem; }
    requirement def R2 { doc /* The Bay Automation Controller shall execute only commands permitted by its approved logic and configured interlocks. @S223 */ subject s : BayAutomationController; }
    requirement def R3 { doc /* The Feeder Protection Relay shall retain its protective function independently of supervisory communications. @S224 */ subject s : FeederProtectionRelay; }
    requirement def R4 { doc /* The Engineering Workstation shall be used for authorized configuration work under established change control. @S228 */ subject s : EngineeringWorkstation; }
    requirement def R5 { doc /* time-quality concerns shall be investigated before records are relied upon for sequence analysis @S229 */ subject s : TimeQualityConcerns; }
    requirement def R6 { doc /* The Station Gateway shall maintain the defined boundary between station automation and external communications. @S230 */ subject s : StationGateway; }
    requirement def R7 { doc /* The Station DC System shall be confirmed available before switching that depends on station control power. @S231 */ subject s : StationDCSystem; }
    requirement def R8 { doc /* The Breaker Control Unit shall reject commands that do not satisfy its configured permissive conditions. @S232 */ subject s : BreakerControlUnit; }
    requirement def R9 { doc /* Keystone shall confirm that switching authority, equipment state, and communication limits are understood before coordinating any automation-enabled action. @S236 */ subject s : SwitchingDeskCoordinator; }
    requirement def R10 { doc /* The Maintenance Remote Terminal shall use controlled access @S240 */ subject s : MaintenanceRemoteTerminal; }
    requirement def R11 { doc /* each maintenance session shall be attributable to an authorized user @S240 */ subject s : MaintenanceSession; }
    requirement def R12 { doc /* The North Bay Controller shall be checked for expected local behavior after approved configuration work. @S241 */ subject s : NorthBayController; }
    requirement def R13 { doc /* The South Bay Controller shall be checked for expected local behavior after approved configuration work. @S242 */ subject s : SouthBayController; }
    requirement def R14 { doc /* The North Protection Panel shall remain available for independent protection functions during supervisory control interruptions. @S243 */ subject s : NorthProtectionPanel; }
    requirement def R15 { doc /* The Transformer Protection Panel shall remain within its approved settings and operating constraints during handover. @S244 */ subject s : TransformerProtectionPanel; }
    requirement def R16 { doc /* Periodic operational reviews shall examine command outcomes, event records, exceptions, and corrective actions so that automation decisions remain traceable and safe. @S245 */ subject s : PeriodicOperationalReviews; }
}
