package L2Model {
    item def AcceptedOutputCommandsItem { doc /* @S177 */ }
    item def AuthorizedStationTrafficItem { doc /* @S172 */ }
    item def AvailableControlsAndIndicationsItem { doc /* @S174 */ }
    item def BayLevelOutputsItem { doc /* @S176 */ }
    item def BayLevelStatusIndicationsItem { doc /* @S155 */ }
    item def ControlPowerItem { doc /* @S021 */ }
    item def DisplaysItem { doc /* @S032 */ }
    item def IndicationQualityItem { doc /* @S181 */ }
    item def IndicationsFromTheNorthProtectionPanelItem { doc /* @S159 */ }
    item def OperatingPowerItem { doc /* @S046 */ }
    item def PositionAndCircuitHealthIndicationsItem { doc /* @S177,S178 */ }
    item def ReferenceForTimeSynchronizationItem { doc /* @S017,S038,S040 */ }
    item def StaleDataStatusItem { doc /* @S181 */ }
    item def StateChangingRequestsItem { doc /* @S176 */ }
    item def SupervisoryCommunicationsItem { doc /* @S029 */ }
    item def SwitchingRequestsItem { doc /* @S125 */ }
    item def TimeItem { doc /* @S039 */ }
    part def AffectedPoints { doc /* @S184 */ }
    part def Alarm { doc /* @S162 */ }
    part def AlarmResponse { doc /* @S167 */ }
    part def Alarms { doc /* @S149 */ }
    part def AlderCreekElectricalDistributionSubstation { doc /* @S001,S017 */ }
    part def ApprovedBoundary { doc /* @S234 */ }
    part def ApprovedSettingGroup { doc /* @S053 */ }
    part def ApprovedSwitchingSequences { doc /* @S128 */ }
    part def ApprovedTools { doc /* @S110 */ }
    part def ArchiveReceiptTime { doc /* @S101 */ }
    part def AuthorizedOperatingPersonnel { doc /* @S174 */ }
    part def Automation { doc /* @S092 */ }
    part def AutomationAndProtectionEquipment { doc /* @S021 */ }
    part def AutomationDecisions { doc /* @S245 */ }
    part def AvailableQualityIndications { doc /* @S101 */ }
    part def BayAutomationController { doc /* @S005,S006,S012,S091,S121,S135,S155,S176,S177,S178,S179,S184,S207,S223 */ }
    part def BayBoundaries { doc /* @S133 */ }
    part def BayLevelStatusIndications { doc /* @S155 */ }
    part def BreakerControlUnit { doc /* @S011,S136,S176,S177,S178,S232 */ }
    part def BreakerStatusDiscrepancy { doc /* @S163 */ }
    part def ClearanceStatus { doc /* @S235 */ }
    part def ClearedIndication { doc /* @S156 */ }
    part def Commands { doc /* @S232 */ }
    part def Communications { doc /* @S036,S215 */ }
    part def CommunicationsInterruption { doc /* @S035 */ }
    part def ControlRoom { doc /* @S080 */ }
    part def ControlRoomAndBayNetworks { doc /* @S172 */ }
    part def ControlRoomOperator { doc /* @S022,S032,S077,S083,S093,S107,S125,S148,S149,S150,S151,S152,S153,S155,S159,S162,S168,S170,S175,S176,S181,S199,S215,S222,S238 */ }
    part def ControlSystemFailure { doc /* @S010 */ }
    part def ControlledCommands { doc /* @S213 */ }
    part def CoordinationChecks { doc /* @S062 */ }
    part def Discrepancy { doc /* @S072,S087 */ }
    part def DisplayedInformation { doc /* @S035 */ }
    part def Displays { doc /* @S028 */ }
    part def EngineeringChanges { doc /* @S073 */ }
    part def EngineeringWorkstation { doc /* @S019,S056,S057,S064,S110,S191,S228 */ }
    part def Equipment { doc /* @S013,S040,S042,S220 */ }
    part def EquipmentSharedAcrossTheBoundary { doc /* @S134 */ }
    part def EquipmentStatus { doc /* @S214 */ }
    part def EventEvidence { doc /* @S165 */ }
    part def EventTime { doc /* @S101 */ }
    part def EventTimestamps { doc /* @S041 */ }
    part def Events { doc /* @S104 */ }
    part def EvidenceFromTheCompletedWork { doc /* @S122 */ }
    part def ExportedEvidence { doc /* @S112 */ }
    part def FeederProtectionRelay { doc /* @S008,S009,S052,S186,S224 */ }
    part def FieldAccess { doc /* @S076 */ }
    part def FieldCrews { doc /* @S094 */ }
    part def FieldPersonnel { doc /* @S085 */ }
    part def FieldWork { doc /* @S200,S209 */ }
    part def HoldoverPerformance { doc /* @S043 */ }
    part def Implementation { doc /* @S068 */ }
    part def Indications { doc /* @S083 */ }
    part def LocalControl { doc /* @S013 */ }
    part def LocalInterlocks { doc /* @S130 */ }
    part def MaintenanceRemoteTerminal { doc /* @S020,S206,S240 */ }
    part def MaintenanceSession { doc /* @S240 */ }
    part def MeasuredOffset { doc /* @S044 */ }
    part def NorthBay { doc /* @S130 */ }
    part def NorthBayController { doc /* @S007,S129,S130,S132,S189,S241 */ }
    part def NorthProtectionPanel { doc /* @S137,S158,S159,S187,S243 */ }
    part def OperatingConditions { doc /* @S083 */ }
    part def OperatingMode { doc /* @S012 */ }
    part def OperationalAssurance { doc /* @S221 */ }
    part def Operators { doc /* @S036,S045 */ }
    part def PeriodicOperationalReviews { doc /* @S245 */ }
    part def Permissives { doc /* @S012 */ }
    part def Personnel { doc /* @S080,S202 */ }
    part def Procedure { doc /* @S092 */ }
    part def ProposedChange { doc /* @S058 */ }
    part def ProposedValues { doc /* @S059 */ }
    part def Protection { doc /* @S239 */ }
    part def ProtectionCoordinationQuestions { doc /* @S143 */ }
    part def ProtectionEquipment { doc /* @S158 */ }
    part def ProtectionFunction { doc /* @S212 */ }
    part def ProtectionIndications { doc /* @S162 */ }
    part def ProtectionRelayEngineer { doc /* @S023,S054,S055,S059,S066,S108,S109,S143,S165,S194,S203,S225,S239 */ }
    part def ProtectionTesting { doc /* @S203 */ }
    part def QualityIndications { doc /* @S118 */ }
    part def Records { doc /* @S104,S118,S221 */ }
    part def RecoveryTesting { doc /* @S118 */ }
    part def RelatedIndications { doc /* @S149 */ }
    part def RelayIndications { doc /* @S165 */ }
    part def RemoteCommands { doc /* @S214 */ }
    part def RemoteIndications { doc /* @S215 */ }
    part def RemoteOperationsInterfaces { doc /* @S029 */ }
    part def RemoteStatus { doc /* @S196,S216,S238 */ }
    part def RequiredPermissives { doc /* @S214 */ }
    part def RequiredRecords { doc /* @S220 */ }
    part def ResponsibleOperator { doc /* @S212 */ }
    part def Restoration { doc /* @S219 */ }
    part def RetainedRecord { doc /* @S101 */ }
    part def ReviewQueries { doc /* @S111 */ }
    part def SatelliteTimeReceiver { doc /* @S017,S038,S039,S040,S044,S103,S144,S183,S229 */ }
    part def SecondQualifiedReviewer { doc /* @S060 */ }
    part def SelfMonitoring { doc /* @S009 */ }
    part def SequenceEventArchive { doc /* @S018,S100,S102,S105,S106,S115,S140,S157,S182,S210,S227 */ }
    part def SettingsConcerns { doc /* @S165 */ }
    part def SettingsReview { doc /* @S058,S061 */ }
    part def SourceIdentity { doc /* @S101 */ }
    part def SouthBayController { doc /* @S007,S131,S132,S190,S242 */ }
    part def StateChangeEvidence { doc /* @S146 */ }
    part def Station { doc /* @S119 */ }
    part def StationAutomationBoundary { doc /* @S002 */ }
    part def StationAutomationEquipment { doc /* @S046 */ }
    part def StationCommunicationsDesign { doc /* @S171 */ }
    part def StationDCSystem { doc /* @S021,S046,S120,S193,S231 */ }
    part def StationEquipment { doc /* @S039 */ }
    part def StationGateway { doc /* @S016,S029,S142,S172,S173,S180,S185,S230 */ }
    part def StationLevelFunctions { doc /* @S029 */ }
    part def StationSupervisoryControlSystem { doc /* @S015,S027,S032,S048,S090,S106,S139,S156,S174,S181,S208,S226 */ }
    part def SubstationFieldCrew { doc /* @S024,S069,S075,S079,S084,S088,S089,S095,S145,S166,S196,S201,S209,S216,S233,S234 */ }
    part def SubstationSupervisor { doc /* @S049,S073,S078,S127,S195,S198,S220,S237 */ }
    part def SupervisoryArchitecture { doc /* @S025 */ }
    part def SupervisoryLayer { doc /* @S031 */ }
    part def SupervisoryVisibility { doc /* @S030 */ }
    part def SupportedSatelliteTimingSignals { doc /* @S038 */ }
    part def Switching { doc /* @S231 */ }
    part def SwitchingAction { doc /* @S134 */ }
    part def SwitchingDeskCoordinator { doc /* @S082,S097,S122,S124,S125,S126,S141,S146,S169,S200,S235,S236 */ }
    part def TimeDistribution { doc /* @S040 */ }
    part def TimeQualityConcerns { doc /* @S229 */ }
    part def TimeQualityIndications { doc /* @S045 */ }
    part def Timestamps { doc /* @S118 */ }
    part def TransformerProtectionPanel { doc /* @S138,S161,S188,S244 */ }
    part def UnexpectedIndications { doc /* @S204 */ }
    part def UnresolvedAlarmCondition { doc /* @S168 */ }
    part def UnresolvedCondition { doc /* @S151 */ }
    part def Updates { doc /* @S184 */ }
    part def Work { doc /* @S077,S082,S094 */ }
    part def WorkArea { doc /* @S096 */ }
    part def WorkPackage { doc /* @S199 */ }
    part system {
        part affectedPoints : AffectedPoints {
            exhibit state modes {
                state s0 { doc /* degraded state @S184 */ }
            }
        }
        part alarm : Alarm {
            perform action a0 { doc /* suggest a possible control-power concern @S162 */ }
        }
        part alarmResponse : AlarmResponse {
            perform action a0 { doc /* requires escalation beyond routine operator actions @S167 */ }
        }
        part alarms : Alarms {
            exhibit state modes {
                state s0 { doc /* new alarm @S149 */ }
            }
        }
        part alderCreekElectricalDistributionSubstation : AlderCreekElectricalDistributionSubstation {
            perform action a0 { doc /* supplies distribution circuits through transformer and feeder bays @S001 */ }
        }
        part approvedBoundary : ApprovedBoundary {
            exhibit state modes {
                state s0 { doc /* uncertain @S234 */ }
            }
        }
        part approvedSettingGroup : ApprovedSettingGroup {
            perform action a0 { doc /* defines the pickup levels, time delays, and logic required for the feeder protection scheme @S053 */ }
        }
        part approvedSwitchingSequences : ApprovedSwitchingSequences {
            perform action a0 { doc /* identify the required order of actions, hold points, and conditions for stopping work @S128 */ }
        }
        part approvedTools : ApprovedTools {
            perform action a0 { doc /* searching, filtering, and exporting event records @S110 */ }
        }
        part archiveReceiptTime : ArchiveReceiptTime;
        part authorizedOperatingPersonnel : AuthorizedOperatingPersonnel;
        part automation : Automation {
            perform action a0 { doc /* does not replace field verification @S092 */ }
        }
        part automationAndProtectionEquipment : AutomationAndProtectionEquipment;
        part automationDecisions : AutomationDecisions {
            perform action a0 { doc /* remain traceable and safe @S245 */ }
        }
        part availableQualityIndications : AvailableQualityIndications;
        part bayAutomationController : BayAutomationController {
            perform action a0 { doc /* performs bay-level sequencing, status evaluation, and control permissive checks @S005 */ }
            perform action a1 { doc /* produces a Bay Status Digest for operational awareness @S006 */ }
            perform action a2 { doc /* requests breaker operations only when the applicable operating mode and permissives allow them @S012 */ }
            perform action a3 { doc /* applies configured permissives and interlocks to supported automated operations @S091 */ }
            perform action a4 { doc /* timestamps locally generated state changes for later correlation @S121 */ }
            perform action a5 { doc /* presents bay control status @S135 */ }
            perform action a6 { doc /* preserving the separate operating scopes of the two controllers @S135 */ }
            perform action a7 { doc /* provides bay-level status indications @S155 */ }
            perform action a8 { doc /* validates each received request against local mode, interlocks, command authority, and equipment availability @S176 */ }
            perform action a9 { doc /* issuing bay-level outputs @S176 */ }
            perform action a10 { doc /* compares returned indications with the requested state @S178 */ }
            perform action a11 { doc /* identifies incomplete or contradictory operation @S178 */ }
            perform action a12 { doc /* uses the inspection tag @S179 */ }
            perform action a13 { doc /* associate the applicable equipment context with an authorized record @S179 */ }
            perform action a14 { doc /* monitors communication health @S184 */ }
            perform action a15 { doc /* places affected points in a defined degraded state @S184 */ }
            perform action a16 { doc /* uses the load test record @S207 */ }
            perform action a17 { doc /* support maintenance review @S207 */ }
            perform action a18 { doc /* execute only commands permitted by its approved logic and configured interlocks @S223 */ }
        }
        part bayBoundaries : BayBoundaries {
            perform action a0 { doc /* defines which controller may operate each device and which indications are used to confirm its state @S133 */ }
        }
        part bayLevelStatusIndications : BayLevelStatusIndications {
            perform action a0 { doc /* support the operator’s assessment of the alarm @S155 */ }
        }
        part breakerControlUnit : BreakerControlUnit {
            perform action a0 { doc /* executes authorized breaker operations @S011 */ }
            perform action a1 { doc /* enforces its local electrical and mechanical interlocks @S011 */ }
            perform action a2 { doc /* executes permitted breaker commands only when the applicable control conditions are satisfied @S136 */ }
            perform action a3 { doc /* applies accepted output commands at the breaker interface @S177 */ }
            perform action a4 { doc /* returns the resulting position and circuit-health indications @S177 */ }
            perform action a5 { doc /* reject commands that do not satisfy its configured permissive conditions @S232 */ }
        }
        part breakerStatusDiscrepancy : BreakerStatusDiscrepancy {
            exhibit state modes {
                state s0 { doc /* abnormal condition @S163 */ }
            }
        }
        part clearanceStatus : ClearanceStatus {
            perform action a0 { doc /* agrees with the active switching record @S235 */ }
        }
        part clearedIndication : ClearedIndication {
            perform action a0 { doc /* has cleared @S156 */ }
        }
        part commands : Commands {
            perform action a0 { doc /* do not satisfy its configured permissive conditions @S232 */ }
        }
        part communications : Communications {
            perform action a0 { doc /* recover @S036 */ }
            exhibit state modes {
                state s0 { doc /* degraded @S215 */ }
            }
        }
        part communicationsInterruption : CommunicationsInterruption {
            perform action a0 { doc /* can leave displayed information stale or temporarily unavailable @S035 */ }
        }
        part controlRoom : ControlRoom {
            perform action a0 { doc /* can account for field staff @S080 */ }
        }
        part controlRoomAndBayNetworks : ControlRoomAndBayNetworks;
        part controlRoomOperator : ControlRoomOperator {
            perform action a0 { doc /* directs routine station operation @S022 */ }
            perform action a1 { doc /* verifies that commanded equipment states are appropriate @S022 */ }
            perform action a2 { doc /* uses the supervisory displays to assess station conditions and coordinate operating actions @S032 */ }
            perform action a3 { doc /* assess station conditions @S032 */ }
            perform action a4 { doc /* coordinate operating actions @S032 */ }
            perform action a5 { doc /* coordinates operational access with the Switching Desk Coordinator @S077 */ }
            perform action a6 { doc /* retains authority to suspend work when operating conditions change or indications become uncertain @S083 */ }
            perform action a7 { doc /* suspend work @S083 */ }
            perform action a8 { doc /* evaluates reported field conditions @S093 */ }
            perform action a9 { doc /* authorizing a return to automated operation @S093 */ }
            perform action a10 { doc /* reviews archived event sequences @S107 */ }
            perform action a11 { doc /* establish the order of alarms, status changes, and operator actions @S107 */ }
            perform action a12 { doc /* submits switching requests with the affected equipment, intended state changes, and requested timing @S125 */ }
            perform action a13 { doc /* reviews the alarm priority, source, time, and associated bay indications @S148 */ }
            perform action a14 { doc /* deciding on a response @S148 */ }
            perform action a15 { doc /* distinguishes a new alarm from a standing condition @S149 */ }
            perform action a16 { doc /* checks whether related indications support the same assessment @S149 */ }
            perform action a17 { doc /* treats the condition as requiring prompt investigation @S150 */ }
            perform action a18 { doc /* acknowledges alarms @S151 */ }
            perform action a19 { doc /* reviewing the indication @S151 */ }
            perform action a20 { doc /* retains awareness of any condition that remains unresolved @S151 */ }
            perform action a21 { doc /* uses the acknowledgement slip @S152 */ }
            perform action a22 { doc /* record the alarm response and any outstanding action @S152 */ }
            perform action a23 { doc /* checks available device status and sequence information @S153 */ }
            perform action a24 { doc /* without treating a cleared indication as proof that the underlying cause has been corrected @S153 */ }
            perform action a25 { doc /* uses indications from the North Protection Panel @S159 */ }
            perform action a26 { doc /* assess feeder protection operations and related alarms @S159 */ }
            perform action a27 { doc /* considers the condition of the Station DC System @S162 */ }
            perform action a28 { doc /* produces the Clearance Handoff Memo @S168 */ }
            perform action a29 { doc /* verifies that alarm status, equipment status, and recorded evidence are consistent @S170 */ }
            perform action a30 { doc /* closing the response @S170 */ }
            perform action a31 { doc /* issues state-changing requests only through approved operating procedures and the configured supervisory interface @S175 */ }
            perform action a32 { doc /* can distinguish a current value from a retained value @S181 */ }
            perform action a33 { doc /* reviews the equipment affected by each work package @S199 */ }
            perform action a34 { doc /* identifies any required operating restrictions @S199 */ }
            perform action a35 { doc /* treats remote indications as unavailable until their reliability is established @S215 */ }
            perform action a36 { doc /* remains responsible for deciding whether an automation request is appropriate for current operating conditions @S222 */ }
            perform action a37 { doc /* deciding whether an automation request is appropriate for current operating conditions @S222 */ }
            perform action a38 { doc /* confirms indications locally @S238 */ }
        }
        part controlSystemFailure : ControlSystemFailure {
            perform action a0 { doc /* does not inhibit fault clearing @S010 */ }
        }
        part controlledCommands : ControlledCommands {
            perform action a0 { doc /* cannot bypass local interlocks or approved operating authority @S213 */ }
        }
        part coordinationChecks : CoordinationChecks {
            perform action a0 { doc /* consider upstream and downstream protection behavior across the expected operating range @S062 */ }
        }
        part discrepancy : Discrepancy {
            perform action a0 { doc /* stops release of the configuration until its cause is resolved and reviewed @S072 */ }
            exhibit state modes {
                state s0 { doc /* unsafe condition @S087 */ }
            }
        }
        part displayedInformation : DisplayedInformation {
            exhibit state modes {
                state s0 { doc /* stale @S035 */ }
                state s1 { doc /* temporarily unavailable @S035 */ }
            }
        }
        part displays : Displays {
            perform action a0 { doc /* show operating conditions and communication quality without replacing local equipment indications @S028 */ }
            perform action a1 { doc /* replacing local equipment indications @S028 */ }
        }
        part engineeringChanges : EngineeringChanges {
            perform action a0 { doc /* follow the established authorization and operational control process @S073 */ }
        }
        part engineeringWorkstation : EngineeringWorkstation {
            perform action a0 { doc /* supports authorized configuration and maintenance activities under controlled access @S019 */ }
            perform action a1 { doc /* maintains the working configuration under revision control @S056 */ }
            perform action a2 { doc /* produces the Settings Review Receipt @S057 */ }
            perform action a3 { doc /* retains the approved configuration and its revision history for controlled access @S064 */ }
            perform action a4 { doc /* provides approved tools for searching, filtering, and exporting event records @S110 */ }
            perform action a5 { doc /* supports approved configuration review @S191 */ }
            perform action a6 { doc /* does not serve as a routine source of operating commands @S191 */ }
        }
        part equipment : Equipment {
            perform action a0 { doc /* receives @S040 */ }
            perform action a1 { doc /* applies the reference @S040 */ }
            perform action a2 { doc /* depends on its individual clock and holdover capabilities @S042 */ }
            exhibit state modes {
                state s0 { doc /* local operation @S013 */ }
                state s1 { doc /* normal service @S220 */ }
            }
        }
        part equipmentSharedAcrossTheBoundary : EquipmentSharedAcrossTheBoundary {
            perform action a0 { doc /* requires explicit coordination @S134 */ }
        }
        part equipmentStatus : EquipmentStatus {
            exhibit state modes {
                state s0 { doc /* uncertain @S214 */ }
            }
        }
        part eventEvidence : EventEvidence {
            perform action a0 { doc /* require technical interpretation @S165 */ }
        }
        part eventTime : EventTime;
        part eventTimestamps : EventTimestamps {
            perform action a0 { doc /* assist event correlation @S041 */ }
            perform action a1 { doc /* do not establish the validity of an electrical measurement or protection decision @S041 */ }
        }
        part events : Events {
            exhibit state modes {
                state s0 { doc /* corrected or estimated times @S104 */ }
            }
        }
        part evidenceFromTheCompletedWork : EvidenceFromTheCompletedWork {
            perform action a0 { doc /* remains available for authorized engineering review @S122 */ }
            exhibit state modes {
                state s0 { doc /* available for authorized engineering review @S122 */ }
            }
        }
        part exportedEvidence : ExportedEvidence {
            perform action a0 { doc /* retains original timestamps and quality flags @S112 */ }
        }
        part feederProtectionRelay : FeederProtectionRelay {
            perform action a0 { doc /* detects feeder faults @S008 */ }
            perform action a1 { doc /* initiates protection actions within its configured protection zone @S008 */ }
            perform action a2 { doc /* produces a Relay Diagnostic Note when its self-monitoring identifies a condition requiring engineering attention @S009 */ }
            perform action a3 { doc /* provides local protection for its assigned feeder @S052 */ }
            perform action a4 { doc /* operates independently of supervisory control availability @S052 */ }
            perform action a5 { doc /* evaluates electrical quantities against approved settings @S186 */ }
            perform action a6 { doc /* issues protective trip outputs @S186 */ }
            perform action a7 { doc /* without relying on supervisory communications @S186 */ }
            perform action a8 { doc /* retain its protective function independently of supervisory communications @S224 */ }
        }
        part fieldAccess : FieldAccess {
            perform action a0 { doc /* begins @S076 */ }
        }
        part fieldCrews : FieldCrews {
            perform action a0 { doc /* maintain communications with the control room throughout work that could affect protection, control, or service continuity @S094 */ }
        }
        part fieldPersonnel : FieldPersonnel {
            perform action a0 { doc /* do not rely on screen indications alone @S085 */ }
            perform action a1 { doc /* establish that equipment is safe to approach or handle @S085 */ }
            perform action a2 { doc /* approach @S085 */ }
            perform action a3 { doc /* handle @S085 */ }
        }
        part fieldWork : FieldWork {
            perform action a0 { doc /* begins @S200 */ }
            perform action a1 { doc /* remains within the approved work boundary @S209 */ }
        }
        part holdoverPerformance : HoldoverPerformance {
            perform action a0 { doc /* varies by device @S043 */ }
            perform action a1 { doc /* may degrade as the interval without a valid reference increases @S043 */ }
        }
        part implementation : Implementation {
            perform action a0 { doc /* could affect feeder protection @S068 */ }
        }
        part indications : Indications {
            perform action a0 { doc /* become uncertain @S083 */ }
        }
        part localControl : LocalControl {
            perform action a0 { doc /* takes precedence when equipment is selected for local operation @S013 */ }
        }
        part localInterlocks : LocalInterlocks {
            perform action a0 { doc /* indicate that the bay is not ready @S130 */ }
        }
        part maintenanceRemoteTerminal : MaintenanceRemoteTerminal {
            perform action a0 { doc /* does not replace local operating authority @S020 */ }
            perform action a1 { doc /* uses the review receipt @S206 */ }
            perform action a2 { doc /* support controlled maintenance review @S206 */ }
            perform action a3 { doc /* use controlled access @S240 */ }
        }
        part maintenanceSession : MaintenanceSession {
            perform action a0 { doc /* be attributable to an authorized user @S240 */ }
        }
        part measuredOffset : MeasuredOffset {
            perform action a0 { doc /* meets the configured reporting condition @S044 */ }
        }
        part northBay : NorthBay {
            exhibit state modes {
                state s0 { doc /* not ready @S130 */ }
            }
        }
        part northBayController : NorthBayController {
            perform action a0 { doc /* provide bay-specific automation for their respective portions of the station @S007 */ }
            perform action a1 { doc /* manages control and interlocking functions assigned to the north bay under the approved sequence @S129 */ }
            perform action a2 { doc /* blocks a close command when its local interlocks indicate that the bay is not ready @S130 */ }
            perform action a3 { doc /* do not substitute for one another when executing a switching sequence @S132 */ }
            perform action a4 { doc /* executing a switching sequence @S132 */ }
            perform action a5 { doc /* maintains local bay control within the approved operating mode @S189 */ }
            exhibit state modes {
                state s0 { doc /* approved operating mode @S189 */ }
            }
        }
        part northProtectionPanel : NorthProtectionPanel {
            perform action a0 { doc /* supports protection functions for the north-side equipment within its assigned scope @S137 */ }
            perform action a1 { doc /* applies its assigned zone logic @S187 */ }
            perform action a2 { doc /* maintains trip paths independently of supervisory network availability @S187 */ }
            perform action a3 { doc /* remain available for independent protection functions during supervisory control interruptions @S243 */ }
        }
        part operatingConditions : OperatingConditions {
            perform action a0 { doc /* change @S083 */ }
        }
        part operatingMode : OperatingMode {
            perform action a0 { doc /* allow them @S012 */ }
        }
        part operationalAssurance : OperationalAssurance {
            perform action a0 { doc /* depends on clear authority, verified equipment state, and records that support later review @S221 */ }
        }
        part operators : Operators {
            perform action a0 { doc /* confirm that indications are current @S036 */ }
            perform action a1 { doc /* relying on them for decisions @S036 */ }
            perform action a2 { doc /* distinguish synchronized operation from degraded or unavailable timing @S045 */ }
        }
        part periodicOperationalReviews : PeriodicOperationalReviews {
            perform action a0 { doc /* examine command outcomes, event records, exceptions, and corrective actions @S245 */ }
        }
        part permissives : Permissives {
            perform action a0 { doc /* allow them @S012 */ }
        }
        part personnel : Personnel {
            perform action a0 { doc /* use the site access process @S080 */ }
            perform action a1 { doc /* record arrival and departure @S080 */ }
            perform action a2 { doc /* approach exposed conductors @S202 */ }
            perform action a3 { doc /* operate equipment under maintenance @S202 */ }
        }
        part procedure : Procedure {
            perform action a0 { doc /* requires direct confirmation of equipment condition @S092 */ }
        }
        part proposedChange : ProposedChange {
            perform action a0 { doc /* receives a unique revision identifier @S058 */ }
        }
        part proposedValues : ProposedValues {
            perform action a0 { doc /* agree with the approved coordination objectives @S059 */ }
        }
        part protection : Protection {
            exhibit state modes {
                state s0 { doc /* service @S239 */ }
            }
        }
        part protectionCoordinationQuestions : ProtectionCoordinationQuestions {
            perform action a0 { doc /* affect the planned switching sequence @S143 */ }
        }
        part protectionEquipment : ProtectionEquipment;
        part protectionFunction : ProtectionFunction {
            exhibit state modes {
                state s0 { doc /* out of service @S212 */ }
            }
        }
        part protectionIndications : ProtectionIndications {
            perform action a0 { doc /* suggest a possible control-power concern @S162 */ }
        }
        part protectionRelayEngineer : ProtectionRelayEngineer {
            perform action a0 { doc /* maintains protection settings @S023 */ }
            perform action a1 { doc /* evaluates relay performance within the approved change process @S023 */ }
            perform action a2 { doc /* develops setting changes against the approved protection study and the current equipment data @S054 */ }
            perform action a3 { doc /* documents the engineering basis and expected operational effect for each proposed change @S055 */ }
            perform action a4 { doc /* verifies that proposed values agree with the approved coordination objectives @S059 */ }
            perform action a5 { doc /* records the approval status @S066 */ }
            perform action a6 { doc /* compares event times and relay indications during disturbance analysis @S108 */ }
            perform action a7 { doc /* uses the Relay Diagnostic Note during fault analysis @S109 */ }
            perform action a8 { doc /* reviews protection coordination questions that could affect the planned switching sequence @S143 */ }
            perform action a9 { doc /* supports investigation @S165 */ }
            perform action a10 { doc /* reviews protection event records @S194 */ }
            perform action a11 { doc /* verifies that approved settings remain consistent with coordination requirements @S194 */ }
            perform action a12 { doc /* reviews test scope, approved settings, and restoration criteria @S203 */ }
            perform action a13 { doc /* reviews protection behavior after material changes @S225 */ }
            perform action a14 { doc /* records any unresolved concerns for operational follow-up @S225 */ }
            perform action a15 { doc /* assesses unexplained trips and abnormal protection indications @S239 */ }
        }
        part protectionTesting : ProtectionTesting {
            perform action a0 { doc /* starts @S203 */ }
        }
        part qualityIndications : QualityIndications {
            perform action a0 { doc /* survive restoration @S118 */ }
        }
        part records : Records {
            perform action a0 { doc /* support later review @S221 */ }
            exhibit state modes {
                state s0 { doc /* readable @S118 */ }
                state s1 { doc /* valid time quality @S104 */ }
            }
        }
        part recoveryTesting : RecoveryTesting {
            perform action a0 { doc /* verifies that retained records remain readable and that timestamps and quality indications survive restoration @S118 */ }
        }
        part relatedIndications : RelatedIndications {
            perform action a0 { doc /* support the same assessment @S149 */ }
        }
        part relayIndications : RelayIndications {
            perform action a0 { doc /* require technical interpretation @S165 */ }
        }
        part remoteCommands : RemoteCommands {
            exhibit state modes {
                state s0 { doc /* inhibited @S214 */ }
            }
        }
        part remoteIndications : RemoteIndications {
            exhibit state modes {
                state s0 { doc /* unavailable @S215 */ }
            }
        }
        part remoteOperationsInterfaces : RemoteOperationsInterfaces;
        part remoteStatus : RemoteStatus {
            exhibit state modes {
                state s0 { doc /* delayed @S238 */ }
                state s1 { doc /* incomplete @S238 */ }
                state s2 { doc /* inconsistent @S238 */ }
                state s3 { doc /* uncertain @S196,S216 */ }
            }
        }
        part requiredPermissives : RequiredPermissives {
            exhibit state modes {
                state s0 { doc /* unavailable @S214 */ }
            }
        }
        part requiredRecords : RequiredRecords {
            exhibit state modes {
                state s0 { doc /* complete @S220 */ }
            }
        }
        part responsibleOperator : ResponsibleOperator {
            perform action a0 { doc /* is tracked by the responsible operator @S212 */ }
        }
        part restoration : Restoration {
            perform action a0 { doc /* includes confirming normal indications, protection availability, communications status, and the removal of temporary test connections @S219 */ }
        }
        part retainedRecord : RetainedRecord;
        part reviewQueries : ReviewQueries;
        part satelliteTimeReceiver : SatelliteTimeReceiver {
            perform action a0 { doc /* provides the station with a reference for time synchronization @S017 */ }
            perform action a1 { doc /* acquires a reference from supported satellite timing signals @S038 */ }
            perform action a2 { doc /* distributes time to station equipment over the configured time-distribution network @S039 */ }
            perform action a3 { doc /* produces the Clock Drift Snapshot when its measured offset meets the configured reporting condition @S044 */ }
            perform action a4 { doc /* supports station time alignment @S103 */ }
            perform action a5 { doc /* provides the station time reference used to align recorded event times @S144 */ }
            perform action a6 { doc /* supplies the station time reference @S183 */ }
            perform action a7 { doc /* supports consistent event timing @S229 */ }
        }
        part secondQualifiedReviewer : SecondQualifiedReviewer {
            perform action a0 { doc /* independently checks calculations, logic changes, and device applicability @S060 */ }
        }
        part selfMonitoring : SelfMonitoring {
            perform action a0 { doc /* identifies a condition requiring engineering attention @S009 */ }
        }
        part sequenceEventArchive : SequenceEventArchive {
            perform action a0 { doc /* retains operational event information for later review @S018 */ }
            perform action a1 { doc /* preserves event records in their received form @S100 */ }
            perform action a2 { doc /* preserves original event ordering @S102 */ }
            perform action a3 { doc /* marks records whose time quality or sequence continuity is uncertain @S102 */ }
            perform action a4 { doc /* retains configuration and access history associated with archive administration @S105 */ }
            perform action a5 { doc /* held by the archive @S106 */ }
            perform action a6 { doc /* retains records under the station records schedule and applicable utility retention requirements @S115 */ }
            perform action a7 { doc /* receives the Clock Drift Snapshot for event-time correlation @S140 */ }
            perform action a8 { doc /* provides time-ordered evidence for later operational review @S157 */ }
            perform action a9 { doc /* retains time-tagged changes and control outcomes for event reconstruction and operational review @S182 */ }
            perform action a10 { doc /* retains event information needed to review testing and restoration activity @S210 */ }
            perform action a11 { doc /* retains time-ordered records needed to reconstruct significant control and protection events @S227 */ }
        }
        part settingsConcerns : SettingsConcerns {
            perform action a0 { doc /* require technical interpretation @S165 */ }
        }
        part settingsReview : SettingsReview {
            perform action a0 { doc /* review begins @S058 */ }
            perform action a1 { doc /* confirms that the proposed configuration is complete, internally consistent, and suitable for the intended feeder @S061 */ }
        }
        part sourceIdentity : SourceIdentity;
        part southBayController : SouthBayController {
            perform action a0 { doc /* provide bay-specific automation for their respective portions of the station @S007 */ }
            perform action a1 { doc /* manages the corresponding control and interlocking functions assigned to the south bay @S131 */ }
            perform action a2 { doc /* do not substitute for one another when executing a switching sequence @S132 */ }
            perform action a3 { doc /* executing a switching sequence @S132 */ }
            perform action a4 { doc /* reports local mode and control availability through its configured bay interface @S190 */ }
        }
        part stateChangeEvidence : StateChangeEvidence {
            perform action a0 { doc /* remains available for authorized engineering review @S146 */ }
            exhibit state modes {
                state s0 { doc /* available for authorized engineering review @S146 */ }
            }
        }
        part station : Station {
            perform action a0 { doc /* preserves an additional protected copy of essential event evidence in accordance with approved backup procedures @S119 */ }
        }
        part stationAutomationBoundary : StationAutomationBoundary {
            perform action a0 { doc /* covers bay-level monitoring and control, station coordination, and the interfaces to external operating personnel and systems @S002 */ }
        }
        part stationAutomationEquipment : StationAutomationEquipment;
        part stationCommunicationsDesign : StationCommunicationsDesign {
            perform action a0 { doc /* separates supervisory requests, bay-level execution, and protection action @S171 */ }
        }
        part stationDCSystem : StationDCSystem {
            perform action a0 { doc /* supplies control power to automation and protection equipment within its design capacity @S021 */ }
            perform action a1 { doc /* supplies operating power to station automation equipment within its designed capacity @S046 */ }
            perform action a2 { doc /* produces a Battery Load Test Record for retention with station engineering records @S120 */ }
            perform action a3 { doc /* supports control and protection functions through monitored station supply circuits @S193 */ }
            exhibit state modes {
                state s0 { doc /* abnormal station condition @S193 */ }
                state s1 { doc /* available @S231 */ }
            }
        }
        part stationEquipment : StationEquipment;
        part stationGateway : StationGateway {
            perform action a0 { doc /* defines the communications boundary for authorized connections beyond the station automation network @S016 */ }
            perform action a1 { doc /* carries supervisory communications between station-level functions and remote operations interfaces @S029 */ }
            perform action a2 { doc /* produces the Protocol Retry Summary for communication review @S142 */ }
            perform action a3 { doc /* brokers authorized station traffic across control-room and bay networks @S172 */ }
            perform action a4 { doc /* applying configured protocol mappings, addressing, and access controls @S172 */ }
            perform action a5 { doc /* rejects malformed, stale, or unauthorized requests @S173 */ }
            perform action a6 { doc /* records each rejection with enough context for operations review @S173 */ }
            perform action a7 { doc /* carries updated indications through the station interface using configured quality and timestamp attributes @S180 */ }
            perform action a8 { doc /* reports link condition and protocol errors @S185 */ }
            perform action a9 { doc /* without converting a communication failure into an equipment-state change @S185 */ }
            perform action a10 { doc /* maintain the defined boundary between station automation and external communications @S230 */ }
        }
        part stationLevelFunctions : StationLevelFunctions;
        part stationSupervisoryControlSystem : StationSupervisoryControlSystem {
            perform action a0 { doc /* provides the station-level operating interface and supervisory coordination @S015 */ }
            perform action a1 { doc /* presents available station and bay indications through a consolidated operator interface @S027 */ }
            perform action a2 { doc /* produces the Alarm Acknowledgement Slip for supervisory recordkeeping @S048 */ }
            perform action a3 { doc /* presents available equipment indications for operator review during normal operation @S090 */ }
            perform action a4 { doc /* presents current operating indications separately from the long-term evidence held by the archive @S106 */ }
            perform action a5 { doc /* uses the status digest @S139 */ }
            perform action a6 { doc /* review current station operating conditions @S139 */ }
            perform action a7 { doc /* retain alarm state and event information for operator review @S156 */ }
            perform action a8 { doc /* presents available controls and indications to authorized operating personnel @S174 */ }
            perform action a9 { doc /* displays indication quality and stale-data status @S181 */ }
            perform action a10 { doc /* receives the Protocol Retry Summary for operational review @S208 */ }
            perform action a11 { doc /* presents control indications and command results for operator assessment @S226 */ }
            exhibit state modes {
                state s0 { doc /* normal operation @S090 */ }
            }
        }
        part substationFieldCrew : SubstationFieldCrew {
            perform action a0 { doc /* performs field checks and equipment work under the applicable switching instructions and clearances @S024 */ }
            perform action a1 { doc /* follows the authorized work instructions during device access and setting transfer @S069 */ }
            perform action a2 { doc /* performs inspections, maintenance, and switching support within the boundaries of approved work @S075 */ }
            perform action a3 { doc /* reviews the work scope, access route, known hazards, and communication arrangements @S079 */ }
            perform action a4 { doc /* entering the yard @S079 */ }
            perform action a5 { doc /* verifies equipment identity at the point of work against the approved work documentation @S084 */ }
            perform action a6 { doc /* promptly reports uncertain equipment conditions through the designated operational communication channel @S088 */ }
            perform action a7 { doc /* completes the Breaker Inspection Tag @S089 */ }
            perform action a8 { doc /* sends the Breaker Inspection Tag @S089 */ }
            perform action a9 { doc /* recording the observed breaker condition and inspection time @S089 */ }
            perform action a10 { doc /* stops affected work @S095 */ }
            perform action a11 { doc /* follows the approved hold and escalation procedure @S095 */ }
            perform action a12 { doc /* confirms device identity and local conditions @S145 */ }
            perform action a13 { doc /* carrying out an authorized operation @S145 */ }
            perform action a14 { doc /* confirms device identity and local conditions @S166 */ }
            perform action a15 { doc /* carrying out an authorized operation @S166 */ }
            perform action a16 { doc /* verifies equipment indications locally @S196 */ }
            perform action a17 { doc /* reports discrepancies through established operating channels @S196 */ }
            perform action a18 { doc /* performs work @S201 */ }
            perform action a19 { doc /* verifies that field work remains within the approved work boundary @S209 */ }
            perform action a20 { doc /* reports any unsafe condition through established channels @S209 */ }
            perform action a21 { doc /* verifies equipment indications locally @S216 */ }
            perform action a22 { doc /* reports discrepancies through established operating channels @S216 */ }
            perform action a23 { doc /* uses the Isolation Boundary Card @S233 */ }
            perform action a24 { doc /* verify the approved work boundary @S233 */ }
            perform action a25 { doc /* entering the controlled area @S233 */ }
            perform action a26 { doc /* reports unexpected equipment conditions promptly @S234 */ }
            perform action a27 { doc /* pauses work when the approved boundary is uncertain @S234 */ }
        }
        part substationSupervisor : SubstationSupervisor {
            perform action a0 { doc /* oversees operational use of the supervisory system and escalation of unresolved availability concerns @S049 */ }
            perform action a1 { doc /* ensures that engineering changes follow the established authorization and operational control process @S073 */ }
            perform action a2 { doc /* confirms that the requested work is consistent with current operating conditions and approved procedures @S078 */ }
            perform action a3 { doc /* resolves priority conflicts @S127 */ }
            perform action a4 { doc /* confirms the operational authority for exceptional switching conditions @S127 */ }
            perform action a5 { doc /* ensures communication changes, point mapping changes, and control logic changes are managed through station change control @S195 */ }
            perform action a6 { doc /* coordinates work timing with the Switching Desk Coordinator @S198 */ }
            perform action a7 { doc /* confirms that operating responsibilities are understood @S198 */ }
            perform action a8 { doc /* confirms that required records are complete and that operating restrictions are formally cleared @S220 */ }
            perform action a9 { doc /* returning equipment to normal service @S220 */ }
            perform action a10 { doc /* verifies that unresolved risks have an assigned owner and an agreed disposition @S237 */ }
        }
        part supervisoryArchitecture : SupervisoryArchitecture {
            perform action a0 { doc /* separates station-wide observation from local bay and protection functions @S025 */ }
        }
        part supervisoryLayer : SupervisoryLayer {
            perform action a0 { doc /* does not perform the protective functions assigned to dedicated protection equipment @S031 */ }
        }
        part supervisoryVisibility : SupervisoryVisibility {
            perform action a0 { doc /* depends on the availability and quality of the underlying communications and status inputs @S030 */ }
        }
        part supportedSatelliteTimingSignals : SupportedSatelliteTimingSignals;
        part switching : Switching {
            perform action a0 { doc /* depends on station control power @S231 */ }
        }
        part switchingAction : SwitchingAction {
            perform action a0 { doc /* affect either bay @S134 */ }
        }
        part switchingDeskCoordinator : SwitchingDeskCoordinator {
            perform action a0 { doc /* confirms the applicable switching and clearance arrangements @S082 */ }
            perform action a1 { doc /* confirms the operational handback arrangements @S097 */ }
            perform action a2 { doc /* confirms operational handback @S122 */ }
            perform action a3 { doc /* maintains the station-wide switching plan @S124 */ }
            perform action a4 { doc /* coordinates work across the two bay boundaries @S124 */ }
            perform action a5 { doc /* checks each request for conflicts with active clearances and other approved work @S126 */ }
            perform action a6 { doc /* produces the Isolation Boundary Card for the planned work @S141 */ }
            perform action a7 { doc /* confirms operational handback @S146 */ }
            perform action a8 { doc /* confirms operational handback @S169 */ }
            perform action a9 { doc /* confirms switching prerequisites @S200 */ }
            perform action a10 { doc /* keeps the approved switching sequence current @S200 */ }
            perform action a11 { doc /* receives the Clearance Handoff Memo @S235 */ }
            perform action a12 { doc /* confirms that its clearance status agrees with the active switching record @S235 */ }
            perform action a13 { doc /* confirm that switching authority, equipment state, and communication limits are understood @S236 */ }
            perform action a14 { doc /* coordinating any automation-enabled action @S236 */ }
        }
        part timeDistribution : TimeDistribution {
            perform action a0 { doc /* supports consistent event timestamps across equipment that receives and applies the reference @S040 */ }
        }
        part timeQualityConcerns : TimeQualityConcerns;
        part timeQualityIndications : TimeQualityIndications {
            perform action a0 { doc /* allow operators to distinguish synchronized operation from degraded or unavailable timing @S045 */ }
        }
        part timestamps : Timestamps {
            perform action a0 { doc /* survive restoration @S118 */ }
        }
        part transformerProtectionPanel : TransformerProtectionPanel {
            perform action a0 { doc /* retains its protection authority independently of the bay switching sequence @S138 */ }
            perform action a1 { doc /* provides local indication of transformer protection operation for assessment during an alarm response @S161 */ }
            perform action a2 { doc /* applies its assigned protective logic @S188 */ }
            perform action a3 { doc /* reports abnormal protection conditions through its configured interface @S188 */ }
            perform action a4 { doc /* remain within its approved settings and operating constraints during handover @S244 */ }
        }
        part unexpectedIndications : UnexpectedIndications {
            perform action a0 { doc /* occur @S204 */ }
        }
        part unresolvedAlarmCondition : UnresolvedAlarmCondition {
            perform action a0 { doc /* requires a formal handoff @S168 */ }
        }
        part unresolvedCondition : UnresolvedCondition {
            exhibit state modes {
                state s0 { doc /* unresolved @S151 */ }
            }
        }
        part updates : Updates {
            perform action a0 { doc /* exceed configured age limits @S184 */ }
        }
        part work : Work {
            perform action a0 { doc /* could affect energized equipment @S077 */ }
            perform action a1 { doc /* work begins @S082 */ }
            perform action a2 { doc /* could affect protection, control, or service continuity @S094 */ }
        }
        part workArea : WorkArea {
            exhibit state modes {
                state s0 { doc /* safe state @S096 */ }
            }
        }
        part workPackage : WorkPackage {
            perform action a0 { doc /* affected by each work package @S199 */ }
        }
        flow f0 of ReferenceForTimeSynchronizationItem from satelliteTimeReceiver to alderCreekElectricalDistributionSubstation { doc /* @S017 */ }
        flow f1 of ControlPowerItem from stationDCSystem to automationAndProtectionEquipment { doc /* @S021 */ }
        flow f2 of SupervisoryCommunicationsItem from stationLevelFunctions to remoteOperationsInterfaces { doc /* @S029 */ }
        flow f3 of SupervisoryCommunicationsItem from remoteOperationsInterfaces to stationLevelFunctions { doc /* @S029 */ }
        flow f4 of DisplaysItem from stationSupervisoryControlSystem to controlRoomOperator { doc /* @S032 */ }
        flow f5 of ReferenceForTimeSynchronizationItem from supportedSatelliteTimingSignals to satelliteTimeReceiver { doc /* @S038 */ }
        flow f6 of TimeItem from satelliteTimeReceiver to stationEquipment { doc /* @S039 */ }
        flow f7 of ReferenceForTimeSynchronizationItem from satelliteTimeReceiver to equipment { doc /* @S040 */ }
        flow f8 of OperatingPowerItem from stationDCSystem to stationAutomationEquipment { doc /* @S046 */ }
        flow f9 of SwitchingRequestsItem from controlRoomOperator to switchingDeskCoordinator { doc /* @S125 */ }
        flow f10 of BayLevelStatusIndicationsItem from bayAutomationController to controlRoomOperator { doc /* @S155 */ }
        flow f11 of IndicationsFromTheNorthProtectionPanelItem from northProtectionPanel to controlRoomOperator { doc /* @S159 */ }
        flow f12 of AuthorizedStationTrafficItem from stationGateway to controlRoomAndBayNetworks { doc /* @S172 */ }
        flow f13 of AvailableControlsAndIndicationsItem from stationSupervisoryControlSystem to authorizedOperatingPersonnel { doc /* @S174 */ }
        flow f14 of StateChangingRequestsItem from controlRoomOperator to bayAutomationController { doc /* @S176 */ }
        flow f15 of BayLevelOutputsItem from bayAutomationController to breakerControlUnit { doc /* @S176 */ }
        flow f16 of AcceptedOutputCommandsItem from bayAutomationController to breakerControlUnit { doc /* @S177 */ }
        flow f17 of PositionAndCircuitHealthIndicationsItem from breakerControlUnit to bayAutomationController { doc /* @S177 */ }
        flow f19 of IndicationQualityItem from stationSupervisoryControlSystem to controlRoomOperator { doc /* @S181 */ }
        flow f20 of StaleDataStatusItem from stationSupervisoryControlSystem to controlRoomOperator { doc /* @S181 */ }
    }
    requirement def R0 { doc /* A controlled outage or other approved work window is required when implementation could affect feeder protection. @S068 */ subject s : Implementation; }
    requirement def R1 { doc /* Review queries should be bounded by station, equipment identifier, and time interval to keep results reproducible. @S111 */ subject s : ReviewQueries; }
    requirement def R2 { doc /* Equipment shared across the boundary requires explicit coordination before a switching action can affect either bay. @S134 */ subject s : EquipmentSharedAcrossTheBoundary; }
    requirement def R3 { doc /* Glasswing shall retain alarm state and event information for operator review after an indication has cleared. @S156 */ subject s : StationSupervisoryControlSystem; }
    requirement def R4 { doc /* The Bay Automation Controller shall execute only commands permitted by its approved logic and configured interlocks. @S223 */ subject s : BayAutomationController; }
    requirement def R5 { doc /* The Feeder Protection Relay shall retain its protective function independently of supervisory communications. @S224 */ subject s : FeederProtectionRelay; }
    requirement def R6 { doc /* The Engineering Workstation shall be used for authorized configuration work under established change control. @S228 */ subject s : EngineeringWorkstation; }
    requirement def R7 { doc /* time-quality concerns shall be investigated before records are relied upon for sequence analysis. @S229 */ subject s : TimeQualityConcerns; }
    requirement def R8 { doc /* The Station Gateway shall maintain the defined boundary between station automation and external communications. @S230 */ subject s : StationGateway; }
    requirement def R9 { doc /* The Station DC System shall be confirmed available before switching that depends on station control power. @S231 */ subject s : StationDCSystem; }
    requirement def R10 { doc /* The Breaker Control Unit shall reject commands that do not satisfy its configured permissive conditions. @S232 */ subject s : BreakerControlUnit; }
    requirement def R11 { doc /* Keystone shall confirm that switching authority, equipment state, and communication limits are understood before coordinating any automation-enabled action. @S236 */ subject s : SwitchingDeskCoordinator; }
    requirement def R12 { doc /* The Maintenance Remote Terminal shall use controlled access @S240 */ subject s : MaintenanceRemoteTerminal; }
    requirement def R13 { doc /* each maintenance session shall be attributable to an authorized user. @S240 */ subject s : MaintenanceSession; }
    requirement def R14 { doc /* The North Bay Controller shall be checked for expected local behavior after approved configuration work. @S241 */ subject s : NorthBayController; }
    requirement def R15 { doc /* The South Bay Controller shall be checked for expected local behavior after approved configuration work. @S242 */ subject s : SouthBayController; }
    requirement def R16 { doc /* The North Protection Panel shall remain available for independent protection functions during supervisory control interruptions. @S243 */ subject s : NorthProtectionPanel; }
    requirement def R17 { doc /* The Transformer Protection Panel shall remain within its approved settings and operating constraints during handover. @S244 */ subject s : TransformerProtectionPanel; }
    requirement def R18 { doc /* Periodic operational reviews shall examine command outcomes, event records, exceptions, and corrective actions so that automation decisions remain traceable and safe. @S245 */ subject s : PeriodicOperationalReviews; }
}
