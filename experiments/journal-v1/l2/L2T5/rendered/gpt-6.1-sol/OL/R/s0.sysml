package L2Model {
    item def AbnormalStartsItem { doc /* @S181 */ }
    item def AcceptanceConcernItem { doc /* @S120 */ }
    item def AlumBatchTicketItem { doc /* @S083 */ }
    item def AnalyticalStatusItem { doc /* @S195 */ }
    item def ChlorineCylinderSealLogItem { doc /* @S223 */ }
    item def ClearwellDiverEntryPermitItem { doc /* @S222 */ }
    item def ConfirmatoryResidualResultsItem { doc /* @S130 */ }
    item def FailuresItem { doc /* @S181,S220 */ }
    item def FilterRunExceptionNoteItem { doc /* @S153 */ }
    item def FirstIndicationOfSystemDemandChangesItem { doc /* @S176 */ }
    item def PressureZoneHandoffCardItem { doc /* @S243 */ }
    item def RakeTorqueSnapshotItem { doc /* @S105 */ }
    item def SampleChainSlipItem { doc /* @S188 */ }
    item def TimeItem { doc /* @S133 */ }
    item def UnusualResultsItem { doc /* @S018 */ }
    item def ValvePositionsItem { doc /* @S181 */ }
    part def AbnormalCondition { doc /* @S116 */ }
    part def AcceptanceConcern { doc /* @S120 */ }
    part def Advisory { doc /* @S166 */ }
    part def AlarmPriorities { doc /* @S209 */ }
    part def AlarmResponseExpectations { doc /* @S213 */ }
    part def AlarmShelving { doc /* @S211 */ }
    part def Alarms { doc /* @S175,S190 */ }
    part def AnalyticalInstruments { doc /* @S014 */ }
    part def AntivirusChanges { doc /* @S207 */ }
    part def AssociatedDrive { doc /* @S044 */ }
    part def AutomaticControl { doc /* @S149,S168 */ }
    part def BackupPower { doc /* @S214 */ }
    part def BackwashRecoveryOperation { doc /* @S150 */ }
    part def BackwashRecoveryTank { doc /* @S008,S151,S154 */ }
    part def Backwashes { doc /* @S074 */ }
    part def BankOfGravityFilters { doc /* @S059 */ }
    part def BriefOperationalReview { doc /* @S225 */ }
    part def CedarFallsMunicipalDrinkingWaterTreatmentPlantControlSystem { doc /* @S001,S002,S007 */ }
    part def Changes { doc /* @S075,S128 */ }
    part def ChemicalDeliveryCoordination { doc /* @S015 */ }
    part def ChemicalDemand { doc /* @S118 */ }
    part def ChemicalSupplierDriver { doc /* @S016,S112,S223,S246 */ }
    part def ChiefOperator { doc /* @S030,S038,S046,S051,S054,S058,S076,S078,S102,S124,S126,S138,S149,S153,S154,S164,S165,S173,S175,S184,S208,S218,S225,S235 */ }
    part def ChlorineContactBasin { doc /* @S008,S011,S232 */ }
    part def ChlorineFeedControls { doc /* @S126 */ }
    part def ChlorineResidualAlarm { doc /* @S025,S095,S119,S129,S194,S210 */ }
    part def ChlorineResidualAlarmTest { doc /* @S234 */ }
    part def CleaningMechanism { doc /* @S035 */ }
    part def ClearwellLevelController { doc /* @S008,S011,S074,S131,S134,S222,S232 */ }
    part def CoagulantDosingSkid { doc /* @S008,S009,S055,S056,S083,S158,S159,S160,S229 */ }
    part def Commissioning { doc /* @S226 */ }
    part def CommissioningTest { doc /* @S227 */ }
    part def Condition { doc /* @S155 */ }
    part def Conditions { doc /* @S029 */ }
    part def ContinuousImprovementActions { doc /* @S250 */ }
    part def ControlArchitecture { doc /* @S014 */ }
    part def ControlChanges { doc /* @S240 */ }
    part def ControlNetwork { doc /* @S206 */ }
    part def ControlOfCoagulationAndFiltration { doc /* @S053 */ }
    part def ControlRoom { doc /* @S129,S176,S186,S191,S192,S195 */ }
    part def ControlSystem { doc /* @S045,S134,S150,S181,S200 */ }
    part def Controlled { doc /* @S167 */ }
    part def ControlledDeliveryProcedures { doc /* @S016 */ }
    part def ControlledIntakeProcess { doc /* @S006 */ }
    part def ControlledSequence { doc /* @S226 */ }
    part def CoordinatedSetpoints { doc /* @S142 */ }
    part def CorrectiveActions { doc /* @S076 */ }
    part def Critical { doc /* @S168 */ }
    part def CriticalService { doc /* @S217 */ }
    part def CustomerComplaintTrends { doc /* @S190 */ }
    part def DebrisLoading { doc /* @S006,S029,S118 */ }
    part def DemandChanges { doc /* @S022 */ }
    part def Disabling { doc /* @S211 */ }
    part def DischargePressure { doc /* @S176 */ }
    part def DisinfectionControl { doc /* @S126 */ }
    part def DistributionDispatcher { doc /* @S022,S075,S144,S177,S182,S189,S193,S197,S220,S242,S243 */ }
    part def DistributionMonitoring { doc /* @S176 */ }
    part def DistributionReadiness { doc /* @S241 */ }
    part def DistributionStation { doc /* @S181,S182 */ }
    part def DistributionSystemCommunications { doc /* @S015 */ }
    part def DocumentedPathways { doc /* @S206 */ }
    part def DownstreamProcessDemand { doc /* @S028 */ }
    part def DownstreamPumpingDemand { doc /* @S170 */ }
    part def DutyEngineer { doc /* @S020,S048,S058,S092,S106,S146,S155,S185,S208,S219,S223,S228 */ }
    part def ElectricPowerService { doc /* @S015 */ }
    part def EmergencyOperatingCondition { doc /* @S217 */ }
    part def EngineeringChanges { doc /* @S020 */ }
    part def EngineeringPrivileges { doc /* @S202 */ }
    part def Equipment { doc /* @S026,S069,S124,S207 */ }
    part def EquipmentCondition { doc /* @S028 */ }
    part def EstablishedOperatingLimits { doc /* @S131 */ }
    part def Evidence { doc /* @S122 */ }
    part def ExcessiveParticulateCarryover { doc /* @S073 */ }
    part def Failures { doc /* @S220 */ }
    part def FeedbackFromMaintenanceWorkOrders { doc /* @S240 */ }
    part def FieldCrews { doc /* @S192 */ }
    part def FieldIndication { doc /* @S096 */ }
    part def FieldMeterReadings { doc /* @S087 */ }
    part def FieldObservations { doc /* @S030 */ }
    part def FieldSamples { doc /* @S080 */ }
    part def FieldVerification { doc /* @S191 */ }
    part def Filter { doc /* @S064 */ }
    part def FilterRun { doc /* @S061 */ }
    part def FilterShutdowns { doc /* @S074 */ }
    part def FiltrationPerformance { doc /* @S161 */ }
    part def FirmwareUpdates { doc /* @S207 */ }
    part def FunctionalTestReadings { doc /* @S122 */ }
    part def FunctionalTesting { doc /* @S229 */ }
    part def GrabSamples { doc /* @S095 */ }
    part def GravityFilters { doc /* @S059 */ }
    part def HeaderPressureControl { doc /* @S139 */ }
    part def HighClearwellLevelAlarms { doc /* @S133 */ }
    part def HighHighLevelCondition { doc /* @S036 */ }
    part def HighServicePump { doc /* @S141 */ }
    part def HighServicePumpHeader { doc /* @S049,S137,S140,S171,S230 */ }
    part def HighServicePumping { doc /* @S183 */ }
    part def ImmediateWaterQualityRisk { doc /* @S070 */ }
    part def IncomingWaterQuality { doc /* @S041 */ }
    part def InletRestrictions { doc /* @S006 */ }
    part def InstrumentResponseChecks { doc /* @S122 */ }
    part def InstrumentTrends { doc /* @S030 */ }
    part def IntakeLimitations { doc /* @S049 */ }
    part def LaboratoryAccounts { doc /* @S221 */ }
    part def LaboratoryConfirmation { doc /* @S096 */ }
    part def LaboratoryInformationHandling { doc /* @S015 */ }
    part def LaboratorySampleReceivingBench { doc /* @S085,S121,S187,S195 */ }
    part def LaboratorySampling { doc /* @S077 */ }
    part def LaboratoryTechnician { doc /* @S018,S039,S065,S081,S083,S084,S088,S093,S094,S100,S120,S130,S161,S162,S188,S221,S237 */ }
    part def LeadBoosterPump { doc /* @S180 */ }
    part def LevelIndications { doc /* @S126 */ }
    part def LocalControls { doc /* @S181,S220 */ }
    part def LocalInspectionResults { doc /* @S122 */ }
    part def LocalPanels { doc /* @S014 */ }
    part def LockoutPlanning { doc /* @S107 */ }
    part def LowClearwellLevelInterlocks { doc /* @S132 */ }
    part def Maintenance { doc /* @S117 */ }
    part def MaintenancePlanner { doc /* @S021,S052,S104,S105,S204,S222,S238,S239 */ }
    part def MajorExternalInterfaces { doc /* @S015 */ }
    part def NormalControlResponse { doc /* @S040 */ }
    part def NormalOperation { doc /* @S175 */ }
    part def NorthDistributionPressureStation { doc /* @S142,S244 */ }
    part def NorthFilterGallery { doc /* @S008,S059,S060,S150,S163,S186,S229 */ }
    part def OnlineAnalyzers { doc /* @S065 */ }
    part def OperatingNeeds { doc /* @S023 */ }
    part def OperatingStaff { doc /* @S064,S071 */ }
    part def OperationalBoundary { doc /* @S003 */ }
    part def Operations { doc /* @S018,S090,S119 */ }
    part def Operator { doc /* @S069,S113,S148,S151,S163 */ }
    part def OperatorAcceptanceComments { doc /* @S122 */ }
    part def OperatorPrivileges { doc /* @S202 */ }
    part def OperatorTraining { doc /* @S236 */ }
    part def OperatorWorkload { doc /* @S118 */ }
    part def OperatorWorkstations { doc /* @S014 */ }
    part def Operators { doc /* @S128,S133,S136,S145,S157,S162,S235 */ }
    part def OverflowConditions { doc /* @S133 */ }
    part def PendingStationInspections { doc /* @S190 */ }
    part def PeriodicPerformanceReviews { doc /* @S249 */ }
    part def Personnel { doc /* @S107 */ }
    part def PlannedChange { doc /* @S111 */ }
    part def PlannedDrill { doc /* @S233 */ }
    part def Plant { doc /* @S215,S226 */ }
    part def PlantPumpingDecisions { doc /* @S144 */ }
    part def PlantStaff { doc /* @S010,S031,S035 */ }
    part def PostMaintenanceTest { doc /* @S124 */ }
    part def PotableWater { doc /* @S001 */ }
    part def PressureZones { doc /* @S199 */ }
    part def ProcessAdjustments { doc /* @S018 */ }
    part def ProcessAndComplianceSamples { doc /* @S017 */ }
    part def ProcessCondition { doc /* @S025 */ }
    part def ProgrammableControllers { doc /* @S014 */ }
    part def Pump { doc /* @S043 */ }
    part def PumpCycling { doc /* @S051 */ }
    part def PumpOperation { doc /* @S132 */ }
    part def PumpSpeedChanges { doc /* @S139 */ }
    part def PumpStarts { doc /* @S139 */ }
    part def PumpStatus { doc /* @S176 */ }
    part def Rainfall { doc /* @S029 */ }
    part def RawAndSettledWaterMeasurements { doc /* @S098 */ }
    part def RawWaterQuality { doc /* @S051 */ }
    part def RawWaterQualityTrends { doc /* @S053 */ }
    part def RawWaterQualityTriggers { doc /* @S038 */ }
    part def RawWaterScreenChannel { doc /* @S006,S034,S035,S036,S105,S229 */ }
    part def RawWaterTurbidity { doc /* @S058 */ }
    part def Records { doc /* @S247 */ }
    part def RecordsRetention { doc /* @S248 */ }
    part def RecoveredWaterQuality { doc /* @S099,S175 */ }
    part def RecoveryWaterQuality { doc /* @S154 */ }
    part def RelatedInstrumentation { doc /* @S008 */ }
    part def ReliabilityTargets { doc /* @S224 */ }
    part def RemoteAccess { doc /* @S203 */ }
    part def ResidualConcentration { doc /* @S210 */ }
    part def ResidualContactTime { doc /* @S170 */ }
    part def ResidualInstruments { doc /* @S126 */ }
    part def ResidualsHandling { doc /* @S175 */ }
    part def ResidualsHauler { doc /* @S245 */ }
    part def ResidualsRemovalScheduling { doc /* @S015 */ }
    part def ReturnPath { doc /* @S154 */ }
    part def ReturnToServiceDecisions { doc /* @S074 */ }
    part def RinseToWasteQuality { doc /* @S063 */ }
    part def RiverConditions { doc /* @S007 */ }
    part def RiverIntakePumpStation { doc /* @S005,S027,S028,S029,S035,S109,S229 */ }
    part def RiverLevel { doc /* @S028,S051 */ }
    part def RiverRise { doc /* @S029 */ }
    part def RoutineOperation { doc /* @S026 */ }
    part def SCADAHistorianServer { doc /* @S013,S014,S047,S067,S086,S125,S147,S152,S188,S196,S205,S231 */ }
    part def SampleResults { doc /* @S122 */ }
    part def ScreenCondition { doc /* @S006 */ }
    part def ScreenDifferential { doc /* @S051 */ }
    part def SecurityPatches { doc /* @S207 */ }
    part def SharedCredentials { doc /* @S201 */ }
    part def ShiftCommunication { doc /* @S116 */ }
    part def ShiftHandoff { doc /* @S190 */ }
    part def SignificantDifferencesBetweenFieldReadingsAndLaboratoryValues { doc /* @S092 */ }
    part def Solids { doc /* @S151 */ }
    part def SolidsHandlingProblems { doc /* @S174 */ }
    part def SouthDistributionPressureStation { doc /* @S142,S180,S243 */ }
    part def SouthFilterGallery { doc /* @S008,S061,S150,S153,S164,S229 */ }
    part def StandingAlarms { doc /* @S212 */ }
    part def StatusOfOpenIsolations { doc /* @S116 */ }
    part def StorageLevel { doc /* @S050 */ }
    part def StorageStability { doc /* @S170 */ }
    part def StormIntakeMode { doc /* @S098,S233 */ }
    part def SupportingProcessQualityIndications { doc /* @S160 */ }
    part def Suppression { doc /* @S211 */ }
    part def SustainedLossOfCoagulationEffectiveness { doc /* @S072 */ }
    part def Task { doc /* @S119 */ }
    part def TelemetryRestoration { doc /* @S191 */ }
    part def TemporaryOperatingLimits { doc /* @S116,S190 */ }
    part def Testing { doc /* @S082 */ }
    part def TotalFlow { doc /* @S176 */ }
    part def TrainedStaff { doc /* @S026 */ }
    part def Transfer { doc /* @S114 */ }
    part def TreatmentScope { doc /* @S008 */ }
    part def TreatmentTargets { doc /* @S077 */ }
    part def Turbidity { doc /* @S040 */ }
    part def TurbidityTrend { doc /* @S063 */ }
    part def UnavailableEquipment { doc /* @S116 */ }
    part def UninterruptiblePowerSupplies { doc /* @S216 */ }
    part def Unnamed { doc /* @S118,S120,S121,S123,S124,S125,S126,S127,S129,S130,S132 */ }
    part def Upsets { doc /* @S165 */ }
    part def UpstreamRunoff { doc /* @S029 */ }
    part def ValveMovements { doc /* @S139 */ }
    part def WaterQualityConfirmation { doc /* @S121 */ }
    part def WetCommissioning { doc /* @S228 */ }
    part def WorkOrder { doc /* @S104,S124 */ }
    part def WorkOrderProcess { doc /* @S101 */ }
    part def Workaround { doc /* @S219 */ }
    part system {
        part abnormalCondition : AbnormalCondition {
            perform action a0 { doc /* could affect the next crew @S116 */ }
        }
        part acceptanceConcern : AcceptanceConcern {
            perform action a0 { doc /* could delay equipment return @S120 */ }
        }
        part advisory : Advisory;
        part alarmPriorities : AlarmPriorities {
            perform action a0 { doc /* reflect consequence, response time, operator action, and the risk of losing treatment, storage, or distribution capability @S209 */ }
        }
        part alarmResponseExpectations : AlarmResponseExpectations {
            perform action a0 { doc /* shall account for higher debris load, faster raw water quality changes, and increased dependence on intake screening and chemical dose verification @S213 */ }
        }
        part alarmShelving : AlarmShelving {
            perform action a0 { doc /* require a documented reason, a time limit, and review at the end of the operating shift @S211 */ }
        }
        part alarms : Alarms {
            perform action a0 { doc /* have cleared @S175 */ }
        }
        part analyticalInstruments : AnalyticalInstruments {
            perform action a0 { doc /* remain synchronized to plant time standards @S014 */ }
        }
        part antivirusChanges : AntivirusChanges;
        part associatedDrive : AssociatedDrive {
            perform action a0 { doc /* reports a fault @S044 */ }
        }
        part automaticControl : AutomaticControl {
            perform action a0 { doc /* cannot maintain the required operating envelope @S168 */ }
        }
        part backupPower : BackupPower {
            perform action a0 { doc /* shall support safe operation or controlled shutdown of the River Intake Pump Station, Raw Water Screen Channel, Chlorine Contact Basin, Clearwell Level Controller, SCADA Historian Server, High Service Pump Header, and essential control-room equipment @S214 */ }
        }
        part backwashRecoveryOperation : BackwashRecoveryOperation {
            perform action a0 { doc /* begins @S150 */ }
        }
        part backwashRecoveryTank : BackwashRecoveryTank {
            perform action a0 { doc /* receives spent washwater under controlled conditions @S151 */ }
            exhibit state modes {
                state s0 { doc /* settle-and-decant condition @S154 */ }
            }
        }
        part backwashes : Backwashes {
            perform action a0 { doc /* do not create avoidable storage swings @S074 */ }
        }
        part bankOfGravityFilters : BankOfGravityFilters;
        part briefOperationalReview : BriefOperationalReview {
            perform action a0 { doc /* identifies the cause, affected services, corrective actions, and any needed procedure changes @S225 */ }
        }
        part cedarFallsMunicipalDrinkingWaterTreatmentPlantControlSystem : CedarFallsMunicipalDrinkingWaterTreatmentPlantControlSystem {
            perform action a0 { doc /* support continuous production of potable water that meets regulatory requirements, utility operating targets, and customer demand @S001 */ }
            perform action a1 { doc /* give operators timely visibility, dependable automatic control, and clear manual intervention points for the intake, treatment, laboratory, and distribution functions @S002 */ }
            exhibit state modes {
                state s0 { doc /* Storm Intake Mode @S007 */ }
            }
        }
        part changes : Changes {
            perform action a0 { doc /* affect the High Service Pump Header @S075 */ }
            perform action a1 { doc /* do not outrun mixing and contact time through the Chlorine Contact Basin @S128 */ }
        }
        part chemicalDeliveryCoordination : ChemicalDeliveryCoordination;
        part chemicalDemand : ChemicalDemand {
            perform action a0 { doc /* may change quickly @S118 */ }
        }
        part chemicalSupplierDriver : ChemicalSupplierDriver {
            perform action a0 { doc /* interacts with the plant through controlled delivery procedures @S016 */ }
            perform action a1 { doc /* sends the Chlorine Cylinder Seal Log @S112 */ }
            perform action a2 { doc /* unloading any replacement cylinders at the plant @S112 */ }
            perform action a3 { doc /* shall follow site access, unloading, verification, and communication procedures established during commissioning and confirmed during training @S246 */ }
        }
        part chiefOperator : ChiefOperator {
            perform action a0 { doc /* authorizes entry into Storm Intake Mode @S030 */ }
            perform action a1 { doc /* determines whether to adjust pumping rate, request additional laboratory testing, or increase downstream process monitoring @S038 */ }
            perform action a2 { doc /* adjust pumping rate @S038 */ }
            perform action a3 { doc /* request additional laboratory testing @S038 */ }
            perform action a4 { doc /* increase downstream process monitoring @S038 */ }
            perform action a5 { doc /* may authorize temporary manual operation only when the cause is understood, the equipment can be observed, and the risk to treatment continuity is acceptable @S046 */ }
            perform action a6 { doc /* accepted by the Chief Operator @S051 */ }
            perform action a7 { doc /* establishes the starting coagulant dose from recent turbidity, color, alkalinity, pH, temperature, and bench-scale treatment observations @S054 */ }
            perform action a8 { doc /* confirms the sustained control point @S058 */ }
            perform action a9 { doc /* reviews trends from the affected operating period @S076 */ }
            perform action a10 { doc /* confirms that corrective actions restored stable clarified and filtered water quality @S076 */ }
            perform action a11 { doc /* establishes daily sampling priorities based on plant conditions, regulatory monitoring requirements, and recent process adjustments @S078 */ }
            perform action a12 { doc /* reviews the next-day schedule with operations staff @S102 */ }
            perform action a13 { doc /* determines whether the equipment remains isolated or can be operated under restriction @S124 */ }
            perform action a14 { doc /* confirms that the chlorine feed controls, residual instruments, and level indications are responding consistently in the SCADA Historian Server @S126 */ }
            perform action a15 { doc /* entered by the Chief Operator @S138 */ }
            perform action a16 { doc /* set by the Chief Operator @S149 */ }
            perform action a17 { doc /* uses the Filter Run Exception Note @S153 */ }
            perform action a18 { doc /* determine whether a shortened run, high headloss, or abnormal turbidity response requires follow-up before the next wash sequence @S153 */ }
            perform action a19 { doc /* holds the return path out of service @S154 */ }
            perform action a20 { doc /* keeps the Backwash Recovery Tank in a settle-and-decant condition @S154 */ }
            perform action a21 { doc /* approves return to service @S164 */ }
            perform action a22 { doc /* classifies upsets as advisory, controlled, or critical based on finished water risk, remaining treatment capacity, alarm persistence, and distribution service impact @S165 */ }
            perform action a23 { doc /* produces the Backwash Solids Manifest @S173 */ }
            perform action a24 { doc /* confirms that the upset classification can be closed @S175 */ }
            perform action a25 { doc /* may direct a conservative pumping posture during unusual demand, main repair activity, or recovery from a treatment upset @S184 */ }
            perform action a26 { doc /* owns alarm governance for process alarms @S208 */ }
            perform action a27 { doc /* has authority to direct emergency operating priorities when treatment, storage, distribution pressure, or personnel safety is at risk @S218 */ }
            perform action a28 { doc /* shall require a brief operational review that identifies the cause, affected services, corrective actions, and any needed procedure changes @S225 */ }
            perform action a29 { doc /* coordinate training @S235 */ }
        }
        part chlorineContactBasin : ChlorineContactBasin {
            perform action a0 { doc /* provide the principal control points for disinfection contact management and finished-water storage coordination @S011 */ }
        }
        part chlorineFeedControls : ChlorineFeedControls {
            perform action a0 { doc /* are responding consistently in the SCADA Historian Server @S126 */ }
        }
        part chlorineResidualAlarm : ChlorineResidualAlarm {
            perform action a0 { doc /* may indicate a public-health risk, an analyzer fault, or a process condition requiring immediate operator assessment @S025 */ }
            perform action a1 { doc /* causes the affected task to pause until operations confirms whether the alarm is process-related or maintenance-induced @S119 */ }
            perform action a2 { doc /* occurs @S129 */ }
            perform action a3 { doc /* remain configured as a high-priority condition when residual concentration indicates a potential treatment compliance or public health concern @S210 */ }
            exhibit state modes {
                state s0 { doc /* active @S095,S194 */ }
                state s1 { doc /* high-priority condition @S210 */ }
            }
        }
        part chlorineResidualAlarmTest : ChlorineResidualAlarmTest {
            perform action a0 { doc /* verify annunciation, operator response guidance, acknowledgement behavior, and escalation to the appropriate duty staff @S234 */ }
        }
        part cleaningMechanism : CleaningMechanism {
            perform action a0 { doc /* is running @S035 */ }
        }
        part clearwellLevelController : ClearwellLevelController {
            perform action a0 { doc /* provide the principal control points for disinfection contact management and finished-water storage coordination @S011 */ }
            perform action a1 { doc /* remains coordinated with filter production @S074 */ }
            perform action a2 { doc /* maintains normal storage within established operating limits that protect disinfectant contact, reserve volume, and high-service pump suction conditions @S131 */ }
            perform action a3 { doc /* sends the Clearwell Diver Entry Permit @S134 */ }
        }
        part coagulantDosingSkid : CoagulantDosingSkid {
            perform action a0 { doc /* supports chemical feed control based on approved setpoints, observed raw-water conditions, and operator direction @S009 */ }
            perform action a1 { doc /* meters the primary coagulant under automatic control during routine operation @S055 */ }
            perform action a2 { doc /* sends the Alum Batch Ticket @S056 */ }
            perform action a3 { doc /* adjusts feed response only within approved operating limits @S158 */ }
            perform action a4 { doc /* does not substitute automatic changes for required operator review during a significant upset @S158 */ }
            perform action a5 { doc /* uses the set @S159 */ }
            perform action a6 { doc /* confirm the selected dose response during an event with rapidly changing raw water quality @S159 */ }
            perform action a7 { doc /* hold the last operator-approved dose @S160 */ }
            perform action a8 { doc /* respond correctly to local and supervisory commands @S229 */ }
            exhibit state modes {
                state s0 { doc /* Routine operation @S055 */ }
            }
        }
        part commissioning : Commissioning;
        part commissioningTest : CommissioningTest {
            perform action a0 { doc /* shall have defined starting conditions, expected responses, acceptance limits, and a responsible reviewer @S227 */ }
        }
        part condition : Condition {
            exhibit state modes {
                state s0 { doc /* chemical @S155 */ }
                state s1 { doc /* hydraulic @S155 */ }
                state s2 { doc /* instrumentation related @S155 */ }
            }
        }
        part conditions : Conditions {
            perform action a0 { doc /* require closer supervision of the intake @S029 */ }
        }
        part continuousImprovementActions : ContinuousImprovementActions;
        part controlArchitecture : ControlArchitecture {
            perform action a0 { doc /* assumes that programmable controllers, local panels, operator workstations, analytical instruments, and the SCADA Historian Server remain synchronized to plant time standards @S014 */ }
        }
        part controlChanges : ControlChanges {
            perform action a0 { doc /* do not mask equipment degradation @S240 */ }
            perform action a1 { doc /* create avoidable field effort @S240 */ }
        }
        part controlNetwork : ControlNetwork;
        part controlOfCoagulationAndFiltration : ControlOfCoagulationAndFiltration {
            perform action a0 { doc /* returns to normal @S053 */ }
            exhibit state modes {
                state s0 { doc /* normal @S053 */ }
            }
        }
        part controlRoom : ControlRoom {
            perform action a0 { doc /* verifies analyzer sample flow @S129 */ }
            perform action a1 { doc /* compares the reading with a grab sample result @S129 */ }
            perform action a2 { doc /* holds any planned production increase until the condition is understood @S129 */ }
            perform action a3 { doc /* treats increased distribution demand as available finished-water capacity @S186 */ }
            perform action a4 { doc /* assumes the last confirmed operating mode remains in effect until field verification or telemetry restoration proves otherwise @S191 */ }
            perform action a5 { doc /* uses that status @S195 */ }
            perform action a6 { doc /* interpret pressure-zone complaints involving taste, odor, or disinfectant concerns @S195 */ }
        }
        part controlSystem : ControlSystem {
            perform action a0 { doc /* alarms the condition @S045 */ }
            perform action a1 { doc /* stops the affected pump according to the severity of the signal @S045 */ }
            perform action a2 { doc /* have been verified by the control system @S134 */ }
            perform action a3 { doc /* confirms that turbidity, valve position, and flow indications are within the expected recovery range @S150 */ }
            perform action a4 { doc /* use role-based access control with named accounts for operators, engineering users, maintenance users, and read-only review users @S200 */ }
        }
        part controlled : Controlled;
        part controlledDeliveryProcedures : ControlledDeliveryProcedures {
            perform action a0 { doc /* allow chemical inventory changes to be checked before operating setpoints are affected @S016 */ }
        }
        part controlledIntakeProcess : ControlledIntakeProcess;
        part controlledSequence : ControlledSequence {
            perform action a0 { doc /* proves each control function @S226 */ }
        }
        part coordinatedSetpoints : CoordinatedSetpoints {
            perform action a0 { doc /* reflect system demand and storage conditions @S142 */ }
        }
        part correctiveActions : CorrectiveActions {
            perform action a0 { doc /* restored stable clarified and filtered water quality @S076 */ }
        }
        part critical : Critical;
        part criticalService : CriticalService {
            exhibit state modes {
                state s0 { doc /* emergency operating condition @S217 */ }
            }
        }
        part customerComplaintTrends : CustomerComplaintTrends {
            perform action a0 { doc /* may affect dispatch decisions @S190 */ }
        }
        part debrisLoading : DebrisLoading {
            perform action a0 { doc /* directly affect downstream stability @S006 */ }
            perform action a1 { doc /* creates conditions that require closer supervision of the intake @S029 */ }
            perform action a2 { doc /* may change quickly @S118 */ }
        }
        part demandChanges : DemandChanges {
            perform action a0 { doc /* may affect pumping and storage strategy @S022 */ }
        }
        part disabling : Disabling {
            perform action a0 { doc /* require a documented reason, a time limit, and review at the end of the operating shift @S211 */ }
        }
        part dischargePressure : DischargePressure {
            perform action a0 { doc /* provide the control room with the first indication of system demand changes @S176 */ }
        }
        part disinfectionControl : DisinfectionControl {
            exhibit state modes {
                state s0 { doc /* normal service @S126 */ }
            }
        }
        part distributionDispatcher : DistributionDispatcher {
            perform action a0 { doc /* coordinates finished-water delivery expectations with the plant @S022 */ }
            perform action a1 { doc /* communicates demand changes that may affect pumping and storage strategy @S022 */ }
            perform action a2 { doc /* communicates expected demand changes, main break impacts, and pressure complaints @S144 */ }
            perform action a3 { doc /* watches each pressure zone for sustained deviations @S177 */ }
            perform action a4 { doc /* reacting to every short pressure fluctuation caused by hydrant use, valve movement, or customer demand changes @S177 */ }
            perform action a5 { doc /* records the reason, the expected duration, and the field contact responsible for the change @S182 */ }
            perform action a6 { doc /* sends the Pressure Zone Handoff Card @S189 */ }
            perform action a7 { doc /* verifying current pressure-zone setpoints, active alarms, and open field work @S189 */ }
            perform action a8 { doc /* coordinates planned hydrant flushing, valve exercising, and main isolation work with pumping schedules @S193 */ }
            perform action a9 { doc /* limit avoidable pressure swings @S193 */ }
            perform action a10 { doc /* avoids unnecessary zone changes unless demand, storage, or public-safety conditions require action @S197 */ }
            perform action a11 { doc /* confirm that distribution readiness messages are acknowledged before any planned change in pressure zone operating status @S242 */ }
        }
        part distributionMonitoring : DistributionMonitoring {
            perform action a0 { doc /* begins at the High Service Pump Header @S176 */ }
        }
        part distributionReadiness : DistributionReadiness;
        part distributionStation : DistributionStation {
            exhibit state modes {
                state s0 { doc /* Manual operation @S182 */ }
                state s1 { doc /* automatic operation @S181 */ }
                state s2 { doc /* local operation @S182 */ }
            }
        }
        part distributionSystemCommunications : DistributionSystemCommunications;
        part documentedPathways : DocumentedPathways;
        part downstreamProcessDemand : DownstreamProcessDemand {
            perform action a0 { doc /* does not support full intake operation @S028 */ }
        }
        part downstreamPumpingDemand : DownstreamPumpingDemand {
            perform action a0 { doc /* remain aligned @S170 */ }
        }
        part dutyEngineer : DutyEngineer {
            perform action a0 { doc /* supports configuration control @S020 */ }
            perform action a1 { doc /* evaluates control-system problems @S020 */ }
            perform action a2 { doc /* approves engineering changes that affect operating behavior or documented boundaries @S020 */ }
            perform action a3 { doc /* reviews storm forecasts and river-stage information @S048 */ }
            perform action a4 { doc /* may authorize a temporary dose adjustment @S058 */ }
            perform action a5 { doc /* reviews significant differences between field readings and laboratory values @S092 */ }
            perform action a6 { doc /* checks proposed work against current operating constraints @S106 */ }
            perform action a7 { doc /* may defer nonessential activity when treatment margin is limited @S106 */ }
            perform action a8 { doc /* review the operating condition @S146 */ }
            perform action a9 { doc /* reviews repeated abnormal wash recovery trends @S155 */ }
            perform action a10 { doc /* determine whether the condition is hydraulic, chemical, instrumentation related, or caused by rapid source water change @S155 */ }
            perform action a11 { doc /* reviews persistent low-pressure complaints, repeated station alarms, or mismatches between observed pressure and modeled expectations @S185 */ }
            perform action a12 { doc /* supports alarm limit review when control changes or recurring nuisance alarms are identified @S208 */ }
            perform action a13 { doc /* may authorize temporary control workarounds during an emergency @S219 */ }
            perform action a14 { doc /* reviews the Chlorine Cylinder Seal Log @S223 */ }
            perform action a15 { doc /* accepting a change in chlorine storage status @S223 */ }
            perform action a16 { doc /* shall confirm that temporary controls, bypasses, and manual operating instructions are understood by the affected staff @S228 */ }
        }
        part electricPowerService : ElectricPowerService;
        part emergencyOperatingCondition : EmergencyOperatingCondition {
            perform action a0 { doc /* requiring immediate notification of the Chief Operator and Duty Engineer @S217 */ }
        }
        part engineeringChanges : EngineeringChanges {
            perform action a0 { doc /* affect operating behavior or documented boundaries @S020 */ }
        }
        part engineeringPrivileges : EngineeringPrivileges {
            perform action a0 { doc /* require separate approval before setpoints, control logic, alarm limits, or historian configuration are changed @S202 */ }
        }
        part equipment : Equipment {
            perform action a0 { doc /* affects water production or distribution pressure @S207 */ }
            exhibit state modes {
                state s0 { doc /* isolated @S124 */ }
                state s1 { doc /* manual control @S069 */ }
                state s2 { doc /* safe manual operation @S026 */ }
                state s3 { doc /* under restriction @S124 */ }
            }
        }
        part equipmentCondition : EquipmentCondition {
            perform action a0 { doc /* does not support full intake operation @S028 */ }
        }
        part establishedOperatingLimits : EstablishedOperatingLimits {
            perform action a0 { doc /* protect disinfectant contact, reserve volume, and high-service pump suction conditions @S131 */ }
        }
        part evidence : Evidence;
        part excessiveParticulateCarryover : ExcessiveParticulateCarryover {
            perform action a0 { doc /* can affect downstream disinfectant demand and contact performance @S073 */ }
        }
        part failures : Failures {
            perform action a0 { doc /* may affect pressure zones or fire-flow readiness @S220 */ }
        }
        part feedbackFromMaintenanceWorkOrders : FeedbackFromMaintenanceWorkOrders;
        part fieldCrews : FieldCrews {
            perform action a0 { doc /* notify the control room @S192 */ }
            perform action a1 { doc /* opening major distribution valves @S192 */ }
            perform action a2 { doc /* closing major distribution valves @S192 */ }
        }
        part fieldIndication : FieldIndication {
            perform action a0 { doc /* caused an operating adjustment @S096 */ }
        }
        part fieldMeterReadings : FieldMeterReadings {
            exhibit state modes {
                state s0 { doc /* provisional @S087 */ }
            }
        }
        part fieldObservations : FieldObservations {
            perform action a0 { doc /* show that normal assumptions are no longer reliable @S030 */ }
        }
        part fieldSamples : FieldSamples {
            perform action a0 { doc /* leave operating areas @S080 */ }
        }
        part fieldVerification : FieldVerification {
            perform action a0 { doc /* proves otherwise @S191 */ }
        }
        part filter : Filter {
            perform action a0 { doc /* shows an unusual turbidity rise @S064 */ }
        }
        part filterRun : FilterRun {
            perform action a0 { doc /* ends outside the normal operating limits @S061 */ }
        }
        part filterShutdowns : FilterShutdowns {
            perform action a0 { doc /* do not create avoidable storage swings @S074 */ }
        }
        part filtrationPerformance : FiltrationPerformance {
            perform action a0 { doc /* changes during a storm-driven event @S161 */ }
        }
        part firmwareUpdates : FirmwareUpdates;
        part functionalTestReadings : FunctionalTestReadings;
        part functionalTesting : FunctionalTesting {
            perform action a0 { doc /* verify that the River Intake Pump Station, Raw Water Screen Channel, North Filter Gallery, South Filter Gallery, and Coagulant Dosing Skid respond correctly to local and supervisory commands @S229 */ }
        }
        part grabSamples : GrabSamples {
            perform action a0 { doc /* receive priority handling @S095 */ }
        }
        part gravityFilters : GravityFilters;
        part headerPressureControl : HeaderPressureControl {
            perform action a0 { doc /* uses a paced response @S139 */ }
        }
        part highClearwellLevelAlarms : HighClearwellLevelAlarms {
            perform action a0 { doc /* give operators time to reduce production or adjust downstream pumping before overflow conditions develop @S133 */ }
        }
        part highHighLevelCondition : HighHighLevelCondition {
            perform action a0 { doc /* requires immediate field confirmation @S036 */ }
            perform action a1 { doc /* may indicate restricted passage, failed cleaning, or abnormal river backwater @S036 */ }
        }
        part highServicePump : HighServicePump {
            perform action a0 { doc /* trips @S141 */ }
        }
        part highServicePumpHeader : HighServicePumpHeader {
            perform action a0 { doc /* meet planned system demand @S049 */ }
            perform action a1 { doc /* sequences available pumps @S137 */ }
            perform action a2 { doc /* meet distribution demand @S137 */ }
            perform action a3 { doc /* avoiding unnecessary starts, short cycling, and operation near unstable portions of the pump curves @S137 */ }
            perform action a4 { doc /* produces the Pump Bearing Vibration Clip @S140 */ }
            perform action a5 { doc /* maintain stable delivery @S171 */ }
            perform action a6 { doc /* demonstrate stable pressure control through startup, lead-lag transfer, and controlled shutdown @S230 */ }
            exhibit state modes {
                state s0 { doc /* controlled shutdown @S230 */ }
                state s1 { doc /* startup @S230 */ }
            }
        }
        part highServicePumping : HighServicePumping {
            perform action a0 { doc /* does not create avoidable level instability @S183 */ }
        }
        part immediateWaterQualityRisk : ImmediateWaterQualityRisk {
            perform action a0 { doc /* requires a larger correction approved by the Chief Operator @S070 */ }
        }
        part incomingWaterQuality : IncomingWaterQuality {
            perform action a0 { doc /* shorten filter run time @S041 */ }
            perform action a1 { doc /* increase solids loading @S041 */ }
        }
        part inletRestrictions : InletRestrictions {
            perform action a0 { doc /* directly affect downstream stability @S006 */ }
        }
        part instrumentResponseChecks : InstrumentResponseChecks;
        part instrumentTrends : InstrumentTrends {
            perform action a0 { doc /* show that normal assumptions are no longer reliable @S030 */ }
        }
        part intakeLimitations : IntakeLimitations {
            perform action a0 { doc /* could reduce the ability of the High Service Pump Header to meet planned system demand @S049 */ }
        }
        part laboratoryAccounts : LaboratoryAccounts {
            perform action a0 { doc /* shall not allow control actions on plant equipment @S221 */ }
        }
        part laboratoryConfirmation : LaboratoryConfirmation {
            perform action a0 { doc /* does not support the field indication that caused an operating adjustment @S096 */ }
        }
        part laboratoryInformationHandling : LaboratoryInformationHandling;
        part laboratorySampleReceivingBench : LaboratorySampleReceivingBench {
            perform action a0 { doc /* sends the Jar Test Photograph Set @S085 */ }
            perform action a1 { doc /* records incoming distribution check samples with the pressure zone, collection point, and time needed for control-room review @S187 */ }
            perform action a2 { doc /* provides analytical status through normal plant reporting channels @S195 */ }
            exhibit state modes {
                state s0 { doc /* available @S121 */ }
            }
        }
        part laboratorySampling : LaboratorySampling {
            perform action a0 { doc /* provides independent confirmation that treatment targets have returned to acceptable control ranges @S077 */ }
        }
        part laboratoryTechnician : LaboratoryTechnician {
            perform action a0 { doc /* provides analytical confirmation @S018 */ }
            perform action a1 { doc /* communicates unusual results to operations @S018 */ }
            perform action a2 { doc /* helps determine whether process adjustments require additional verification @S018 */ }
            perform action a3 { doc /* supports intake decisions @S039 */ }
            perform action a4 { doc /* prioritizing raw-water checks @S039 */ }
            perform action a5 { doc /* provides confirmation testing @S065 */ }
            perform action a6 { doc /* checks container type, holding time, temperature, preservative status, and seal condition @S081 */ }
            perform action a7 { doc /* logging a sample for analysis @S081 */ }
            perform action a8 { doc /* uses the Alum Batch Ticket @S083 */ }
            perform action a9 { doc /* verify chemical lot identity @S083 */ }
            perform action a10 { doc /* recording related laboratory observations @S083 */ }
            perform action a11 { doc /* prepares the Sample Chain Slip @S084 */ }
            perform action a12 { doc /* sends the Sample Chain Slip @S084 */ }
            perform action a13 { doc /* verifying that custody entries are complete and legible @S084 */ }
            perform action a14 { doc /* records any mismatch between bottle labels, bench log entries, and operator notes @S088 */ }
            perform action a15 { doc /* assigning an acceptance status to the sample @S088 */ }
            perform action a16 { doc /* confirms that sample mixing, settling time, and instrument range are appropriate for the expected raw or filtered water condition @S093 */ }
            perform action a17 { doc /* confirms reagent condition, sample contact time, and measurement timing @S094 */ }
            perform action a18 { doc /* accepting the result @S094 */ }
            perform action a19 { doc /* preserves all custody and acceptance records for review by the Chief Operator, Duty Engineer, and regulatory auditors @S100 */ }
            perform action a20 { doc /* supports work control by confirming sampling needs and by reporting any acceptance concern that could delay equipment return @S120 */ }
            perform action a21 { doc /* confirming sampling needs @S120 */ }
            perform action a22 { doc /* reporting any acceptance concern that could delay equipment return @S120 */ }
            perform action a23 { doc /* provides confirmatory residual results @S130 */ }
            perform action a24 { doc /* prioritizes turbidity, apparent color, alkalinity, and disinfectant residual checks @S161 */ }
            perform action a25 { doc /* shall retain access needed for sample status review and reporting @S221 */ }
        }
        part leadBoosterPump : LeadBoosterPump;
        part levelIndications : LevelIndications {
            perform action a0 { doc /* are responding consistently in the SCADA Historian Server @S126 */ }
        }
        part localControls : LocalControls {
            perform action a0 { doc /* sequence pumps within approved limits @S181 */ }
            perform action a1 { doc /* report abnormal starts, failures, or valve positions to the control system @S181 */ }
        }
        part localInspectionResults : LocalInspectionResults;
        part localPanels : LocalPanels {
            perform action a0 { doc /* remain synchronized to plant time standards @S014 */ }
        }
        part lockoutPlanning : LockoutPlanning {
            perform action a0 { doc /* identifies electrical, hydraulic, pneumatic, chemical, and stored-energy hazards @S107 */ }
        }
        part lowClearwellLevelInterlocks : LowClearwellLevelInterlocks {
            perform action a0 { doc /* prevent pump operation from drawing the storage volume below the minimum level needed for safe hydraulic operation @S132 */ }
        }
        part maintenance : Maintenance {
            perform action a0 { doc /* changes the availability of the High Service Pump Header, North Distribution Pressure Station, or South Distribution Pressure Station @S117 */ }
        }
        part maintenancePlanner : MaintenancePlanner {
            perform action a0 { doc /* converts equipment condition information into planned work @S021 */ }
            perform action a1 { doc /* coordinating with operations @S021 */ }
            perform action a2 { doc /* avoid unnecessary treatment or distribution risk @S021 */ }
            perform action a3 { doc /* reviews intake equipment condition @S052 */ }
            perform action a4 { doc /* schedules cleaning or inspection work needed to restore reliable operation @S052 */ }
            perform action a5 { doc /* verifies that each work order identifies affected equipment, required isolations, parts staging, and the evidence needed to close the work @S104 */ }
            perform action a6 { doc /* uses the snapshot to compare planned rake work against recent mechanical loading @S105 */ }
            perform action a7 { doc /* compare planned rake work against recent mechanical loading @S105 */ }
            perform action a8 { doc /* releasing the task package @S105 */ }
            perform action a9 { doc /* maintains the weekly access review for maintenance accounts @S204 */ }
            perform action a10 { doc /* disables privileges after reassignment @S204 */ }
            perform action a11 { doc /* uses the permit to verify isolation boundaries before confined-space work is released @S222 */ }
            perform action a12 { doc /* verify isolation boundaries @S222 */ }
            perform action a13 { doc /* review commissioning defects, recurring nuisance alarms, calibration drift, and equipment access problems @S238 */ }
            perform action a14 { doc /* use the clip @S239 */ }
            perform action a15 { doc /* compare observed pump condition with planned inspection intervals and corrective work priorities @S239 */ }
        }
        part majorExternalInterfaces : MajorExternalInterfaces;
        part normalControlResponse : NormalControlResponse {
            perform action a0 { doc /* can stabilize @S040 */ }
        }
        part normalOperation : NormalOperation {
            perform action a0 { doc /* resumes @S175 */ }
        }
        part northDistributionPressureStation : NorthDistributionPressureStation {
            perform action a0 { doc /* receive pressure support through coordinated setpoints that reflect system demand and storage conditions @S142 */ }
        }
        part northFilterGallery : NorthFilterGallery {
            perform action a0 { doc /* records individual filter effluent turbidity and headloss at the end of each control scan @S060 */ }
            perform action a1 { doc /* completes a backwash cycle @S150 */ }
            perform action a2 { doc /* shows rapid headloss growth after a verified chemical adjustment @S163 */ }
            perform action a3 { doc /* provide a reliable filter service status indication @S186 */ }
            perform action a4 { doc /* respond correctly to local and supervisory commands @S229 */ }
        }
        part onlineAnalyzers : OnlineAnalyzers {
            perform action a0 { doc /* disagree with observed filter performance or with routine process samples @S065 */ }
        }
        part operatingNeeds : OperatingNeeds {
            perform action a0 { doc /* influence finished-water pumping decisions @S023 */ }
        }
        part operatingStaff : OperatingStaff {
            perform action a0 { doc /* compare the analyzer trend with nearby sample results @S064 */ }
            perform action a1 { doc /* declaring a process upset @S064 */ }
            perform action a2 { doc /* hold the last verified safe dose @S071 */ }
            perform action a3 { doc /* revert to an approved fixed dose @S071 */ }
            perform action a4 { doc /* collecting additional grab samples @S071 */ }
        }
        part operationalBoundary : OperationalBoundary {
            perform action a0 { doc /* begins at the River Intake Pump Station and Raw Water Screen Channel @S003 */ }
            perform action a1 { doc /* extends through treatment, disinfection, finished-water storage control, and discharge to the High Service Pump Header @S003 */ }
        }
        part operations : Operations {
            perform action a0 { doc /* confirms whether the alarm is process-related or maintenance-induced @S119 */ }
        }
        part operator : Operator {
            perform action a0 { doc /* placing equipment in manual control @S069 */ }
            perform action a1 { doc /* state the reason @S069 */ }
            perform action a2 { doc /* monitor the affected process variable closely @S069 */ }
            perform action a3 { doc /* restore automatic control as soon as practicable @S069 */ }
            perform action a4 { doc /* observe chemical connections and vehicle movement @S113 */ }
            perform action a5 { doc /* can maintain residual targets, clearwell limits, and distribution pressure with direct observation of the affected indications @S148 */ }
            perform action a6 { doc /* has verified acceptable clarity @S151 */ }
            perform action a7 { doc /* may stagger wash timing @S163 */ }
            perform action a8 { doc /* avoid simultaneous recovery surges @S163 */ }
        }
        part operatorAcceptanceComments : OperatorAcceptanceComments;
        part operatorPrivileges : OperatorPrivileges;
        part operatorTraining : OperatorTraining {
            perform action a0 { doc /* include classroom review, simulator or dry-run practice where practical, field walkdowns, and supervised operation during early service @S236 */ }
        }
        part operatorWorkload : OperatorWorkload {
            perform action a0 { doc /* may change quickly @S118 */ }
        }
        part operatorWorkstations : OperatorWorkstations {
            perform action a0 { doc /* remain synchronized to plant time standards @S014 */ }
        }
        part operators : Operators {
            perform action a0 { doc /* adjust chlorine feed gradually @S128 */ }
            perform action a1 { doc /* reduce production @S133 */ }
            perform action a2 { doc /* adjust downstream pumping @S133 */ }
            perform action a3 { doc /* need a short confirmation name @S136 */ }
            perform action a4 { doc /* watch the relationship between raw water quality, filter loading, disinfectant demand, and high-service pumping @S145 */ }
            perform action a5 { doc /* avoid forcing production beyond treatment capability @S145 */ }
            perform action a6 { doc /* monitor influent turbidity, screen differential level, coagulant demand, and filter headloss more frequently than during normal raw water conditions @S157 */ }
            perform action a7 { doc /* make a sustained change to coagulation or filter loading strategy @S162 */ }
            perform action a8 { doc /* understand the control concept, normal sequencing, manual fallback methods, and alarm response expectations @S235 */ }
        }
        part overflowConditions : OverflowConditions {
            perform action a0 { doc /* develop @S133 */ }
        }
        part pendingStationInspections : PendingStationInspections;
        part periodicPerformanceReviews : PeriodicPerformanceReviews {
            perform action a0 { doc /* shall compare actual plant operation with the control concept, including alarm burden, manual interventions, water quality stability, chemical use, and energy use @S249 */ }
        }
        part personnel : Personnel {
            perform action a0 { doc /* enter @S107 */ }
            perform action a1 { doc /* service plant equipment @S107 */ }
        }
        part plannedChange : PlannedChange {
            perform action a0 { doc /* affecting the Clearwell Level Controller @S111 */ }
            perform action a1 { doc /* requires coordination with the High Service Pump Header operating plan @S111 */ }
        }
        part plannedDrill : PlannedDrill {
            perform action a0 { doc /* confirms operator prompts, intake constraints, and return-to-normal steps @S233 */ }
        }
        part plant : Plant {
            perform action a0 { doc /* shall maintain written expectations for generator start time, automatic transfer performance, fuel availability, and operator checks during extended utility outages @S215 */ }
            perform action a1 { doc /* relies on it for normal service @S226 */ }
            exhibit state modes {
                state s0 { doc /* normal service @S226 */ }
            }
        }
        part plantPumpingDecisions : PlantPumpingDecisions {
            perform action a0 { doc /* match field conditions @S144 */ }
        }
        part plantStaff : PlantStaff {
            perform action a0 { doc /* increase observation of river level, screen loading, turbidity, and pump cycling frequency @S031 */ }
            perform action a1 { doc /* verify that the cleaning mechanism is running and that the River Intake Pump Station is not drawing the channel down too quickly @S035 */ }
        }
        part postMaintenanceTest : PostMaintenanceTest {
            perform action a0 { doc /* fails @S124 */ }
        }
        part potableWater : PotableWater {
            perform action a0 { doc /* meets regulatory requirements, utility operating targets, and customer demand @S001 */ }
        }
        part pressureZones : PressureZones {
            exhibit state modes {
                state s0 { doc /* stable @S199 */ }
            }
        }
        part processAdjustments : ProcessAdjustments {
            perform action a0 { doc /* require additional verification @S018 */ }
        }
        part processAndComplianceSamples : ProcessAndComplianceSamples {
            perform action a0 { doc /* support treatment decisions and regulatory documentation @S017 */ }
        }
        part processCondition : ProcessCondition {
            perform action a0 { doc /* requiring immediate operator assessment @S025 */ }
        }
        part programmableControllers : ProgrammableControllers {
            perform action a0 { doc /* remain synchronized to plant time standards @S014 */ }
        }
        part pump : Pump {
            perform action a0 { doc /* start @S043 */ }
        }
        part pumpCycling : PumpCycling {
            perform action a0 { doc /* have stabilized for a period accepted by the Chief Operator @S051 */ }
        }
        part pumpOperation : PumpOperation {
            perform action a0 { doc /* drawing the storage volume below the minimum level needed for safe hydraulic operation @S132 */ }
        }
        part pumpSpeedChanges : PumpSpeedChanges {
            perform action a0 { doc /* do not create avoidable pressure transients in the distribution system @S139 */ }
        }
        part pumpStarts : PumpStarts {
            perform action a0 { doc /* do not create avoidable pressure transients in the distribution system @S139 */ }
        }
        part pumpStatus : PumpStatus {
            perform action a0 { doc /* provide the control room with the first indication of system demand changes @S176 */ }
        }
        part rainfall : Rainfall {
            perform action a0 { doc /* creates conditions that require closer supervision of the intake @S029 */ }
        }
        part rawAndSettledWaterMeasurements : RawAndSettledWaterMeasurements {
            perform action a0 { doc /* show stable behavior @S098 */ }
        }
        part rawWaterQuality : RawWaterQuality {
            perform action a0 { doc /* have stabilized for a period accepted by the Chief Operator @S051 */ }
        }
        part rawWaterQualityTrends : RawWaterQualityTrends {
            perform action a0 { doc /* support stable chemical feed and predictable filter loading @S053 */ }
        }
        part rawWaterQualityTriggers : RawWaterQualityTriggers {
            perform action a0 { doc /* occurs @S038 */ }
        }
        part rawWaterScreenChannel : RawWaterScreenChannel {
            perform action a0 { doc /* sends the Rake Torque Snapshot at the end of each cleaning cycle @S034 */ }
            perform action a1 { doc /* preserve the recorded loading condition @S034 */ }
            perform action a2 { doc /* shows rapid level change @S035 */ }
            perform action a3 { doc /* respond correctly to local and supervisory commands @S229 */ }
            exhibit state modes {
                state s0 { doc /* high-high level condition @S036 */ }
            }
        }
        part rawWaterTurbidity : RawWaterTurbidity {
            perform action a0 { doc /* changes quickly @S058 */ }
        }
        part records : Records {
            perform action a0 { doc /* support troubleshooting, regulatory review, warranty claims, and future operator training @S247 */ }
        }
        part recordsRetention : RecordsRetention {
            perform action a0 { doc /* shall follow municipal policy and applicable drinking water requirements @S248 */ }
        }
        part recoveredWaterQuality : RecoveredWaterQuality {
            perform action a0 { doc /* could influence filter performance or finished water stability @S099 */ }
            exhibit state modes {
                state s0 { doc /* stable @S175 */ }
            }
        }
        part recoveryWaterQuality : RecoveryWaterQuality {
            exhibit state modes {
                state s0 { doc /* outside the operating band @S154 */ }
            }
        }
        part relatedInstrumentation : RelatedInstrumentation;
        part reliabilityTargets : ReliabilityTargets {
            perform action a0 { doc /* shall include prompt detection of failed sensors, redundant communication paths where practical, recoverable configuration backups, and periodic restoration testing @S224 */ }
        }
        part remoteAccess : RemoteAccess {
            perform action a0 { doc /* require multi-factor authentication, encrypted connectivity, a recorded business reason, and approval by the Chief Operator or Duty Engineer @S203 */ }
        }
        part residualConcentration : ResidualConcentration {
            perform action a0 { doc /* indicates a potential treatment compliance or public health concern @S210 */ }
        }
        part residualContactTime : ResidualContactTime {
            perform action a0 { doc /* remain aligned @S170 */ }
        }
        part residualInstruments : ResidualInstruments {
            perform action a0 { doc /* are responding consistently in the SCADA Historian Server @S126 */ }
        }
        part residualsHandling : ResidualsHandling {
            exhibit state modes {
                state s0 { doc /* complete @S175 */ }
            }
        }
        part residualsHauler : ResidualsHauler {
            perform action a0 { doc /* use the Backwash Solids Manifest @S245 */ }
            perform action a1 { doc /* confirm load identity, destination, and acceptance requirements @S245 */ }
        }
        part residualsRemovalScheduling : ResidualsRemovalScheduling;
        part returnPath : ReturnPath {
            exhibit state modes {
                state s0 { doc /* out of service @S154 */ }
            }
        }
        part returnToServiceDecisions : ReturnToServiceDecisions {
            perform action a0 { doc /* do not create avoidable storage swings @S074 */ }
        }
        part rinseToWasteQuality : RinseToWasteQuality {
            perform action a0 { doc /* meets the operating target @S063 */ }
        }
        part riverConditions : RiverConditions {
            perform action a0 { doc /* require more conservative intake operation, closer operator review, or modified treatment readiness @S007 */ }
        }
        part riverIntakePumpStation : RiverIntakePumpStation {
            perform action a0 { doc /* provides the first controlled pumping function @S005 */ }
            perform action a1 { doc /* normally operates in automatic service @S027 */ }
            perform action a2 { doc /* is not drawing the channel down too quickly @S035 */ }
            perform action a3 { doc /* shall remain unavailable for routine maintenance release until isolation points are tagged, verified locally, and acknowledged in the shift turnover record @S109 */ }
            perform action a4 { doc /* respond correctly to local and supervisory commands @S229 */ }
            exhibit state modes {
                state s0 { doc /* Reduced-capacity service @S028 */ }
                state s1 { doc /* Storm Intake Mode @S029 */ }
                state s2 { doc /* automatic service @S027 */ }
                state s3 { doc /* full intake operation @S028 */ }
                state s4 { doc /* unavailable for routine maintenance release @S109 */ }
            }
        }
        part riverLevel : RiverLevel {
            perform action a0 { doc /* does not support full intake operation @S028 */ }
            perform action a1 { doc /* have stabilized for a period accepted by the Chief Operator @S051 */ }
        }
        part riverRise : RiverRise {
            perform action a0 { doc /* creates conditions that require closer supervision of the intake @S029 */ }
        }
        part routineOperation : RoutineOperation {
            perform action a0 { doc /* assumes trained staff are available to supervise automatic control, place equipment in safe manual operation when needed, and document deviations through approved plant procedures @S026 */ }
        }
        part sCADAHistorianServer : SCADAHistorianServer {
            perform action a0 { doc /* stores operating data needed for trend review, compliance support, incident reconstruction, and performance evaluation @S013 */ }
            perform action a1 { doc /* remain synchronized to plant time standards @S014 */ }
            perform action a2 { doc /* retains river level, screen differential, pump status, and raw-water quality trends for operating review and event reconstruction @S047 */ }
            perform action a3 { doc /* retains dose changes, analyzer values, filter status changes, wash sequences, and operator comments for later review @S067 */ }
            perform action a4 { doc /* retain accepted laboratory result timestamps with the associated process trend interval @S086 */ }
            perform action a5 { doc /* retains operating data needed to compare pre-work and post-work performance for pumps, dosing systems, filters, and level controls @S125 */ }
            perform action a6 { doc /* stores residual, level, pressure, and pump status data at sufficient resolution @S147 */ }
            perform action a7 { doc /* support event reconstruction after alarms or customer pressure complaints @S147 */ }
            perform action a8 { doc /* records recovery volume, tank level, turbidity trend, and return timing for each backwash recovery event @S152 */ }
            perform action a9 { doc /* uses the Sample Chain Slip @S188 */ }
            perform action a10 { doc /* associate distribution water-quality entries with the operating period shown in the electronic log @S188 */ }
            perform action a11 { doc /* retains pressure, flow, pump status, and alarm data needed to reconstruct dispatch decisions after an event @S196 */ }
            perform action a12 { doc /* supports compliance review, alarm analysis, operational trending, and event reconstruction @S205 */ }
        }
        part sampleResults : SampleResults;
        part screenCondition : ScreenCondition {
            perform action a0 { doc /* directly affect downstream stability @S006 */ }
        }
        part screenDifferential : ScreenDifferential {
            perform action a0 { doc /* have stabilized for a period accepted by the Chief Operator @S051 */ }
        }
        part securityPatches : SecurityPatches;
        part sharedCredentials : SharedCredentials;
        part shiftCommunication : ShiftCommunication;
        part shiftHandoff : ShiftHandoff;
        part significantDifferencesBetweenFieldReadingsAndLaboratoryValues : SignificantDifferencesBetweenFieldReadingsAndLaboratoryValues {
            perform action a0 { doc /* could affect chemical feed, filter loading, or disinfection decisions @S092 */ }
        }
        part solids : Solids {
            perform action a0 { doc /* have settled @S151 */ }
        }
        part solidsHandlingProblems : SolidsHandlingProblems {
            perform action a0 { doc /* indicate a need for inspection of tank mixing, decant valves, sludge transfer equipment, or instrumentation @S174 */ }
        }
        part southDistributionPressureStation : SouthDistributionPressureStation {
            perform action a0 { doc /* receive pressure support through coordinated setpoints that reflect system demand and storage conditions @S142 */ }
            perform action a1 { doc /* starts its lead booster pump @S180 */ }
            perform action a2 { doc /* use the card @S243 */ }
            perform action a3 { doc /* confirm zone status, valve lineup, and communication checks @S243 */ }
        }
        part southFilterGallery : SouthFilterGallery {
            perform action a0 { doc /* sends the Filter Run Exception Note @S061 */ }
            perform action a1 { doc /* completes a backwash cycle @S150 */ }
            perform action a2 { doc /* shows turbidity breakthrough or delayed ripening @S164 */ }
            perform action a3 { doc /* respond correctly to local and supervisory commands @S229 */ }
            exhibit state modes {
                state s0 { doc /* out of normal production @S164 */ }
            }
        }
        part standingAlarms : StandingAlarms;
        part statusOfOpenIsolations : StatusOfOpenIsolations;
        part storageLevel : StorageLevel {
            perform action a0 { doc /* provides the main buffer between reduced raw-water supply and treated-water delivery @S050 */ }
        }
        part storageStability : StorageStability {
            perform action a0 { doc /* remain aligned @S170 */ }
        }
        part stormIntakeMode : StormIntakeMode {
            perform action a0 { doc /* changes the character of incoming water @S098 */ }
        }
        part supportingProcessQualityIndications : SupportingProcessQualityIndications {
            perform action a0 { doc /* become inconsistent or unavailable @S160 */ }
            exhibit state modes {
                state s0 { doc /* inconsistent @S160 */ }
                state s1 { doc /* unavailable @S160 */ }
            }
        }
        part suppression : Suppression {
            perform action a0 { doc /* require a documented reason, a time limit, and review at the end of the operating shift @S211 */ }
        }
        part sustainedLossOfCoagulationEffectiveness : SustainedLossOfCoagulationEffectiveness {
            perform action a0 { doc /* prompts review of chemical strength, feed pump status, mixing energy, and raw-water characteristics @S072 */ }
        }
        part task : Task {
            perform action a0 { doc /* pause @S119 */ }
        }
        part telemetryRestoration : TelemetryRestoration {
            perform action a0 { doc /* proves otherwise @S191 */ }
        }
        part temporaryOperatingLimits : TemporaryOperatingLimits;
        part testing : Testing {
            perform action a0 { doc /* begins @S082 */ }
        }
        part totalFlow : TotalFlow {
            perform action a0 { doc /* provide the control room with the first indication of system demand changes @S176 */ }
        }
        part trainedStaff : TrainedStaff {
            perform action a0 { doc /* supervise automatic control @S026 */ }
            perform action a1 { doc /* place equipment in safe manual operation when needed @S026 */ }
            perform action a2 { doc /* document deviations through approved plant procedures @S026 */ }
        }
        part transfer : Transfer {
            perform action a0 { doc /* begins @S114 */ }
        }
        part treatmentScope : TreatmentScope;
        part treatmentTargets : TreatmentTargets {
            perform action a0 { doc /* have returned to acceptable control ranges @S077 */ }
        }
        part turbidity : Turbidity {
            perform action a0 { doc /* changes faster than the normal control response can stabilize @S040 */ }
        }
        part turbidityTrend : TurbidityTrend {
            exhibit state modes {
                state s0 { doc /* stable @S063 */ }
            }
        }
        part unavailableEquipment : UnavailableEquipment;
        part uninterruptiblePowerSupplies : UninterruptiblePowerSupplies {
            perform action a0 { doc /* bridge transfer events @S216 */ }
            perform action a1 { doc /* allow orderly shutdown of servers, network switches, control processors, and communication equipment @S216 */ }
        }
        part unnamed : Unnamed {
            perform action a0 { doc /* is reviewed again @S118 */ }
            perform action a1 { doc /* is returned to service @S121 */ }
            perform action a2 { doc /* is returned to service @S123 */ }
            perform action a3 { doc /* have been removed @S123 */ }
            perform action a4 { doc /* formally accepted for continued use @S123 */ }
            perform action a5 { doc /* can be operated under restriction @S124 */ }
            perform action a6 { doc /* compare pre-work and post-work performance for pumps, dosing systems, filters, and level controls @S125 */ }
            perform action a7 { doc /* is returned to normal service @S126 */ }
            perform action a8 { doc /* is operated to maintain the required contact time under the current production rate, basin level, and measured disinfectant residual @S127 */ }
            perform action a9 { doc /* maintain the required contact time under the current production rate, basin level, and measured disinfectant residual @S127 */ }
            perform action a10 { doc /* is understood @S129 */ }
            perform action a11 { doc /* is suspected @S130 */ }
            perform action a12 { doc /* are configured to prevent pump operation from drawing the storage volume below the minimum level needed for safe hydraulic operation @S132 */ }
            exhibit state modes {
                state s0 { doc /* Storm Intake Mode @S118 */ }
            }
        }
        part upsets : Upsets {
            exhibit state modes {
                state s0 { doc /* advisory @S165 */ }
                state s1 { doc /* controlled @S165 */ }
                state s2 { doc /* critical @S165 */ }
            }
        }
        part upstreamRunoff : UpstreamRunoff {
            perform action a0 { doc /* creates conditions that require closer supervision of the intake @S029 */ }
        }
        part valveMovements : ValveMovements {
            perform action a0 { doc /* do not create avoidable pressure transients in the distribution system @S139 */ }
        }
        part waterQualityConfirmation : WaterQualityConfirmation;
        part wetCommissioning : WetCommissioning {
            perform action a0 { doc /* begins @S228 */ }
        }
        part workOrder : WorkOrder {
            perform action a0 { doc /* identifies affected equipment, required isolations, parts staging, and the evidence needed to close the work @S104 */ }
            exhibit state modes {
                state s0 { doc /* open @S124 */ }
            }
        }
        part workOrderProcess : WorkOrderProcess {
            perform action a0 { doc /* ties each task to an approved operating window, a named responsible person, and a defined return-to-service condition @S101 */ }
        }
        part workaround : Workaround;
        flow f0 of UnusualResultsItem from laboratoryTechnician to operations { doc /* @S018 */ }
        flow f1 of AlumBatchTicketItem from coagulantDosingSkid to laboratoryTechnician { doc /* @S083 */ }
        flow f2 of RakeTorqueSnapshotItem from rawWaterScreenChannel to maintenancePlanner { doc /* @S105 */ }
        flow f3 of AcceptanceConcernItem from laboratoryTechnician to unnamed { doc /* @S120 */ }
        flow f4 of ConfirmatoryResidualResultsItem from laboratoryTechnician to unnamed { doc /* @S130 */ }
        flow f5 of TimeItem from highClearwellLevelAlarms to operators { doc /* @S133 */ }
        flow f6 of FilterRunExceptionNoteItem from southFilterGallery to chiefOperator { doc /* @S153 */ }
        flow f7 of FirstIndicationOfSystemDemandChangesItem from dischargePressure to controlRoom { doc /* @S176 */ }
        flow f8 of FirstIndicationOfSystemDemandChangesItem from totalFlow to controlRoom { doc /* @S176 */ }
        flow f9 of FirstIndicationOfSystemDemandChangesItem from pumpStatus to controlRoom { doc /* @S176 */ }
        flow f10 of AbnormalStartsItem from localControls to controlSystem { doc /* @S181 */ }
        flow f11 of FailuresItem from localControls to controlSystem { doc /* @S181 */ }
        flow f12 of ValvePositionsItem from localControls to controlSystem { doc /* @S181 */ }
        flow f13 of SampleChainSlipItem from laboratoryTechnician to sCADAHistorianServer { doc /* @S188 */ }
        flow f14 of AnalyticalStatusItem from laboratorySampleReceivingBench to controlRoom { doc /* @S195 */ }
        flow f15 of FailuresItem from localControls to distributionDispatcher { doc /* @S220 */ }
        flow f16 of ClearwellDiverEntryPermitItem from clearwellLevelController to maintenancePlanner { doc /* @S222 */ }
        flow f17 of ChlorineCylinderSealLogItem from chemicalSupplierDriver to dutyEngineer { doc /* @S223 */ }
        flow f18 of PressureZoneHandoffCardItem from distributionDispatcher to southDistributionPressureStation { doc /* @S243 */ }
    }
    requirement def R0 { doc /* A high-high level condition at the Raw Water Screen Channel requires immediate field confirmation because it may indicate restricted passage, failed cleaning, or abnormal river backwater. @S036 */ subject s : RawWaterScreenChannel; }
    requirement def R1 { doc /* A pump is not permitted to start when the Raw Water Screen Channel downstream level is below the established low-level limit. @S043 */ subject s : Pump; }
    requirement def R2 { doc /* An operator placing equipment in manual control is expected to state the reason, monitor the affected process variable closely, and restore automatic control as soon as practicable. @S069 */ subject s : Operator; }
    requirement def R3 { doc /* Lantern must retain accepted laboratory result timestamps with the associated process trend interval so that reconciliation can be repeated during audits. @S086 */ subject s : SCADAHistorianServer; }
    requirement def R4 { doc /* Ironwood shall remain unavailable for routine maintenance release until isolation points are tagged, verified locally, and acknowledged in the shift turnover record. @S109 */ subject s : RiverIntakePumpStation; }
    requirement def R5 { doc /* Any planned change affecting the Clearwell Level Controller requires coordination with the High Service Pump Header operating plan before the change is applied. @S111 */ subject s : PlannedChange; }
    requirement def R6 { doc /* water quality confirmation is required before a unit is returned to service @S121 */ subject s : WaterQualityConfirmation; }
    requirement def R7 { doc /* Abnormal clearwell level, loss of residual, loss of pump header pressure, or conflicting instrument readings require the Duty Engineer to review the operating condition before setpoints are changed outside normal ranges. @S146 */ subject s : DutyEngineer; }
    requirement def R8 { doc /* Return to automatic control requires stable chlorine residual, stable clearwell level response, and confirmed high-service pressure control for a period set by the Chief Operator. @S149 */ subject s : AutomaticControl; }
    requirement def R9 { doc /* Marigold shall hold the last operator-approved dose if the supporting process quality indications become inconsistent or unavailable. @S160 */ subject s : CoagulantDosingSkid; }
    requirement def R10 { doc /* An advisory upset requires closer monitoring and documented operator awareness but does not require immediate removal of treatment capacity. @S166 */ subject s : Advisory; }
    requirement def R11 { doc /* A controlled upset requires an operator-directed change, such as reducing filter loading, extending filter-to-waste operation, increasing verification sampling, or holding recovered washwater. @S167 */ subject s : Controlled; }
    requirement def R12 { doc /* A critical upset requires immediate protection of treated water quality, and the Duty Engineer is notified when automatic control cannot maintain the required operating envelope. @S168 */ subject s : Critical; }
    requirement def R13 { doc /* When a distribution station is in automatic operation, local controls are expected to sequence pumps within approved limits and report abnormal starts, failures, or valve positions to the control system. @S181 */ subject s : LocalControls; }
    requirement def R14 { doc /* Cobalt shall provide a reliable filter service status indication before the control room treats increased distribution demand as available finished-water capacity. @S186 */ subject s : NorthFilterGallery; }
    requirement def R15 { doc /* The control system for the Cedar Falls Municipal Drinking Water Treatment Plant shall use role-based access control with named accounts for operators, engineering users, maintenance users, and read-only review users. @S200 */ subject s : ControlSystem; }
    requirement def R16 { doc /* Shared credentials are not acceptable for routine operation of the River Intake Pump Station, North Filter Gallery, South Filter Gallery, Coagulant Dosing Skid, Chlorine Contact Basin, Clearwell Level Controller, High Service Pump Header, North Distribution Pressure Station, or South Distribution Pressure Station. @S201 */ subject s : SharedCredentials; }
    requirement def R17 { doc /* Operator privileges shall be limited to the actions needed to run assigned plant areas @S202 */ subject s : OperatorPrivileges; }
    requirement def R18 { doc /* engineering privileges shall require separate approval before setpoints, control logic, alarm limits, or historian configuration are changed. @S202 */ subject s : EngineeringPrivileges; }
    requirement def R19 { doc /* Remote access to the control network shall require multi-factor authentication, encrypted connectivity, a recorded business reason, and approval by the Chief Operator or Duty Engineer. @S203 */ subject s : RemoteAccess; }
    requirement def R20 { doc /* The SCADA Historian Server shall be protected as a critical asset because it supports compliance review, alarm analysis, operational trending, and event reconstruction. @S205 */ subject s : SCADAHistorianServer; }
    requirement def R21 { doc /* The control network shall be segmented from administrative networks @S206 */ subject s : ControlNetwork; }
    requirement def R22 { doc /* only documented pathways shall be allowed between the SCADA Historian Server, operator workstations, controllers, and approved support systems. @S206 */ subject s : DocumentedPathways; }
    requirement def R23 { doc /* Security patches, firmware updates, and antivirus changes shall be tested in a controlled manner before deployment to equipment that affects water production or distribution pressure. @S207 */ subject s : SecurityPatches; }
    requirement def R24 { doc /* Security patches, firmware updates, and antivirus changes shall be tested in a controlled manner before deployment to equipment that affects water production or distribution pressure. @S207 */ subject s : FirmwareUpdates; }
    requirement def R25 { doc /* Security patches, firmware updates, and antivirus changes shall be tested in a controlled manner before deployment to equipment that affects water production or distribution pressure. @S207 */ subject s : AntivirusChanges; }
    requirement def R26 { doc /* Alarm priorities shall reflect consequence, response time, operator action, and the risk of losing treatment, storage, or distribution capability. @S209 */ subject s : AlarmPriorities; }
    requirement def R27 { doc /* A Chlorine Residual Alarm shall remain configured as a high-priority condition when residual concentration indicates a potential treatment compliance or public health concern. @S210 */ subject s : ChlorineResidualAlarm; }
    requirement def R28 { doc /* Alarm shelving, suppression, and disabling shall require a documented reason, a time limit, and review at the end of the operating shift. @S211 */ subject s : AlarmShelving; }
    requirement def R29 { doc /* Alarm shelving, suppression, and disabling shall require a documented reason, a time limit, and review at the end of the operating shift. @S211 */ subject s : Suppression; }
    requirement def R30 { doc /* Alarm shelving, suppression, and disabling shall require a documented reason, a time limit, and review at the end of the operating shift. @S211 */ subject s : Disabling; }
    requirement def R31 { doc /* Standing alarms shall be reviewed during each shift turnover so that unresolved equipment failures are not hidden by routine acknowledgement. @S212 */ subject s : StandingAlarms; }
    requirement def R32 { doc /* During Storm Intake Mode, alarm response expectations shall account for higher debris load, faster raw water quality changes, and increased dependence on intake screening and chemical dose verification. @S213 */ subject s : AlarmResponseExpectations; }
    requirement def R33 { doc /* Backup power shall support safe operation or controlled shutdown of the River Intake Pump Station, Raw Water Screen Channel, Chlorine Contact Basin, Clearwell Level Controller, SCADA Historian Server, High Service Pump Header, and essential control-room equipment. @S214 */ subject s : BackupPower; }
    requirement def R34 { doc /* The plant shall maintain written expectations for generator start time, automatic transfer performance, fuel availability, and operator checks during extended utility outages. @S215 */ subject s : Plant; }
    requirement def R35 { doc /* Uninterruptible power supplies shall be sized to bridge transfer events and allow orderly shutdown of servers, network switches, control processors, and communication equipment. @S216 */ subject s : UninterruptiblePowerSupplies; }
    requirement def R36 { doc /* Loss of both normal and standby power to a critical service shall be treated as an emergency operating condition requiring immediate notification of the Chief Operator and Duty Engineer. @S217 */ subject s : CriticalService; }
    requirement def R37 { doc /* the workaround shall be logged, bounded by time or condition, and removed when normal control is restored @S219 */ subject s : Workaround; }
    requirement def R38 { doc /* The Distribution Dispatcher shall be informed when failures at the High Service Pump Header, North Distribution Pressure Station, or South Distribution Pressure Station may affect pressure zones or fire-flow readiness. @S220 */ subject s : DistributionDispatcher; }
    requirement def R39 { doc /* The Laboratory Technician shall retain access needed for sample status review and reporting @S221 */ subject s : LaboratoryTechnician; }
    requirement def R40 { doc /* laboratory accounts shall not allow control actions on plant equipment @S221 */ subject s : LaboratoryAccounts; }
    requirement def R41 { doc /* Reliability targets for critical plant services shall include prompt detection of failed sensors, redundant communication paths where practical, recoverable configuration backups, and periodic restoration testing. @S224 */ subject s : ReliabilityTargets; }
    requirement def R42 { doc /* After any cybersecurity event, major alarm failure, or emergency control action, the Chief Operator shall require a brief operational review that identifies the cause, affected services, corrective actions, and any needed procedure changes. @S225 */ subject s : ChiefOperator; }
    requirement def R43 { doc /* Commissioning shall be planned as a controlled sequence that proves each control function before the plant relies on it for normal service. @S226 */ subject s : Commissioning; }
    requirement def R44 { doc /* Each commissioning test shall have defined starting conditions, expected responses, acceptance limits, and a responsible reviewer. @S227 */ subject s : CommissioningTest; }
    requirement def R45 { doc /* Before wet commissioning begins, the Duty Engineer shall confirm that temporary controls, bypasses, and manual operating instructions are understood by the affected staff. @S228 */ subject s : DutyEngineer; }
    requirement def R46 { doc /* Functional testing shall verify that the River Intake Pump Station, Raw Water Screen Channel, North Filter Gallery, South Filter Gallery, and Coagulant Dosing Skid respond correctly to local and supervisory commands. @S229 */ subject s : FunctionalTesting; }
    requirement def R47 { doc /* During integrated testing, Juniper shall demonstrate stable pressure control through startup, lead-lag transfer, and controlled shutdown. @S230 */ subject s : HighServicePumpHeader; }
    requirement def R48 { doc /* The SCADA Historian Server shall be checked for correct time synchronization, tag naming, data retention, and retrieval of key commissioning trends. @S231 */ subject s : SCADAHistorianServer; }
    requirement def R49 { doc /* The Chlorine Contact Basin and Clearwell Level Controller shall be tested under representative level, flow, and residual control conditions before treated water is released for routine distribution. @S232 */ subject s : ChlorineContactBasin; }
    requirement def R50 { doc /* The Chlorine Contact Basin and Clearwell Level Controller shall be tested under representative level, flow, and residual control conditions before treated water is released for routine distribution. @S232 */ subject s : ClearwellLevelController; }
    requirement def R51 { doc /* Storm Intake Mode shall be exercised in a planned drill that confirms operator prompts, intake constraints, and return-to-normal steps. @S233 */ subject s : StormIntakeMode; }
    requirement def R52 { doc /* A Chlorine Residual Alarm test shall verify annunciation, operator response guidance, acknowledgement behavior, and escalation to the appropriate duty staff. @S234 */ subject s : ChlorineResidualAlarmTest; }
    requirement def R53 { doc /* The Chief Operator shall coordinate training so that operators understand the control concept, normal sequencing, manual fallback methods, and alarm response expectations. @S235 */ subject s : ChiefOperator; }
    requirement def R54 { doc /* Operator training shall include classroom review, simulator or dry-run practice where practical, field walkdowns, and supervised operation during early service. @S236 */ subject s : OperatorTraining; }
    requirement def R55 { doc /* The Laboratory Technician shall be trained on sample timing, result entry, data review responsibilities, and communication of unusual water quality findings. @S237 */ subject s : LaboratoryTechnician; }
    requirement def R56 { doc /* The Maintenance Planner shall review commissioning defects, recurring nuisance alarms, calibration drift, and equipment access problems before preventive maintenance intervals are finalized. @S238 */ subject s : MaintenancePlanner; }
    requirement def R57 { doc /* The Maintenance Planner shall use the clip to compare observed pump condition with planned inspection intervals and corrective work priorities. @S239 */ subject s : MaintenancePlanner; }
    requirement def R58 { doc /* Feedback from maintenance work orders shall be reviewed with operations so that control changes do not mask equipment degradation or create avoidable field effort. @S240 */ subject s : FeedbackFromMaintenanceWorkOrders; }
    requirement def R59 { doc /* Distribution readiness shall be declared only after pressure control, reservoir or clearwell constraints, communications, and emergency contact paths have been verified. @S241 */ subject s : DistributionReadiness; }
    requirement def R60 { doc /* Falcon shall confirm that distribution readiness messages are acknowledged before any planned change in pressure zone operating status. @S242 */ subject s : DistributionDispatcher; }
    requirement def R61 { doc /* Before distribution readiness is declared, the South Distribution Pressure Station shall use the card to confirm zone status, valve lineup, and communication checks. @S243 */ subject s : SouthDistributionPressureStation; }
    requirement def R62 { doc /* The North Distribution Pressure Station shall be included in readiness checks for telemetry validity, pump permissives, local alarm indication, and operator communications. @S244 */ subject s : NorthDistributionPressureStation; }
    requirement def R63 { doc /* During commissioning of residuals handling, the Residuals Hauler shall use the Backwash Solids Manifest to confirm load identity, destination, and acceptance requirements. @S245 */ subject s : ResidualsHauler; }
    requirement def R64 { doc /* The Chemical Supplier Driver shall follow site access, unloading, verification, and communication procedures established during commissioning and confirmed during training. @S246 */ subject s : ChemicalSupplierDriver; }
    requirement def R65 { doc /* Records generated during commissioning and early operation shall be complete enough to support troubleshooting, regulatory review, warranty claims, and future operator training. @S247 */ subject s : Records; }
    requirement def R66 { doc /* Records retention shall follow municipal policy and applicable drinking water requirements, with electronic records protected against unauthorized change and accidental loss. @S248 */ subject s : RecordsRetention; }
    requirement def R67 { doc /* Periodic performance reviews shall compare actual plant operation with the control concept, including alarm burden, manual interventions, water quality stability, chemical use, and energy use. @S249 */ subject s : PeriodicPerformanceReviews; }
    requirement def R68 { doc /* Continuous improvement actions shall be prioritized by risk, reviewed by the Chief Operator and Duty Engineer, tested before release, and incorporated into updated procedures and training materials. @S250 */ subject s : ContinuousImprovementActions; }
}
