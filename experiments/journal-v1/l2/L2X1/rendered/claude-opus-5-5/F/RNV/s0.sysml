package L2Model {
    item def AcceptedIntentDataItem { doc /* @S128 */ }
    item def AcceptedOrRejectedExemptionItem { doc /* @S239 */ }
    item def ActiveRestrictionStatusItem { doc /* @S337 */ }
    item def ActiveSpacingRulesItem { doc /* @S297 */ }
    item def AffectedRunwayQueueHighlightItem { doc /* @S366 */ }
    item def AgreedTargetOffBlockTimeValuesAndStakeholderRemarksItem { doc /* @S429 */ }
    item def AirspaceAlertAcknowledgementAndDownstreamDecisionItem { doc /* @S333 */ }
    item def ApronCongestionConditionItem { doc /* @S218 */ }
    item def ApronSweepCompletionNoteItem { doc /* @S678 */ }
    item def ArrivalPlanItem { doc /* @S405 */ }
    item def CandidatePushbackSpacingItem { doc /* @S456 */ }
    item def CapacityPictureChangeNotificationItem { doc /* @S121 */ }
    item def CivilRoutingConstraintAlertItem { doc /* @S093 */ }
    item def ConditionsThatMayAffectRunwayTaxiwayStandOrApronAvailabilityItem { doc /* @S175 */ }
    item def ConstraintsItem { doc /* @S135,S225 */ }
    item def CrewBusDelaySlipItem { doc /* @S237 */ }
    item def CrewDutyExtensionLogItem { doc /* @S726 */ }
    item def CurrentRegionalDemandAndConstraintContextItem { doc /* @S164 */ }
    item def CustomsHoldReleaseNoteItem { doc /* @S679 */ }
    item def DegradedWeatherInputsItem { doc /* @S112 */ }
    item def DeicingPadQueueCardItem { doc /* @S378 */ }
    item def DemandItem { doc /* @S225 */ }
    item def DemandForecastItem { doc /* @S101 */ }
    item def DemandProjectionsItem { doc /* @S107 */ }
    item def DepartureFixLoadSheetItem { doc /* @S598 */ }
    item def DiversionRationalePriorityClassificationResourceCommitmentAndAgreedRecoveryTargetItem { doc /* @S506 */ }
    item def DutyDeskConfirmationTransactionsItem { doc /* @S194 */ }
    item def ExpectedServiceCompletionTimesItem { doc /* @S302 */ }
    item def ExternalCoordinationOutcomesItem { doc /* @S084 */ }
    item def FiledFlightInformationItem { doc /* @S103 */ }
    item def FlightIntentMessageItem { doc /* @S126 */ }
    item def FuelTruckHoldAdviceItem { doc /* @S450 */ }
    item def GateReopeningMemoItem { doc /* @S472 */ }
    item def LateBaggageTagListItem { doc /* @S519 */ }
    item def MedicalDiversionNoticeItem { doc /* @S576 */ }
    item def MorningWeatherOutlookItem { doc /* @S057 */ }
    item def MovementAreaOccupancyAndEquipmentStatusIndicatorsItem { doc /* @S445 */ }
    item def MovementIndicationsItem { doc /* @S179 */ }
    item def MovementUpdatesItem { doc /* @S222 */ }
    item def NotificationsItem { doc /* @S614 */ }
    item def OperationalBasisForCandidateAirportAcceptanceRateValuesItem { doc /* @S400 */ }
    item def OperationalSignificanceOfTheConditionItem { doc /* @S447 */ }
    item def OverlappingOccupancyAlertItem { doc /* @S210 */ }
    item def PassengerMisconnectCountItem { doc /* @S851 */ }
    item def PlannedRemoteStandOperatingPostureItem { doc /* @S544 */ }
    item def PositionUpdatesItem { doc /* @S179 */ }
    item def PredictedReadinessItem { doc /* @S593 */ }
    item def ProposedDepartureOpportunitiesAndAssociatedCalculatedTakeoffTimeValuesItem { doc /* @S242 */ }
    item def ProposedSubstitutionItem { doc /* @S667 */ }
    item def PushbackWindowTokenItem { doc /* @S503 */ }
    item def ReconsiderationRequestItem { doc /* @S363 */ }
    item def RemoteStandShuttleCountItem { doc /* @S648 */ }
    item def ResourceDrivenFeasibilityStatusItem { doc /* @S312 */ }
    item def RevisedInputsItem { doc /* @S699 */ }
    item def RunwayInspectionNoteItem { doc /* @S181 */ }
    item def RunwayLightingOutageCardItem { doc /* @S693 */ }
    item def RunwaySpecificCapacityValuesItem { doc /* @S114 */ }
    item def ScheduledMovementsItem { doc /* @S593 */ }
    item def SlotComplianceEventsItem { doc /* @S789 */ }
    item def SlotSwapPermissionEmailItem { doc /* @S795 */ }
    item def StandTowRequestFormItem { doc /* @S304 */ }
    item def StormCellSnapshotItem { doc /* @S133 */ }
    item def SubscriptionRulesItem { doc /* @S332 */ }
    item def SynchronizedTimestampsItem { doc /* @S098 */ }
    item def TemporaryRestrictionNoticeItem { doc /* @S399 */ }
    item def TowbarShortageReportItem { doc /* @S556 */ }
    item def UnresolvedAssumptionsItem { doc /* @S071 */ }
    item def WeatherDataItem { doc /* @S086 */ }
    part def AccountableParticipant { doc /* @S168 */ }
    part def AdvancedTurnaroundPrediction { doc /* @S946 */ }
    part def AffectedComponent { doc /* @S832 */ }
    part def AirTrafficControllers { doc /* @S865 */ }
    part def AircraftOperatorRepresentative { doc /* @S055,S082,S312,S363,S405,S620,S726,S854,S868 */ }
    part def AirlineInterfaceAdapter { doc /* @S031,S126,S128,S135,S235,S452,S519,S618,S829,S947,S979 */ }
    part def AirlineOperationsCentre { doc /* @S126,S135,S139 */ }
    part def AirlineOperationsCoordinator { doc /* @S054,S081,S121,S138,S214,S237,S259,S260,S312,S362,S403,S472,S507,S667,S679,S740,S795,S820,S851,S854,S868 */ }
    part def AirportCDMPortal { doc /* @S016,S031,S164,S166,S172,S179,S293,S312,S337,S363,S405,S429,S447,S503,S544,S648,S667,S793,S947 */ }
    part def AirportDutyManager { doc /* @S062,S088,S116,S144,S162,S175,S181,S218,S435,S447,S471,S496,S544,S568,S576,S678,S679,S809,S816,S860,S872,S917 */ }
    part def AirportOnboarding { doc /* @S902 */ }
    part def AirportParticipant { doc /* @S167 */ }
    part def AirspaceSectorPlanner { doc /* @S058,S079,S326,S402,S501,S871 */ }
    part def AlertDistributionHub { doc /* @S031,S073,S121,S193,S332,S366,S461,S529,S588,S614,S705,S834 */ }
    part def ArrivalRegulationConsole { doc /* @S031,S070,S095,S241,S336,S407,S535,S576,S698,S980 */ }
    part def AuditEventLedger { doc /* @S031,S098,S123,S194,S222,S333,S777,S779,S788,S789,S792,S797,S811,S924,S955,S981 */ }
    part def AvailabilityTargets { doc /* @S934 */ }
    part def BusinessRulesRegistry { doc /* @S031,S297,S332,S436,S799,S831,S849,S931,S939 */ }
    part def CalculatedTakeoffTime { doc /* @S976 */ }
    part def CandidateAirport { doc /* @S893 */ }
    part def CapacityAssessmentModule { doc /* @S014,S031,S057,S066,S107,S114,S120,S133,S225,S341,S351,S373,S400,S431,S494,S803,S825,S853,S900,S944 */ }
    part def CollaborativeDecisionLog { doc /* @S071,S084,S239,S506,S794,S901,S925,S955 */ }
    part def CommonSituationDisplay { doc /* @S072,S337,S366,S400,S822,S823,S974 */ }
    part def ContingencyOperationsConsole { doc /* @S031,S195,S247,S719,S783,S908,S952 */ }
    part def CriticalIncident { doc /* @S920 */ }
    part def CutoverDecision { doc /* @S906 */ }
    part def DataGovernanceSteward { doc /* @S098,S273,S785,S806,S813,S833,S837,S861,S876,S958 */ }
    part def DeicingCoordinator { doc /* @S092,S294,S375,S378,S390,S875 */ }
    part def DemandPredictionService { doc /* @S013,S031,S053,S101,S103,S105,S107,S131,S216,S225,S350,S430,S593,S825,S900,S941 */ }
    part def DepartureMeteringService { doc /* @S031,S069,S095,S242,S278,S335,S348,S379,S426,S456,S483,S656,S686,S699,S728,S825,S851,S950,S980 */ }
    part def DigitalBriefingRoom { doc /* @S031,S071,S506 */ }
    part def EastApronSensor { doc /* @S031,S179,S578,S845 */ }
    part def EmergencyChanges { doc /* @S932 */ }
    part def EmergencyResponseCoordinator { doc /* @S096,S499,S874 */ }
    part def FlightDataExchange { doc /* @S031,S052,S103,S128,S278,S593,S638,S684,S827,S940,S979 */ }
    part def FutureReleases { doc /* @S959 */ }
    part def GateConflictDetector { doc /* @S031,S210,S364,S386,S472,S900 */ }
    part def Governance { doc /* @S983 */ }
    part def GroundDelayProgram { doc /* @S977 */ }
    part def GroundHandlingDispatcher { doc /* @S064,S091,S140,S237,S261,S292,S302,S383,S519,S523,S556,S643,S869 */ }
    part def HandlingResourcePlanner { doc /* @S065,S302,S304,S384,S522,S547,S648,S830,S947 */ }
    part def HarborEastAirport { doc /* @S026 */ }
    part def HighPriorityIncident { doc /* @S921 */ }
    part def IdentityAccessService { doc /* @S031,S152,S194,S272,S781,S782,S786,S957,S981 */ }
    part def Incident { doc /* @S919 */ }
    part def InitialPilot { doc /* @S892 */ }
    part def IntegratedTacticalManagementPosition { doc /* @S420,S429 */ }
    part def Interface { doc /* @S899 */ }
    part def InterfaceCertification { doc /* @S898 */ }
    part def LakesideRegionalAirport { doc /* @S026 */ }
    part def LearningModels { doc /* @S945 */ }
    part def LocalTool { doc /* @S904,S905 */ }
    part def LocalUsers { doc /* @S907 */ }
    part def MachineAssistedRecoveryOptions { doc /* @S951 */ }
    part def MediumAndLowPriorityIncidents { doc /* @S922 */ }
    part def MeridianInternationalAirport { doc /* @S026 */ }
    part def MeridianRegionalAirTrafficFlowManagementAndAirportCollaborativeDecisionMakingSystem { doc /* @S838,S863,S878,S884 */ }
    part def MeridianRegionalCapability { doc /* @S031 */ }
    part def MeteorologyBriefingOfficer { doc /* @S056,S085,S086,S087,S112,S133,S372,S434,S819,S858,S873 */ }
    part def MigrationPlan { doc /* @S903 */ }
    part def MilitaryAirspaceLiaison { doc /* @S059,S093,S325,S399 */ }
    part def NetworkOperationsLiaison { doc /* @S083,S084,S339,S413,S614,S871,S917 */ }
    part def NorthRunwayMeter { doc /* @S031,S114,S454,S845,S900 */ }
    part def NorthValleyAirport { doc /* @S026 */ }
    part def OnboardingWave { doc /* @S910 */ }
    part def OperationalUser { doc /* @S764 */ }
    part def ParticipatingAirportNetwork { doc /* @S026 */ }
    part def ParticipatingOrganization { doc /* @S960 */ }
    part def PerformanceAnalyticsWarehouse { doc /* @S031,S074,S148,S737,S776,S804,S805,S836,S839,S840,S841,S843,S846,S847,S852,S855,S856,S857,S859,S957,S982 */ }
    part def PilotAirportSelection { doc /* @S891 */ }
    part def PlannedChangeWindows { doc /* @S930 */ }
    part def PostExerciseReviews { doc /* @S887 */ }
    part def PostIncidentReview { doc /* @S928,S929 */ }
    part def PostOperationsReport { doc /* @S862 */ }
    part def RampControlLead { doc /* @S063,S090,S142,S200,S202,S208,S210,S211,S218,S219,S304,S357,S378,S387,S473,S556,S614,S647,S678,S818,S917 */ }
    part def RampMovementBoard { doc /* @S031,S222,S255,S361,S427,S445,S450,S801,S844,S947,S980 */ }
    part def RampPersonnel { doc /* @S867 */ }
    part def ReadinessGate1 { doc /* @S894 */ }
    part def ReadinessGate2 { doc /* @S895 */ }
    part def ReadinessGate3 { doc /* @S896 */ }
    part def ReadinessGate4 { doc /* @S897 */ }
    part def RecoveryRecommendations { doc /* @S954 */ }
    part def RegionalExpansion { doc /* @S956 */ }
    part def RegionalFlowManager { doc /* @S010,S050,S078,S093,S094,S117,S121,S228,S246,S327,S343,S367,S393,S396,S399,S410,S492,S598,S614,S721,S800,S808,S814,S842,S864,S911,S917,S935 */ }
    part def RegionalFlowPlatform { doc /* @S031,S047,S051,S073,S101,S147,S164,S250,S268,S314,S333,S349,S371,S422,S593,S767,S774,S775,S780,S787,S789,S790,S796,S810,S812,S821,S826,S879,S888,S889,S890,S909,S912,S936 */ }
    part def SectorLoadMonitor { doc /* @S031,S106,S329,S484,S592,S598,S900,S943 */ }
    part def ServiceDesk { doc /* @S915 */ }
    part def ServiceLevelTargets { doc /* @S933 */ }
    part def ServiceModel { doc /* @S913 */ }
    part def SimulationExercises { doc /* @S880,S881,S882,S883 */ }
    part def SlotAllocationEngine { doc /* @S015,S031,S134,S225,S234,S253,S355,S428,S456,S503,S669,S699,S825,S900,S949,S980 */ }
    part def SlotComplianceState { doc /* @S791,S850 */ }
    part def SlotCoordinator { doc /* @S068,S080,S136,S161,S229,S239,S258,S285,S614,S672,S722,S726,S795,S798,S815,S848,S870 */ }
    part def SouthRunwayMeter { doc /* @S031,S114,S845,S900 */ }
    part def SouthportAirport { doc /* @S026 */ }
    part def StakeholderOrganization { doc /* @S048 */ }
    part def SurfaceSurveillanceAdapter { doc /* @S031,S179,S281,S445,S580,S606,S693,S802,S828,S979 */ }
    part def System { doc /* @S022,S023,S953 */ }
    part def SystemSupportEngineer { doc /* @S171,S732,S772,S807,S835,S877,S914,S916,S918,S923,S927 */ }
    part def TargetOffBlockTime { doc /* @S948 */ }
    part def TimeSynchronizationService { doc /* @S031,S098,S110,S187,S585,S778,S824,S957 */ }
    part def TowerSequenceManager { doc /* @S031,S242,S254,S297,S334,S380,S445,S450,S801,S844,S950,S980 */ }
    part def TowerSupervisor { doc /* @S060,S061,S089,S121,S143,S175,S181,S218,S243,S263,S277,S313,S358,S401,S500,S614,S693,S817,S866,S917 */ }
    part def TrainingAssessments { doc /* @S886 */ }
    part def TrajectoryPrediction { doc /* @S942 */ }
    part def WeatherIngestGateway { doc /* @S031,S057,S086,S102,S108,S111,S112,S182,S409,S943,S979 */ }
    part def WestApronSensor { doc /* @S031,S179,S845 */ }
    part def WorkstationLayouts { doc /* @S885 */ }
    part system {
        part accountableParticipant : AccountableParticipant;
        part advancedTurnaroundPrediction : AdvancedTurnaroundPrediction;
        part affectedComponent : AffectedComponent;
        part airTrafficControllers : AirTrafficControllers;
        part aircraftOperatorRepresentative : AircraftOperatorRepresentative {
            perform action a0 { doc /* validates that operator priorities are visible @S055 */ }
            perform action a1 { doc /* provides aircraft-specific constraints @S082 */ }
            perform action a2 { doc /* sends the Crew Duty Extension Log @S620 */ }
        }
        part airlineInterfaceAdapter : AirlineInterfaceAdapter {
            perform action a0 { doc /* validates message structure @S128 */ }
            perform action a1 { doc /* produces the Late Baggage Tag List @S452 */ }
            perform action a2 { doc /* accepts legality indicators @S618 */ }
        }
        part airlineOperationsCentre : AirlineOperationsCentre;
        part airlineOperationsCoordinator : AirlineOperationsCoordinator {
            perform action a0 { doc /* reviews material deviations from filed intent @S054 */ }
            perform action a1 { doc /* confirms that Flight Intent Message updates are complete, timely, and traceable @S081 */ }
            perform action a2 { doc /* evaluates each constraint @S138 */ }
            perform action a3 { doc /* reviews the proposed Target Off Block Time @S259 */ }
            perform action a4 { doc /* confirms whether each affected aircraft can absorb the assigned delay at stand @S362 */ }
            perform action a5 { doc /* reviews the proposed treatment for network impact @S403 */ }
            perform action a6 { doc /* sends the Passenger Misconnect Count @S740 */ }
        }
        part airportCDMPortal : AirportCDMPortal {
            perform action a0 { doc /* provides airport stakeholders with a controlled interface @S016 */ }
        }
        part airportDutyManager : AirportDutyManager {
            perform action a0 { doc /* confirms terminal opening status @S062 */ }
            perform action a1 { doc /* confirms that airport-side constraints are reflected consistently @S088 */ }
            perform action a2 { doc /* may request a manual capacity review @S116 */ }
            perform action a3 { doc /* monitors the Common Situation Display @S144 */ }
            perform action a4 { doc /* confirming transitions between Normal Operations, Adverse Weather Mode, Capacity Reduction State, and Recovery Phase @S162 */ }
            perform action a5 { doc /* can declare Normal Operations, Adverse Weather Mode, Capacity Reduction State, Recovery Phase, or Contingency Fallback State @S435 */ }
            perform action a6 { doc /* sets the recovery priority for stands @S471 */ }
            perform action a7 { doc /* sends the Medical Diversion Notice @S496 */ }
            perform action a8 { doc /* produces the Customs Hold Release Note @S568 */ }
        }
        part airportOnboarding : AirportOnboarding;
        part airportParticipant : AirportParticipant;
        part airspaceSectorPlanner : AirspaceSectorPlanner {
            perform action a0 { doc /* declares expected sector constraints @S058 */ }
            perform action a1 { doc /* validating sector constraints in the Sector Load Monitor @S079 */ }
            perform action a2 { doc /* converts confirmed restricted area information into sector availability assumptions @S326 */ }
            perform action a3 { doc /* confirms whether terminal and en-route sector loads can absorb the regulated stream @S402 */ }
            perform action a4 { doc /* may request a Tactical Regulation Proposal @S501 */ }
        }
        part alertDistributionHub : AlertDistributionHub {
            perform action a0 { doc /* routes notifications according to severity @S529 */ }
            perform action a1 { doc /* issues targeted alerts @S588 */ }
        }
        part arrivalRegulationConsole : ArrivalRegulationConsole {
            perform action a0 { doc /* highlights inbound demand periods @S070 */ }
            perform action a1 { doc /* applies airspace capacity reductions to inbound flows @S336 */ }
            perform action a2 { doc /* issues alerts before predicted holding stacks form @S407 */ }
            perform action a3 { doc /* applies the revised Airport Acceptance Rate @S698 */ }
        }
        part auditEventLedger : AuditEventLedger {
            perform action a0 { doc /* retains the trace from incoming forecast product to capacity value @S123 */ }
        }
        part availabilityTargets : AvailabilityTargets;
        part businessRulesRegistry : BusinessRulesRegistry;
        part calculatedTakeoffTime : CalculatedTakeoffTime;
        part candidateAirport : CandidateAirport;
        part capacityAssessmentModule : CapacityAssessmentModule {
            perform action a0 { doc /* supports the assessment of declared and tactical capacity @S014 */ }
            perform action a1 { doc /* combines the runway declaration, weather outlook, airspace constraints, stand readiness, and ground resource assumptions into a proposed Airport Acceptance Rate @S066 */ }
            perform action a2 { doc /* combines demand projections with the Airport Capacity Plan @S107 */ }
            perform action a3 { doc /* flags the associated capacity values as provisional @S120 */ }
            perform action a4 { doc /* recalculates the effective Airport Acceptance Rate @S341 */ }
            perform action a5 { doc /* compares that demand with the active Airport Acceptance Rate @S351 */ }
            perform action a6 { doc /* reduces practical departure capacity @S373 */ }
            perform action a7 { doc /* recalculates available capacity @S431 */ }
            perform action a8 { doc /* evaluates runway availability, stand availability, sector load, handling capacity, and service constraints @S494 */ }
        }
        part collaborativeDecisionLog : CollaborativeDecisionLog;
        part commonSituationDisplay : CommonSituationDisplay {
            perform action a0 { doc /* presents the approved pre-tactical baseline @S072 */ }
        }
        part contingencyOperationsConsole : ContingencyOperationsConsole {
            perform action a0 { doc /* provides a degraded channel for recording tower and duty desk decisions @S195 */ }
            perform action a1 { doc /* preserves the last valid allocation @S247 */ }
            perform action a2 { doc /* marks the resulting Slot Compliance State as provisional @S247 */ }
            perform action a3 { doc /* provides a protected operating position @S719 */ }
        }
        part criticalIncident : CriticalIncident;
        part cutoverDecision : CutoverDecision;
        part dataGovernanceSteward : DataGovernanceSteward {
            perform action a0 { doc /* verifies that operational decisions, role acknowledgements, and exception handling are captured in the Audit Event Ledger @S098 */ }
            perform action a1 { doc /* reviews audit samples @S273 */ }
        }
        part deicingCoordinator : DeicingCoordinator {
            perform action a0 { doc /* provides pre-tactical and tactical advice @S092 */ }
            perform action a1 { doc /* sends the Deicing Pad Queue Card @S294 */ }
            perform action a2 { doc /* maintains the active pad configuration @S375 */ }
            perform action a3 { doc /* marks the treatment as expired @S390 */ }
        }
        part demandPredictionService : DemandPredictionService {
            perform action a0 { doc /* estimates expected demand @S013 */ }
            perform action a1 { doc /* converts the normalized schedule into expected arrival and departure demand @S053 */ }
            perform action a2 { doc /* generates the demand forecast @S101 */ }
            perform action a3 { doc /* estimate arrival and departure loads by planning interval @S105 */ }
            perform action a4 { doc /* uses current airline intents to refine departure demand, arrival demand, and recovery demand @S131 */ }
            perform action a5 { doc /* estimates the departure demand profile @S350 */ }
            perform action a6 { doc /* updates short-term traffic forecasts @S430 */ }
        }
        part departureMeteringService : DepartureMeteringService {
            perform action a0 { doc /* estimates provisional Target Off Block Time sensitivity @S069 */ }
            perform action a1 { doc /* aligns each Target Off Block Time with the applicable Calculated Takeoff Time @S278 */ }
            perform action a2 { doc /* adjust departure release guidance @S335 */ }
            perform action a3 { doc /* converts runway demand into controlled stand delay @S348 */ }
            perform action a4 { doc /* withholds further push clearances @S379 */ }
            perform action a5 { doc /* sequences recovered departures @S483 */ }
            perform action a6 { doc /* suppresses release recommendations @S656 */ }
            perform action a7 { doc /* recalculates metering advisories @S686 */ }
        }
        part digitalBriefingRoom : DigitalBriefingRoom {
            perform action a0 { doc /* displays the emerging Airport Capacity Plan @S071 */ }
        }
        part eastApronSensor : EastApronSensor;
        part emergencyChanges : EmergencyChanges;
        part emergencyResponseCoordinator : EmergencyResponseCoordinator {
            perform action a0 { doc /* confirms rescue, medical, and airport safety readiness with the Airport Duty Manager @S499 */ }
        }
        part flightDataExchange : FlightDataExchange {
            perform action a0 { doc /* normalizes flight identifiers, aircraft types, routing fields, and planned operating times @S052 */ }
        }
        part futureReleases : FutureReleases;
        part gateConflictDetector : GateConflictDetector {
            perform action a0 { doc /* warns when continued stand holding would block an inbound allocation @S364 */ }
            perform action a1 { doc /* produces the Gate Reopening Memo @S386 */ }
        }
        part governance : Governance;
        part groundDelayProgram : GroundDelayProgram;
        part groundHandlingDispatcher : GroundHandlingDispatcher {
            perform action a0 { doc /* confirms whether planned handling teams and equipment coverage are sufficient @S064 */ }
            perform action a1 { doc /* escalates material deviations through the Airport Duty Manager @S091 */ }
            perform action a2 { doc /* sends the Crew Bus Delay Slip @S140 */ }
            perform action a3 { doc /* updates handling milestones @S261 */ }
            perform action a4 { doc /* updates boarding, loading, door closure, and tow readiness milestones @S292 */ }
            perform action a5 { doc /* updates remaining fluid inventory and truck serviceability @S383 */ }
            perform action a6 { doc /* sends the Towbar Shortage Report @S523 */ }
            perform action a7 { doc /* assigns qualified personnel to perform apron sweeps @S643 */ }
        }
        part handlingResourcePlanner : HandlingResourcePlanner {
            perform action a0 { doc /* compares the demand curve with available ground resources @S065 */ }
            perform action a1 { doc /* flags time bands @S065 */ }
            perform action a2 { doc /* compares fluid inventory with scheduled deicing demand @S384 */ }
            perform action a3 { doc /* assigns a severity level to the handler exception @S522 */ }
            perform action a4 { doc /* produces the Remote Stand Shuttle Count @S547 */ }
        }
        part harborEastAirport : HarborEastAirport;
        part highPriorityIncident : HighPriorityIncident;
        part identityAccessService : IdentityAccessService {
            perform action a0 { doc /* controls access to the Airport CDM Portal @S152 */ }
            perform action a1 { doc /* ensures that only users with the assigned operational role can approve frozen-time changes @S272 */ }
        }
        part incident : Incident;
        part initialPilot : InitialPilot;
        part integratedTacticalManagementPosition : IntegratedTacticalManagementPosition {
            perform action a0 { doc /* presents a combined tactical view @S420 */ }
        }
        part interfacePart : Interface;
        part interfaceCertification : InterfaceCertification;
        part lakesideRegionalAirport : LakesideRegionalAirport;
        part learningModels : LearningModels;
        part localTool : LocalTool;
        part localUsers : LocalUsers;
        part machineAssistedRecoveryOptions : MachineAssistedRecoveryOptions;
        part mediumAndLowPriorityIncidents : MediumAndLowPriorityIncidents;
        part meridianInternationalAirport : MeridianInternationalAirport;
        part meridianRegionalAirTrafficFlowManagementAndAirportCollaborativeDecisionMakingSystem : MeridianRegionalAirTrafficFlowManagementAndAirportCollaborativeDecisionMakingSystem;
        part meridianRegionalCapability : MeridianRegionalCapability;
        part meteorologyBriefingOfficer : MeteorologyBriefingOfficer {
            perform action a0 { doc /* provides the morning weather outlook @S056 */ }
            perform action a1 { doc /* produces the Storm Cell Snapshot @S085 */ }
            perform action a2 { doc /* briefs forecast confidence, timing risk, and expected operational impact @S086 */ }
            perform action a3 { doc /* states the trigger conditions @S087 */ }
            perform action a4 { doc /* confirms the trigger conditions in the Digital Briefing Room @S372 */ }
            perform action a5 { doc /* verifies weather impacts shown from the Weather Ingest Gateway @S434 */ }
        }
        part migrationPlan : MigrationPlan;
        part militaryAirspaceLiaison : MilitaryAirspaceLiaison {
            perform action a0 { doc /* confirms whether shared airspace assumptions remain valid @S059 */ }
            perform action a1 { doc /* sends the Temporary Restriction Notice @S325 */ }
        }
        part networkOperationsLiaison : NetworkOperationsLiaison {
            perform action a0 { doc /* coordinates with adjacent network units @S083 */ }
            perform action a1 { doc /* coordinates with external network positions @S339 */ }
            perform action a2 { doc /* coordinates with affected airline control centers @S413 */ }
        }
        part northRunwayMeter : NorthRunwayMeter {
            perform action a0 { doc /* reduces the departure release rate @S454 */ }
        }
        part northValleyAirport : NorthValleyAirport;
        part onboardingWave : OnboardingWave;
        part operationalUser : OperationalUser;
        part participatingAirportNetwork : ParticipatingAirportNetwork;
        part participatingOrganization : ParticipatingOrganization;
        part performanceAnalyticsWarehouse : PerformanceAnalyticsWarehouse {
            perform action a0 { doc /* retains the baseline inputs, capacity declarations, and approval timestamps @S074 */ }
            perform action a1 { doc /* compares submitted intents, issued constraints, actual off-block times, and achieved arrival outcomes @S148 */ }
        }
        part pilotAirportSelection : PilotAirportSelection;
        part plannedChangeWindows : PlannedChangeWindows;
        part postExerciseReviews : PostExerciseReviews;
        part postIncidentReview : PostIncidentReview;
        part postOperationsReport : PostOperationsReport;
        part rampControlLead : RampControlLead {
            perform action a0 { doc /* reviews early stand readiness @S063 */ }
            perform action a1 { doc /* maintains the Ramp Movement Board @S090 */ }
            perform action a2 { doc /* uses the Ramp Movement Board to identify whether the proposed recovery action can be supported @S142 */ }
            perform action a3 { doc /* maintains the operational sequence for pushbacks, stand exits, stand entries, and towing movements @S200 */ }
            perform action a4 { doc /* sends the Stand Tow Request Form @S208 */ }
            perform action a5 { doc /* coordinates with the Ground Handling Dispatcher @S211 */ }
            perform action a6 { doc /* increases spacing between pushbacks and towing movements @S219 */ }
            perform action a7 { doc /* reviews the proposed windows @S357 */ }
            perform action a8 { doc /* coordinates stand reopening with the Ground Handling Dispatcher @S473 */ }
            perform action a9 { doc /* sends the Apron Sweep Completion Note @S647 */ }
        }
        part rampMovementBoard : RampMovementBoard {
            perform action a0 { doc /* maintains milestone timestamps @S255 */ }
            perform action a1 { doc /* produces the Fuel Truck Hold Advice @S361 */ }
        }
        part rampPersonnel : RampPersonnel;
        part readinessGate1 : ReadinessGate1;
        part readinessGate2 : ReadinessGate2;
        part readinessGate3 : ReadinessGate3;
        part readinessGate4 : ReadinessGate4;
        part recoveryRecommendations : RecoveryRecommendations;
        part regionalExpansion : RegionalExpansion;
        part regionalFlowManager : RegionalFlowManager {
            perform action a0 { doc /* balancing demand against capacity across the Meridian region @S010 */ }
            perform action a1 { doc /* coordinating regional traffic management actions @S010 */ }
            perform action a2 { doc /* owns the baseline process @S050 */ }
            perform action a3 { doc /* reviews the Airport Capacity Plan, the Ground Delay Program status, and any Tactical Regulation Proposal @S078 */ }
            perform action a4 { doc /* authorizes changes to flow measures @S094 */ }
            perform action a5 { doc /* uses the Common Situation Display to compare forecast demand, assessed capacity, and any active Ground Delay Program effects @S117 */ }
            perform action a6 { doc /* may authorize temporary rule changes @S228 */ }
            perform action a7 { doc /* approved shorter recalculation cycles @S246 */ }
            perform action a8 { doc /* assesses whether the effect is localized to one stream @S327 */ }
            perform action a9 { doc /* decides whether to absorb the impact @S343 */ }
            perform action a10 { doc /* may increase stand absorption @S367 */ }
            perform action a11 { doc /* authorizes a controlled transition from Capacity Reduction State toward Recovery Phase @S393 */ }
            perform action a12 { doc /* evaluates regulation options in the Arrival Regulation Console @S396 */ }
            perform action a13 { doc /* may apply a tactical landing-rate reduction @S410 */ }
            perform action a14 { doc /* maintain a ranked view of candidate diversions @S492 */ }
            perform action a15 { doc /* applies the last verified Airport Capacity Plan @S721 */ }
        }
        part regionalFlowPlatform : RegionalFlowPlatform {
            perform action a0 { doc /* creates the initial demand picture @S051 */ }
            perform action a1 { doc /* permits more frequent intent updates @S147 */ }
            perform action a2 { doc /* creates the initial Target Off Block Time proposal @S250 */ }
            perform action a3 { doc /* locks the Target Off Block Time @S268 */ }
            perform action a4 { doc /* marks a proposed Target Off Block Time as conditional @S314 */ }
            perform action a5 { doc /* normalizes each Flight Intent Message against the current Airport Capacity Plan @S349 */ }
            perform action a6 { doc /* synchronizes the tactical display with the Time Synchronization Service @S422 */ }
            exhibit state modes {
                state s0 { doc /* Adverse Weather Mode @S047 */ }
                state s1 { doc /* Capacity Reduction State @S047 */ }
                state s2 { doc /* Contingency Fallback State @S047 */ }
                state s3 { doc /* Normal Operations @S047 */ }
                state s4 { doc /* Recovery Phase @S047 */ }
                state s5 { doc /* Slot Compliance State @S047 */ }
                state s6 { doc /* winter operating mode @S371 */ }
            }
        }
        part sectorLoadMonitor : SectorLoadMonitor {
            perform action a0 { doc /* highlights intervals where overload is likely @S329 */ }
            perform action a1 { doc /* produces the Departure Fix Load Sheet @S484 */ }
        }
        part serviceDesk : ServiceDesk;
        part serviceLevelTargets : ServiceLevelTargets;
        part serviceModel : ServiceModel;
        part simulationExercises : SimulationExercises;
        part slotAllocationEngine : SlotAllocationEngine {
            perform action a0 { doc /* supports fair and traceable allocation of constrained departure and arrival opportunities @S015 */ }
            perform action a1 { doc /* converts accepted constraints into Calculated Takeoff Time values and Target Off Block Time guidance @S134 */ }
            perform action a2 { doc /* derives the Calculated Takeoff Time @S253 */ }
            perform action a3 { doc /* produces the Pushback Window Token @S428 */ }
            perform action a4 { doc /* evaluates the candidate swap @S669 */ }
        }
        part slotComplianceState : SlotComplianceState;
        part slotCoordinator : SlotCoordinator {
            perform action a0 { doc /* uses the Slot Allocation Engine to prepare an initial slot feasibility view @S068 */ }
            perform action a1 { doc /* confirms that the Slot Allocation Engine applies the current Business Rules Registry parameters @S080 */ }
            perform action a2 { doc /* reviews airline requests for priority handling @S136 */ }
            perform action a3 { doc /* checking Calculated Takeoff Time feasibility @S161 */ }
            perform action a4 { doc /* administers the allocation run @S229 */ }
            perform action a5 { doc /* reviews proposed Calculated Takeoff Time values against network constraints @S258 */ }
            perform action a6 { doc /* verifies that any proposed resequencing remains compatible with the Calculated Takeoff Time tolerance @S285 */ }
            perform action a7 { doc /* sends the Slot Swap Permission Email @S672 */ }
            perform action a8 { doc /* initiates manual slot procedures @S722 */ }
        }
        part southRunwayMeter : SouthRunwayMeter;
        part southportAirport : SouthportAirport;
        part stakeholderOrganization : StakeholderOrganization;
        part surfaceSurveillanceAdapter : SurfaceSurveillanceAdapter {
            perform action a0 { doc /* confirms whether an aircraft is still at stand @S281 */ }
            perform action a1 { doc /* normalizes apron sensing data @S580 */ }
            perform action a2 { doc /* produces the Runway Lighting Outage Card @S606 */ }
        }
        part systemPart : System;
        part systemSupportEngineer : SystemSupportEngineer {
            perform action a0 { doc /* monitors portal availability, interface latency, user session faults, and synchronization status @S171 */ }
            perform action a1 { doc /* isolates failed components @S732 */ }
        }
        part targetOffBlockTime : TargetOffBlockTime;
        part timeSynchronizationService : TimeSynchronizationService;
        part towerSequenceManager : TowerSequenceManager {
            perform action a0 { doc /* maintains the tactical runway sequence expectation @S254 */ }
            perform action a1 { doc /* reserves departure sequence positions @S380 */ }
        }
        part towerSupervisor : TowerSupervisor {
            perform action a0 { doc /* sends the Runway Inspection Note @S060 */ }
            perform action a1 { doc /* declares anticipated runway configuration @S061 */ }
            perform action a2 { doc /* confirms that the Tower Sequence Manager reflects the current runway configuration @S089 */ }
            perform action a3 { doc /* reviews metering effects in the Tower Sequence Manager @S143 */ }
            perform action a4 { doc /* may reject a proposed departure opportunity @S243 */ }
            perform action a5 { doc /* may challenge a proposed Calculated Takeoff Time @S263 */ }
            perform action a6 { doc /* uses the Tower Sequence Manager to confirm that each flight can be advanced @S277 */ }
            perform action a7 { doc /* monitors whether the planned release rate remains compatible @S358 */ }
            perform action a8 { doc /* confirms whether the proposed landing rate is compatible @S401 */ }
            perform action a9 { doc /* coordinates airborne sequencing with the Airspace Sector Planner @S500 */ }
        }
        part trainingAssessments : TrainingAssessments;
        part trajectoryPrediction : TrajectoryPrediction;
        part weatherIngestGateway : WeatherIngestGateway {
            perform action a0 { doc /* preserves the forecast issue time @S057 */ }
            perform action a1 { doc /* normalizes external and local meteorological feeds @S102 */ }
            perform action a2 { doc /* accepts aviation forecasts @S108 */ }
            perform action a3 { doc /* marks the feed as degraded @S111 */ }
            perform action a4 { doc /* updates the arrival model @S409 */ }
        }
        part westApronSensor : WestApronSensor;
        part workstationLayouts : WorkstationLayouts;
        flow f0 of MorningWeatherOutlookItem from weatherIngestGateway to capacityAssessmentModule { doc /* @S057 */ }
        flow f1 of UnresolvedAssumptionsItem from digitalBriefingRoom to collaborativeDecisionLog { doc /* @S071 */ }
        flow f2 of ExternalCoordinationOutcomesItem from networkOperationsLiaison to collaborativeDecisionLog { doc /* @S084 */ }
        flow f3 of WeatherDataItem from weatherIngestGateway to meteorologyBriefingOfficer { doc /* @S086 */ }
        flow f4 of CivilRoutingConstraintAlertItem from militaryAirspaceLiaison to regionalFlowManager { doc /* @S093 */ }
        flow f5 of SynchronizedTimestampsItem from timeSynchronizationService to auditEventLedger { doc /* @S098 */ }
        flow f6 of DemandForecastItem from demandPredictionService to regionalFlowPlatform { doc /* @S101 */ }
        flow f7 of FiledFlightInformationItem from flightDataExchange to demandPredictionService { doc /* @S103 */ }
        flow f8 of DemandProjectionsItem from demandPredictionService to capacityAssessmentModule { doc /* @S107 */ }
        flow f9 of DegradedWeatherInputsItem from weatherIngestGateway to meteorologyBriefingOfficer { doc /* @S112 */ }
        flow f10 of RunwaySpecificCapacityValuesItem from capacityAssessmentModule to northRunwayMeter { doc /* @S114 */ }
        flow f11 of RunwaySpecificCapacityValuesItem from capacityAssessmentModule to southRunwayMeter { doc /* @S114 */ }
        flow f12 of CapacityPictureChangeNotificationItem from alertDistributionHub to regionalFlowManager { doc /* @S121 */ }
        flow f13 of CapacityPictureChangeNotificationItem from alertDistributionHub to towerSupervisor { doc /* @S121 */ }
        flow f14 of CapacityPictureChangeNotificationItem from alertDistributionHub to airlineOperationsCoordinator { doc /* @S121 */ }
        flow f15 of FlightIntentMessageItem from airlineOperationsCentre to airlineInterfaceAdapter { doc /* @S126 */ }
        flow f16 of AcceptedIntentDataItem from airlineInterfaceAdapter to flightDataExchange { doc /* @S128 */ }
        flow f17 of StormCellSnapshotItem from meteorologyBriefingOfficer to capacityAssessmentModule { doc /* @S133 */ }
        flow f18 of ConstraintsItem from airlineInterfaceAdapter to airlineOperationsCentre { doc /* @S135 */ }
        flow f19 of CurrentRegionalDemandAndConstraintContextItem from regionalFlowPlatform to airportCDMPortal { doc /* @S164 */ }
        flow f20 of ConditionsThatMayAffectRunwayTaxiwayStandOrApronAvailabilityItem from towerSupervisor to airportDutyManager { doc /* @S175 */ }
        flow f21 of PositionUpdatesItem from eastApronSensor to surfaceSurveillanceAdapter { doc /* @S179 */ }
        flow f22 of PositionUpdatesItem from westApronSensor to surfaceSurveillanceAdapter { doc /* @S179 */ }
        flow f23 of MovementIndicationsItem from surfaceSurveillanceAdapter to airportCDMPortal { doc /* @S179 */ }
        flow f24 of RunwayInspectionNoteItem from towerSupervisor to airportDutyManager { doc /* @S181 */ }
        flow f25 of DutyDeskConfirmationTransactionsItem from identityAccessService to auditEventLedger { doc /* @S194 */ }
        flow f26 of OverlappingOccupancyAlertItem from gateConflictDetector to rampControlLead { doc /* @S210 */ }
        flow f27 of ApronCongestionConditionItem from rampControlLead to towerSupervisor { doc /* @S218 */ }
        flow f28 of ApronCongestionConditionItem from rampControlLead to airportDutyManager { doc /* @S218 */ }
        flow f29 of MovementUpdatesItem from rampMovementBoard to auditEventLedger { doc /* @S222 */ }
        flow f30 of DemandItem from demandPredictionService to slotAllocationEngine { doc /* @S225 */ }
        flow f31 of ConstraintsItem from capacityAssessmentModule to slotAllocationEngine { doc /* @S225 */ }
        flow f32 of CrewBusDelaySlipItem from groundHandlingDispatcher to airlineOperationsCoordinator { doc /* @S237 */ }
        flow f33 of AcceptedOrRejectedExemptionItem from slotCoordinator to collaborativeDecisionLog { doc /* @S239 */ }
        flow f34 of ProposedDepartureOpportunitiesAndAssociatedCalculatedTakeoffTimeValuesItem from departureMeteringService to towerSequenceManager { doc /* @S242 */ }
        flow f35 of ActiveSpacingRulesItem from businessRulesRegistry to towerSequenceManager { doc /* @S297 */ }
        flow f36 of ExpectedServiceCompletionTimesItem from groundHandlingDispatcher to handlingResourcePlanner { doc /* @S302 */ }
        flow f37 of StandTowRequestFormItem from rampControlLead to handlingResourcePlanner { doc /* @S304 */ }
        flow f38 of ResourceDrivenFeasibilityStatusItem from airportCDMPortal to airlineOperationsCoordinator { doc /* @S312 */ }
        flow f39 of ResourceDrivenFeasibilityStatusItem from airportCDMPortal to aircraftOperatorRepresentative { doc /* @S312 */ }
        flow f40 of SubscriptionRulesItem from businessRulesRegistry to alertDistributionHub { doc /* @S332 */ }
        flow f41 of AirspaceAlertAcknowledgementAndDownstreamDecisionItem from regionalFlowPlatform to auditEventLedger { doc /* @S333 */ }
        flow f42 of ActiveRestrictionStatusItem from airportCDMPortal to commonSituationDisplay { doc /* @S337 */ }
        flow f43 of ReconsiderationRequestItem from aircraftOperatorRepresentative to airportCDMPortal { doc /* @S363 */ }
        flow f44 of AffectedRunwayQueueHighlightItem from alertDistributionHub to commonSituationDisplay { doc /* @S366 */ }
        flow f45 of DeicingPadQueueCardItem from deicingCoordinator to rampControlLead { doc /* @S378 */ }
        flow f46 of TemporaryRestrictionNoticeItem from militaryAirspaceLiaison to regionalFlowManager { doc /* @S399 */ }
        flow f47 of OperationalBasisForCandidateAirportAcceptanceRateValuesItem from capacityAssessmentModule to commonSituationDisplay { doc /* @S400 */ }
        flow f48 of ArrivalPlanItem from airportCDMPortal to aircraftOperatorRepresentative { doc /* @S405 */ }
        flow f49 of AgreedTargetOffBlockTimeValuesAndStakeholderRemarksItem from airportCDMPortal to integratedTacticalManagementPosition { doc /* @S429 */ }
        flow f50 of MovementAreaOccupancyAndEquipmentStatusIndicatorsItem from surfaceSurveillanceAdapter to rampMovementBoard { doc /* @S445 */ }
        flow f51 of MovementAreaOccupancyAndEquipmentStatusIndicatorsItem from surfaceSurveillanceAdapter to towerSequenceManager { doc /* @S445 */ }
        flow f52 of OperationalSignificanceOfTheConditionItem from airportDutyManager to airportCDMPortal { doc /* @S447 */ }
        flow f53 of FuelTruckHoldAdviceItem from rampMovementBoard to towerSequenceManager { doc /* @S450 */ }
        flow f54 of CandidatePushbackSpacingItem from departureMeteringService to slotAllocationEngine { doc /* @S456 */ }
        flow f55 of GateReopeningMemoItem from gateConflictDetector to airlineOperationsCoordinator { doc /* @S472 */ }
        flow f56 of PushbackWindowTokenItem from slotAllocationEngine to airportCDMPortal { doc /* @S503 */ }
        flow f57 of DiversionRationalePriorityClassificationResourceCommitmentAndAgreedRecoveryTargetItem from digitalBriefingRoom to collaborativeDecisionLog { doc /* @S506 */ }
        flow f58 of LateBaggageTagListItem from airlineInterfaceAdapter to groundHandlingDispatcher { doc /* @S519 */ }
        flow f59 of PlannedRemoteStandOperatingPostureItem from airportDutyManager to airportCDMPortal { doc /* @S544 */ }
        flow f60 of TowbarShortageReportItem from groundHandlingDispatcher to rampControlLead { doc /* @S556 */ }
        flow f61 of MedicalDiversionNoticeItem from airportDutyManager to arrivalRegulationConsole { doc /* @S576 */ }
        flow f62 of ScheduledMovementsItem from flightDataExchange to regionalFlowPlatform { doc /* @S593 */ }
        flow f63 of PredictedReadinessItem from demandPredictionService to regionalFlowPlatform { doc /* @S593 */ }
        flow f64 of DepartureFixLoadSheetItem from sectorLoadMonitor to regionalFlowManager { doc /* @S598 */ }
        flow f65 of NotificationsItem from alertDistributionHub to regionalFlowManager { doc /* @S614 */ }
        flow f66 of NotificationsItem from alertDistributionHub to towerSupervisor { doc /* @S614 */ }
        flow f67 of NotificationsItem from alertDistributionHub to rampControlLead { doc /* @S614 */ }
        flow f68 of NotificationsItem from alertDistributionHub to slotCoordinator { doc /* @S614 */ }
        flow f69 of NotificationsItem from alertDistributionHub to networkOperationsLiaison { doc /* @S614 */ }
        flow f70 of RemoteStandShuttleCountItem from handlingResourcePlanner to airportCDMPortal { doc /* @S648 */ }
        flow f71 of ProposedSubstitutionItem from airlineOperationsCoordinator to airportCDMPortal { doc /* @S667 */ }
        flow f72 of ApronSweepCompletionNoteItem from rampControlLead to airportDutyManager { doc /* @S678 */ }
        flow f73 of CustomsHoldReleaseNoteItem from airportDutyManager to airlineOperationsCoordinator { doc /* @S679 */ }
        flow f74 of RunwayLightingOutageCardItem from surfaceSurveillanceAdapter to towerSupervisor { doc /* @S693 */ }
        flow f75 of RevisedInputsItem from departureMeteringService to slotAllocationEngine { doc /* @S699 */ }
        flow f76 of CrewDutyExtensionLogItem from aircraftOperatorRepresentative to slotCoordinator { doc /* @S726 */ }
        flow f77 of PassengerMisconnectCountItem from airlineOperationsCoordinator to departureMeteringService { doc /* @S851 */ }
        flow f78 of SlotSwapPermissionEmailItem from slotCoordinator to airlineOperationsCoordinator { doc /* @S795 */ }
        flow f79 of SlotComplianceEventsItem from regionalFlowPlatform to auditEventLedger { doc /* @S789 */ }
    }
    requirement def R0 { doc /* During Adverse Weather Mode or Capacity Reduction State, the system must support rapid development of a Tactical Regulation Proposal and consistent communication of the resulting Ground Delay Program when one is required. @S022 */ subject s : System; }
    requirement def R1 { doc /* During Recovery Phase, the system must help stakeholders restore scheduled flow while monitoring Target Off Block Time, Calculated Takeoff Time, and Slot Compliance State performance. @S023 */ subject s : System; }
    requirement def R2 { doc /* Participation in the regional system requires each stakeholder organization to assign accountable representatives, maintain current contact details, follow agreed data use rules, and support post-operational review of decisions made through the Regional Flow Platform. @S048 */ subject s : StakeholderOrganization; }
    requirement def R3 { doc /* identifies any conditional availability that must be treated as uncertain @S059 */ subject s : MilitaryAirspaceLiaison; }
    requirement def R4 { doc /* changes must be entered through controlled Regional Flow Platform functions @S073 */ subject s : RegionalFlowPlatform; }
    requirement def R5 { doc /* outputs must remain visible on the Common Situation Display @S095 */ subject s : DepartureMeteringService; }
    requirement def R6 { doc /* outputs must remain visible on the Common Situation Display @S095 */ subject s : ArrivalRegulationConsole; }
    requirement def R7 { doc /* Escalation to the Emergency Response Coordinator is required when a safety event, security event, or emergency response activity may affect airport acceptance, surface movement, or airspace availability. @S096 */ subject s : EmergencyResponseCoordinator; }
    requirement def R8 { doc /* Cedarbell shall expose the current regional demand and constraint context to the shared workspace at each publication cycle without requiring manual re-entry. @S164 */ subject s : RegionalFlowPlatform; }
    requirement def R9 { doc /* When a milestone becomes stale, the Airport CDM Portal shall highlight the affected flight and notify the role accountable for the next update through the Alert Distribution Hub. @S166 */ subject s : AirportCDMPortal; }
    requirement def R10 { doc /* Each airport participant shall update a material change within two minutes of becoming aware of it during Normal Operations and within one minute during Adverse Weather Mode or Capacity Reduction State. @S167 */ subject s : AirportParticipant; }
    requirement def R11 { doc /* If the exact value is not yet known, the accountable participant shall enter a provisional value with an uncertainty flag rather than leaving the milestone unchanged. @S168 */ subject s : AccountableParticipant; }
    requirement def R12 { doc /* During Contingency Fallback State, the Airport CDM Portal shall preserve the last synchronized milestone set and clearly mark any updates entered under degraded operating procedures. @S172 */ subject s : AirportCDMPortal; }
    requirement def R13 { doc /* Orchard shall issue time-stamped weather condition updates for use in tower and airport duty coordination. @S182 */ subject s : WeatherIngestGateway; }
    requirement def R14 { doc /* The Time Synchronization Service shall keep tower, duty desk, surveillance, and portal event times aligned so that later review can reconstruct the sequence of events. @S187 */ subject s : TimeSynchronizationService; }
    requirement def R15 { doc /* The Ramp Control Lead shall not release a pushback until the Tower Supervisor has confirmed that the movement can be integrated with the active ground route and runway plan. @S202 */ subject s : RampControlLead; }
    requirement def R16 { doc /* Airline Operations Coordinator participation is required when a resequence would materially affect passenger boarding, connection protection, or aircraft rotation plans. @S214 */ subject s : AirlineOperationsCoordinator; }
    requirement def R17 { doc /* Marlinstone shall refresh stand demand forecasts when the Ramp Movement Board records a material change in planned off-block timing. @S216 */ subject s : DemandPredictionService; }
    requirement def R18 { doc /* The engine shall not improve one operator's position by imposing an excessive delay on another operator unless the rule basis is visible and logged. @S234 */ subject s : SlotAllocationEngine; }
    requirement def R19 { doc /* Saffron shall confirm any operator-requested Target Off Block Time revision in the Airport CDM Portal before the freeze horizon expires. @S260 */ subject s : AirlineOperationsCoordinator; }
    requirement def R20 { doc /* Foxglove shall publish tower readiness changes to authenticated airline and handling users within the configured refresh interval. @S293 */ subject s : AirportCDMPortal; }
    requirement def R21 { doc /* Brindle must confirm that any revised off-block sequence remains compatible with the Departure Metering Service before the change is released to the airport community. @S313 */ subject s : TowerSupervisor; }
    requirement def R22 { doc /* Ironleaf must refresh affected departure sequence advisories when a restriction changes the usable departure routes or expected release spacing. @S334 */ subject s : TowerSequenceManager; }
    requirement def R23 { doc /* Blueharbor shall adjust allocated departure times when metering rules require additional stand absorption to preserve the planned runway sequence. @S355 */ subject s : SlotAllocationEngine; }
    requirement def R24 { doc /* Quartzline must coordinate every pad release with the Tower Supervisor before the aircraft leaves the treated area. @S387 */ subject s : RampControlLead; }
    requirement def R25 { doc /* Skylark must refresh the apron movement layer within five seconds of each validated surface event. @S427 */ subject s : RampMovementBoard; }
    requirement def R26 { doc /* Lantern must distribute surface equipment and apron congestion advisories to subscribed operational roles within the latency target defined in the Business Rules Registry. @S461 */ subject s : AlertDistributionHub; }
    requirement def R27 { doc /* Nightjar shall suppress handler-exception annotations for arriving flights unless the exception changes the Airport Acceptance Rate or a regulated arrival sequence. @S535 */ subject s : ArrivalRegulationConsole; }
    requirement def R28 { doc /* The Time Synchronization Service is required because customs status events and apron sensor events must align with Calculated Takeoff Time and Target Off Block Time decisions. @S585 */ subject s : TimeSynchronizationService; }
    requirement def R29 { doc /* The Departure Metering Service may remain in monitoring mode while manual slot control is active, but it must not automatically overwrite issued times. @S728 */ subject s : DepartureMeteringService; }
    requirement def R30 { doc /* Each named operational user shall authenticate with an individually assigned identity before accessing the Airport CDM Portal, Digital Briefing Room, or any operational console. @S764 */ subject s : OperationalUser; }
    requirement def R31 { doc /* Role profiles shall grant the minimum access needed to view, propose, approve, or administer operational data within the Regional Flow Platform. @S767 */ subject s : RegionalFlowPlatform; }
    requirement def R32 { doc /* operational approval privileges shall remain separated from technical administration privileges @S772 */ subject s : SystemSupportEngineer; }
    requirement def R33 { doc /* Operational segregation shall prevent a single user from creating, approving, and technically concealing a material change to a Ground Delay Program, Airport Acceptance Rate, or Tactical Regulation Proposal. @S774 */ subject s : RegionalFlowPlatform; }
    requirement def R34 { doc /* Where dual control is required, the Regional Flow Platform shall record the initiating user, the approving user, the affected operational object, and the effective time of the decision. @S775 */ subject s : RegionalFlowPlatform; }
    requirement def R35 { doc /* Access to the Performance Analytics Warehouse shall be restricted to authorized analytical roles and shall not allow retrospective alteration of operational records held in the Audit Event Ledger. @S776 */ subject s : PerformanceAnalyticsWarehouse; }
    requirement def R36 { doc /* The Audit Event Ledger shall capture successful and failed authentication attempts, role changes, privilege elevations, operational approvals, configuration changes, data exports, and emergency access activations. @S777 */ subject s : AuditEventLedger; }
    requirement def R37 { doc /* All audit records shall use time derived from the Time Synchronization Service so that investigations can reconstruct event order across the Airport CDM Portal, Slot Allocation Engine, and Alert Distribution Hub. @S778 */ subject s : TimeSynchronizationService; }
    requirement def R38 { doc /* Audit records shall be protected against ordinary user modification and retained for a period agreed by the airport operator, regional authority, and participating aircraft operators. @S779 */ subject s : AuditEventLedger; }
    requirement def R39 { doc /* Security monitoring shall alert the System Support Engineer and Data Governance Steward when unusual access patterns indicate possible credential compromise or inappropriate privilege use. @S780 */ subject s : RegionalFlowPlatform; }
    requirement def R40 { doc /* The Identity Access Service shall support rapid suspension of accounts when a user changes role, leaves an organization, or becomes subject to an operational integrity concern. @S781 */ subject s : IdentityAccessService; }
    requirement def R41 { doc /* Temporary access shall have a defined sponsor, purpose, role scope, and expiry time, and shall be reviewed after the operational need has ended. @S782 */ subject s : IdentityAccessService; }
    requirement def R42 { doc /* Silverpine shall accept emergency access activations only after the Identity Access Service records the authorizing incident reference and expiry time. @S783 */ subject s : ContingencyOperationsConsole; }
    requirement def R43 { doc /* Use of emergency access shall generate prominent audit events and shall require post-event review by the Data Governance Steward and the responsible operational authority. @S785 */ subject s : DataGovernanceSteward; }
    requirement def R44 { doc /* During Contingency Fallback State, access control shall continue to enforce role separation even when some integrations are unavailable and manual coordination becomes necessary. @S786 */ subject s : IdentityAccessService; }
    requirement def R45 { doc /* When normal connectivity is restored, the Regional Flow Platform shall reconcile contingency actions with the Collaborative Decision Log so that accountability is preserved across the full incident timeline. @S787 */ subject s : RegionalFlowPlatform; }
    requirement def R46 { doc /* After connectivity is restored, audit processing shall treat reconciled contingency actions as part of the same operational record as actions taken during Normal Operations. @S788 */ subject s : AuditEventLedger; }
    requirement def R47 { doc /* The Regional Flow Platform shall record slot compliance events in the Audit Event Ledger using the operating date, flight identifier, airport, runway direction, and applicable regulation reference. @S789 */ subject s : RegionalFlowPlatform; }
    requirement def R48 { doc /* Each compliance assessment shall compare the Calculated Takeoff Time, the Target Off Block Time, actual off-block time, and actual takeoff time against the tolerance defined in the Business Rules Registry. @S790 */ subject s : RegionalFlowPlatform; }
    requirement def R49 { doc /* The Slot Compliance State shall indicate whether a flight was compliant, early, late, exempted, substituted, cancelled, or pending review at the end of the traffic period. @S791 */ subject s : SlotComplianceState; }
    requirement def R50 { doc /* The Audit Event Ledger shall preserve the time source applied by the Time Synchronization Service so that later review can distinguish operational delay from data latency. @S792 */ subject s : AuditEventLedger; }
    requirement def R51 { doc /* User decisions entered through the Airport CDM Portal shall be linked to the authenticated role provided by the Identity Access Service. @S793 */ subject s : AirportCDMPortal; }
    requirement def R52 { doc /* The Collaborative Decision Log shall retain the stated reason, decision time, affected flight, and visible operational context for each material change to a slot or sequence. @S794 */ subject s : CollaborativeDecisionLog; }
    requirement def R53 { doc /* Substitution records shall show the original flight, replacement flight, assigned Calculated Takeoff Time, acceptance status, and any subsequent cancellation or reversion. @S796 */ subject s : RegionalFlowPlatform; }
    requirement def R54 { doc /* When an Aircraft Operator Representative proposes a substitution, the audit trail shall capture whether the change preserved the constraints of the active Ground Delay Program. @S797 */ subject s : AuditEventLedger; }
    requirement def R55 { doc /* The Slot Coordinator shall review substitution activity after operations to confirm that priority rules were applied consistently across participating operators. @S798 */ subject s : SlotCoordinator; }
    requirement def R56 { doc /* Late operational changes shall be distinguished from planned updates by comparing the change timestamp with the freeze horizon held in the Business Rules Registry. @S799 */ subject s : BusinessRulesRegistry; }
    requirement def R57 { doc /* Changes made inside the freeze horizon shall require a reason code and shall be visible to the Regional Flow Manager during post-operations review. @S800 */ subject s : RegionalFlowManager; }
    requirement def R58 { doc /* The Tower Sequence Manager and Ramp Movement Board shall provide actual movement milestones that support independent verification of slot performance. @S801 */ subject s : TowerSequenceManager; }
    requirement def R59 { doc /* The Tower Sequence Manager and Ramp Movement Board shall provide actual movement milestones that support independent verification of slot performance. @S801 */ subject s : RampMovementBoard; }
    requirement def R60 { doc /* Surface movement evidence from the Surface Surveillance Adapter shall be retained long enough to support dispute resolution and regulatory audit requests. @S802 */ subject s : SurfaceSurveillanceAdapter; }
    requirement def R61 { doc /* Capacity changes made through the Capacity Assessment Module shall be correlated with the active Airport Capacity Plan and Airport Acceptance Rate used at the time of allocation. @S803 */ subject s : CapacityAssessmentModule; }
    requirement def R62 { doc /* The Performance Analytics Warehouse shall aggregate compliance outcomes by carrier, route group, regulation, airport operating configuration, and time band. @S804 */ subject s : PerformanceAnalyticsWarehouse; }
    requirement def R63 { doc /* Aggregated metrics shall support review of systemic lateness without exposing commercially sensitive detail beyond authorized roles. @S805 */ subject s : PerformanceAnalyticsWarehouse; }
    requirement def R64 { doc /* The Data Governance Steward shall verify that audit fields required for slot performance reporting remain complete, immutable, and traceable to approved data definitions. @S806 */ subject s : DataGovernanceSteward; }
    requirement def R65 { doc /* The System Support Engineer shall investigate technical gaps when audit sequences show missing events, duplicate updates, or inconsistent timestamps. @S807 */ subject s : SystemSupportEngineer; }
    requirement def R66 { doc /* The Regional Flow Manager shall use the Post Operations Report to identify whether noncompliance resulted from operator choice, airport constraint, airspace constraint, weather impact, or system issue. @S808 */ subject s : RegionalFlowManager; }
    requirement def R67 { doc /* The Airport Duty Manager shall review late airport-driven changes that affected multiple flights and shall record whether the operational justification was valid. @S809 */ subject s : AirportDutyManager; }
    requirement def R68 { doc /* Findings from the review shall feed adjustments to tolerance values, reason code definitions, and training material, subject to change control. @S810 */ subject s : RegionalFlowPlatform; }
    requirement def R69 { doc /* All audit outputs shall be retained according to the approved records schedule and shall remain searchable for compliance investigations, performance meetings, and lessons-learned activity. @S811 */ subject s : AuditEventLedger; }
    requirement def R70 { doc /* Data governance for the Regional Flow Platform shall assign accountable owners to each operational data domain and shall make those assignments visible in the Airport CDM Portal. @S812 */ subject s : RegionalFlowPlatform; }
    requirement def R71 { doc /* The Data Governance Steward shall maintain the data ownership register and shall coordinate updates through the Business Rules Registry. @S813 */ subject s : DataGovernanceSteward; }
    requirement def R72 { doc /* The Regional Flow Manager shall own flow management policy data, including Ground Delay Program parameters and Tactical Regulation Proposal status values. @S814 */ subject s : RegionalFlowManager; }
    requirement def R73 { doc /* The Slot Coordinator shall own slot allocation reference data, including Calculated Takeoff Time tolerances and Slot Compliance State definitions. @S815 */ subject s : SlotCoordinator; }
    requirement def R74 { doc /* The Airport Duty Manager shall own airport capacity declarations, including Airport Capacity Plan records and Airport Acceptance Rate values. @S816 */ subject s : AirportDutyManager; }
    requirement def R75 { doc /* The Tower Supervisor shall own tower sequence status data maintained for the Tower Sequence Manager. @S817 */ subject s : TowerSupervisor; }
    requirement def R76 { doc /* The Ramp Control Lead shall own ramp movement status data maintained for the Ramp Movement Board. @S818 */ subject s : RampControlLead; }
    requirement def R77 { doc /* The Meteorology Briefing Officer shall own operational weather classification inputs accepted by the Weather Ingest Gateway. @S819 */ subject s : MeteorologyBriefingOfficer; }
    requirement def R78 { doc /* The Airline Operations Coordinator shall be accountable for airline-supplied schedule intent, readiness status, and Target Off Block Time updates submitted through approved interfaces. @S820 */ subject s : AirlineOperationsCoordinator; }
    requirement def R79 { doc /* Each owned data element shall have a defined business meaning, allowed value range, update authority, retention class, and escalation contact. @S821 */ subject s : RegionalFlowPlatform; }
    requirement def R80 { doc /* Freshness indicators shall be displayed on the Common Situation Display wherever stale data could affect sequencing, metering, regulation, or resource allocation decisions. @S822 */ subject s : CommonSituationDisplay; }
    requirement def R81 { doc /* The freshness indicator shall include the time of last accepted update, the maximum permitted age, and a visual state that distinguishes current, aging, stale, and unavailable data. @S823 */ subject s : CommonSituationDisplay; }
    requirement def R82 { doc /* The Time Synchronization Service shall provide the common time basis used for freshness calculations across the Regional Flow Platform. @S824 */ subject s : TimeSynchronizationService; }
    requirement def R83 { doc /* shall reject data that lacks a trusted timestamp @S825 */ subject s : DemandPredictionService; }
    requirement def R84 { doc /* shall reject data that lacks a trusted timestamp @S825 */ subject s : CapacityAssessmentModule; }
    requirement def R85 { doc /* shall reject data that lacks a trusted timestamp @S825 */ subject s : SlotAllocationEngine; }
    requirement def R86 { doc /* shall reject data that lacks a trusted timestamp @S825 */ subject s : DepartureMeteringService; }
    requirement def R87 { doc /* Validation rules shall include schema checks, mandatory field checks, code set checks, temporal sequence checks, and operational plausibility checks. @S826 */ subject s : RegionalFlowPlatform; }
    requirement def R88 { doc /* The Flight Data Exchange shall validate Flight Intent Message content before the data is made available for operational use. @S827 */ subject s : FlightDataExchange; }
    requirement def R89 { doc /* The Surface Surveillance Adapter shall apply position quality checks and shall mark uncertain observations before they are used by surface decision functions. @S828 */ subject s : SurfaceSurveillanceAdapter; }
    requirement def R90 { doc /* The Airline Interface Adapter shall apply carrier-specific format checks while preserving the common operational meaning required by the Regional Flow Platform. @S829 */ subject s : AirlineInterfaceAdapter; }
    requirement def R91 { doc /* The Handling Resource Planner shall validate resource quantities, task timing, and allocation identifiers against active operational reference data. @S830 */ subject s : HandlingResourcePlanner; }
    requirement def R92 { doc /* The Business Rules Registry shall hold the current validation thresholds, allowable reason codes, and exception rules approved for Normal Operations, Adverse Weather Mode, Capacity Reduction State, Recovery Phase, and Contingency Fallback State. @S831 */ subject s : BusinessRulesRegistry; }
    requirement def R93 { doc /* When a discrepancy is detected, the affected component shall mark the data as disputed and shall preserve the prior accepted value until an authorized correction is available. @S832 */ subject s : AffectedComponent; }
    requirement def R94 { doc /* The Data Governance Steward shall coordinate discrepancy resolution with the responsible operational owner and shall record the disposition in the Audit Event Ledger. @S833 */ subject s : DataGovernanceSteward; }
    requirement def R95 { doc /* Urgent discrepancies that could change a metering, arrival regulation, or slot allocation decision shall be raised through the Alert Distribution Hub and reviewed in the Digital Briefing Room. @S834 */ subject s : AlertDistributionHub; }
    requirement def R96 { doc /* The System Support Engineer shall investigate technical causes of missing, delayed, duplicated, or transformed records and shall provide evidence needed for stewardship decisions. @S835 */ subject s : SystemSupportEngineer; }
    requirement def R97 { doc /* The Performance Analytics Warehouse shall retain data quality measures, including validation failure rates, freshness breaches, manual corrections, and recurring ownership conflicts. @S836 */ subject s : PerformanceAnalyticsWarehouse; }
    requirement def R98 { doc /* Stewardship reviews shall use those measures to update training, adjust validation rules, and improve the reliability of information used in operational decision making. @S837 */ subject s : DataGovernanceSteward; }
    requirement def R99 { doc /* Performance measurement shall convert operational events into repeatable indicators that can be reviewed after each operating day. @S838 */ subject s : MeridianRegionalAirTrafficFlowManagementAndAirportCollaborativeDecisionMakingSystem; }
    requirement def R100 { doc /* The Performance Analytics Warehouse shall calculate delay absorption as the portion of expected airborne or terminal-area delay that is converted into controlled ground delay before departure. @S839 */ subject s : PerformanceAnalyticsWarehouse; }
    requirement def R101 { doc /* Delay absorption shall be measured by comparing the unconstrained demand predicted by the Demand Prediction Service with the regulated demand produced by the Slot Allocation Engine and the realized movement times captured through the Flight Data Exchange. @S840 */ subject s : PerformanceAnalyticsWarehouse; }
    requirement def R102 { doc /* The principal delay absorption indicator shall report minutes absorbed at origin, minutes remaining in the arrival stream, and minutes transferred to surface queues within the region. @S841 */ subject s : PerformanceAnalyticsWarehouse; }
    requirement def R103 { doc /* The Regional Flow Manager shall use this indicator to verify that a Ground Delay Program reduced airborne holding without creating excessive departure congestion at constrained airports. @S842 */ subject s : RegionalFlowManager; }
    requirement def R104 { doc /* Queue length performance shall be measured for runway departure queues, arrival metering queues, apron movement queues, and regulation waiting lists. @S843 */ subject s : PerformanceAnalyticsWarehouse; }
    requirement def R105 { doc /* The Tower Sequence Manager shall provide runway sequence counts. @S844 */ subject s : TowerSequenceManager; }
    requirement def R106 { doc /* the Ramp Movement Board shall provide surface queue counts based on movement status and surveillance confirmation. @S844 */ subject s : RampMovementBoard; }
    requirement def R107 { doc /* shall support independent checks of queue length where surveillance coverage is available @S845 */ subject s : NorthRunwayMeter; }
    requirement def R108 { doc /* shall support independent checks of queue length where surveillance coverage is available @S845 */ subject s : SouthRunwayMeter; }
    requirement def R109 { doc /* shall support independent checks of queue length where surveillance coverage is available @S845 */ subject s : EastApronSensor; }
    requirement def R110 { doc /* shall support independent checks of queue length where surveillance coverage is available @S845 */ subject s : WestApronSensor; }
    requirement def R111 { doc /* Queue metrics shall include maximum queue length, average queue length, time above threshold, and recovery time after a constraint is lifted. @S846 */ subject s : PerformanceAnalyticsWarehouse; }
    requirement def R112 { doc /* Slot adherence shall be measured as the difference between actual movement times and the assigned Calculated Takeoff Time or Target Off Block Time. @S847 */ subject s : PerformanceAnalyticsWarehouse; }
    requirement def R113 { doc /* The Slot Coordinator shall review slot adherence by operator, airport, time band, and regulation identifier to detect recurring causes of noncompliance. @S848 */ subject s : SlotCoordinator; }
    requirement def R114 { doc /* A flight shall be counted within tolerance when the actual takeoff or off-block event occurs inside the operating window defined in the Business Rules Registry. @S849 */ subject s : BusinessRulesRegistry; }
    requirement def R115 { doc /* The Slot Compliance State shall be used to identify periods when adherence monitoring has operational priority over advisory optimization. @S850 */ subject s : SlotComplianceState; }
    requirement def R116 { doc /* Cancellation avoidance shall be estimated by comparing actual cancellations with a baseline scenario derived from demand, capacity, weather, and historical disruption outcomes. @S852 */ subject s : PerformanceAnalyticsWarehouse; }
    requirement def R117 { doc /* The Capacity Assessment Module shall record the available Airport Acceptance Rate used in each baseline so that avoided cancellation estimates remain traceable. @S853 */ subject s : CapacityAssessmentModule; }
    requirement def R118 { doc /* shall be able to challenge cancellation avoidance results through the Collaborative Decision Log when local business decisions affected the outcome @S854 */ subject s : AirlineOperationsCoordinator; }
    requirement def R119 { doc /* shall be able to challenge cancellation avoidance results through the Collaborative Decision Log when local business decisions affected the outcome @S854 */ subject s : AircraftOperatorRepresentative; }
    requirement def R120 { doc /* Emissions reduction shall be estimated from reduced airborne holding, reduced taxi-out time, avoided engine running in queues, and smoother departure metering. @S855 */ subject s : PerformanceAnalyticsWarehouse; }
    requirement def R121 { doc /* The Performance Analytics Warehouse shall apply approved fuel burn and emissions factors by aircraft category, operating phase, and delay location. @S856 */ subject s : PerformanceAnalyticsWarehouse; }
    requirement def R122 { doc /* Emissions metrics shall distinguish between actual reductions and delay transfers that only move fuel burn from one phase of flight to another. @S857 */ subject s : PerformanceAnalyticsWarehouse; }
    requirement def R123 { doc /* The Meteorology Briefing Officer shall support interpretation of emissions results by identifying periods when weather routing or convective avoidance dominated fuel performance. @S858 */ subject s : MeteorologyBriefingOfficer; }
    requirement def R124 { doc /* Stakeholder benefit tracking shall allocate measured outcomes to aircraft operators, airport operations, air navigation service functions, ground handling activities, and passengers where the source data supports that attribution. @S859 */ subject s : PerformanceAnalyticsWarehouse; }
    requirement def R125 { doc /* The Airport Duty Manager shall receive benefit summaries that show changes in stand occupancy, surface congestion, recovery duration, and passenger-facing disruption indicators. @S860 */ subject s : AirportDutyManager; }
    requirement def R126 { doc /* The Data Governance Steward shall ensure that published performance measures identify data sources, calculation versions, confidence limits, and known exclusions. @S861 */ subject s : DataGovernanceSteward; }
    requirement def R127 { doc /* The Post Operations Report shall present regional benefits alongside operational trade-offs so that decision makers can see whether delay, queue, slot, cancellation, and emissions objectives were balanced in practice. @S862 */ subject s : PostOperationsReport; }
    requirement def R128 { doc /* Training shall be role based and shall cover normal coordination, constrained operations, recovery actions, and degraded system use. @S863 */ subject s : MeridianRegionalAirTrafficFlowManagementAndAirportCollaborativeDecisionMakingSystem; }
    requirement def R129 { doc /* The Regional Flow Manager shall receive advanced instruction on interpreting demand and capacity information, leading collaborative decisions, and authorizing operational measures in the Regional Flow Platform. @S864 */ subject s : RegionalFlowManager; }
    requirement def R130 { doc /* Air traffic controllers shall be trained to understand how flow measures, sequencing changes, and calculated times affect sector workload, runway demand, and controller tactical flexibility. @S865 */ subject s : AirTrafficControllers; }
    requirement def R131 { doc /* The Tower Supervisor shall receive practical training on the Tower Sequence Manager, Departure Metering Service, Arrival Regulation Console, North Runway Meter, and South Runway Meter. @S866 */ subject s : TowerSupervisor; }
    requirement def R132 { doc /* Ramp personnel shall be trained under the direction of the Ramp Control Lead to use the Ramp Movement Board without substituting system indications for required visual checks, radio coordination, and local safety procedures. @S867 */ subject s : RampPersonnel; }
    requirement def R133 { doc /* shall be trained to submit, review, and update Flight Intent Message data through approved interfaces and to assess the operational effect of Calculated Takeoff Time and Target Off Block Time changes @S868 */ subject s : AirlineOperationsCoordinator; }
    requirement def R134 { doc /* shall be trained to submit, review, and update Flight Intent Message data through approved interfaces and to assess the operational effect of Calculated Takeoff Time and Target Off Block Time changes @S868 */ subject s : AircraftOperatorRepresentative; }
    requirement def R135 { doc /* Ground handling personnel shall be trained by the Ground Handling Dispatcher on the Handling Resource Planner and on procedures for confirming that resource constraints are represented accurately before they influence collaborative decisions. @S869 */ subject s : GroundHandlingDispatcher; }
    requirement def R136 { doc /* The Slot Coordinator shall receive training on the Slot Allocation Engine, Airport CDM Portal, and applicable Business Rules Registry entries so that slot actions are applied consistently and transparently. @S870 */ subject s : SlotCoordinator; }
    requirement def R137 { doc /* shall be trained to coordinate regional constraints, sector load conditions, and network measures using the Sector Load Monitor and Common Situation Display @S871 */ subject s : NetworkOperationsLiaison; }
    requirement def R138 { doc /* shall be trained to coordinate regional constraints, sector load conditions, and network measures using the Sector Load Monitor and Common Situation Display @S871 */ subject s : AirspaceSectorPlanner; }
    requirement def R139 { doc /* The Airport Duty Manager shall be trained to recognize when an Airport Capacity Plan requires revision and when the operational state should move from Normal Operations to Adverse Weather Mode or Capacity Reduction State. @S872 */ subject s : AirportDutyManager; }
    requirement def R140 { doc /* The Meteorology Briefing Officer shall be trained to explain weather uncertainty in operational terms and to verify that the Weather Ingest Gateway supports the assumptions used during briefings. @S873 */ subject s : MeteorologyBriefingOfficer; }
    requirement def R141 { doc /* The Emergency Response Coordinator shall participate in recurrent training so that emergency priorities are integrated into flow management decisions without obscuring command authority or safety responsibilities. @S874 */ subject s : EmergencyResponseCoordinator; }
    requirement def R142 { doc /* The Deicing Coordinator shall receive seasonal refresher training on how deicing capacity assumptions are represented in demand and departure metering tools. @S875 */ subject s : DeicingCoordinator; }
    requirement def R143 { doc /* The Data Governance Steward shall train operational users on data quality responsibilities, privacy expectations, and the correct interpretation of audit records in the Audit Event Ledger. @S876 */ subject s : DataGovernanceSteward; }
    requirement def R144 { doc /* The System Support Engineer shall train superusers on service status checks, access fault escalation, and safe use of the Contingency Operations Console during partial outages. @S877 */ subject s : SystemSupportEngineer; }
    requirement def R145 { doc /* Initial training shall include classroom instruction, supervised workstation practice, scenario walkthroughs in the Digital Briefing Room, and observed operational shadowing before independent system use is authorized. @S878 */ subject s : MeridianRegionalAirTrafficFlowManagementAndAirportCollaborativeDecisionMakingSystem; }
    requirement def R146 { doc /* Recurrent training shall be required at least annually and after major changes to the Regional Flow Platform, Demand Prediction Service, Capacity Assessment Module, or Flight Data Exchange. @S879 */ subject s : RegionalFlowPlatform; }
    requirement def R147 { doc /* Simulation exercises shall use realistic traffic samples, weather constraints, surface congestion, airline schedule pressure, handling resource shortages, and recovery objectives to test coordinated decision making. @S880 */ subject s : SimulationExercises; }
    requirement def R148 { doc /* Each exercise shall include participants from tower, ramp, airline operations, handling, airport operations, network coordination, meteorology, data governance, and system support functions when those functions are relevant to the scenario. @S881 */ subject s : SimulationExercises; }
    requirement def R149 { doc /* Exercises shall cover transitions among Normal Operations, Adverse Weather Mode, Capacity Reduction State, Recovery Phase, Contingency Fallback State, and Slot Compliance State. @S882 */ subject s : SimulationExercises; }
    requirement def R150 { doc /* Simulation events shall require users to compare automated recommendations with local knowledge, document significant decisions in the Collaborative Decision Log, and explain departures from system proposals. @S883 */ subject s : SimulationExercises; }
    requirement def R151 { doc /* Human factors safeguards shall include workload monitoring, clear alert prioritization, consistent terminology, confirmation steps for high impact actions, and protection against silent mode changes. @S884 */ subject s : MeridianRegionalAirTrafficFlowManagementAndAirportCollaborativeDecisionMakingSystem; }
    requirement def R152 { doc /* Workstation layouts shall support rapid comparison between the Common Situation Display, Airport CDM Portal, Tower Sequence Manager, Ramp Movement Board, and relevant advisory messages without forcing users to copy critical values manually. @S885 */ subject s : WorkstationLayouts; }
    requirement def R153 { doc /* Training assessments shall verify that users can identify stale data, time synchronization problems, duplicate flights, conflicting constraints, and inappropriate automation reliance before such issues affect live operations. @S886 */ subject s : TrainingAssessments; }
    requirement def R154 { doc /* Post-exercise reviews shall use evidence from the Performance Analytics Warehouse and Audit Event Ledger to improve procedures, refine training materials, and confirm that human performance concerns are assigned to accountable owners. @S887 */ subject s : PostExerciseReviews; }
    requirement def R155 { doc /* Deployment of the Regional Flow Platform shall proceed through phased increments that limit operational exposure while progressively adding airports, interfaces, and decision support functions. @S888 */ subject s : RegionalFlowPlatform; }
    requirement def R156 { doc /* The first increment shall establish the core operational baseline for the Regional Flow Manager, Network Operations Liaison, Data Governance Steward, and System Support Engineer in a controlled production environment. @S889 */ subject s : RegionalFlowPlatform; }
    requirement def R157 { doc /* This baseline shall include the Identity Access Service, Time Synchronization Service, Audit Event Ledger, Performance Analytics Warehouse, and Business Rules Registry before any airport is permitted to exchange operational data. @S890 */ subject s : RegionalFlowPlatform; }
    requirement def R158 { doc /* Pilot airport selection shall favor locations with stable operational leadership, representative traffic complexity, available surface surveillance data, and demonstrated willingness to participate in joint procedure development. @S891 */ subject s : PilotAirportSelection; }
    requirement def R159 { doc /* The initial pilot shall include one constrained primary airport and one less constrained regional airport so that both high-demand and routine operating patterns are exercised. @S892 */ subject s : InitialPilot; }
    requirement def R160 { doc /* Each candidate airport shall provide evidence that the Airport Duty Manager, Tower Supervisor, Ramp Control Lead, Airline Operations Coordinator, Ground Handling Dispatcher, and Aircraft Operator Representative have named accountable implementation contacts. @S893 */ subject s : CandidateAirport; }
    requirement def R161 { doc /* Readiness Gate 1 shall confirm that governance, security approvals, user role definitions, operating hours, and support escalation paths are documented and accepted by local stakeholders. @S894 */ subject s : ReadinessGate1; }
    requirement def R162 { doc /* Readiness Gate 2 shall confirm that the Flight Data Exchange, Airline Interface Adapter, Surface Surveillance Adapter, and Weather Ingest Gateway can be connected without disrupting existing airport operations. @S895 */ subject s : ReadinessGate2; }
    requirement def R163 { doc /* Readiness Gate 3 shall confirm that local procedures have been mapped to the Airport CDM Portal, Tower Sequence Manager, Ramp Movement Board, Departure Metering Service, and Arrival Regulation Console. @S896 */ subject s : ReadinessGate3; }
    requirement def R164 { doc /* Readiness Gate 4 shall confirm that training, shadow operations, contingency procedures, and operational acceptance criteria have been completed before live collaborative decisions are made through the Regional Flow Platform. @S897 */ subject s : ReadinessGate4; }
    requirement def R165 { doc /* Interface certification shall be performed separately from operational acceptance so that technical conformance defects do not become unresolved procedural issues. @S898 */ subject s : InterfaceCertification; }
    requirement def R166 { doc /* Each interface shall be tested for message structure, time stamping, identity attribution, replay handling, duplicate detection, outage recovery, and rejection behavior under degraded network conditions. @S899 */ subject s : Interface; }
    requirement def R167 { doc /* shall be certified against agreed reference scenarios before they are used for operational recommendations @S900 */ subject s : DemandPredictionService; }
    requirement def R168 { doc /* shall be certified against agreed reference scenarios before they are used for operational recommendations @S900 */ subject s : CapacityAssessmentModule; }
    requirement def R169 { doc /* shall be certified against agreed reference scenarios before they are used for operational recommendations @S900 */ subject s : SlotAllocationEngine; }
    requirement def R170 { doc /* shall be certified against agreed reference scenarios before they are used for operational recommendations @S900 */ subject s : GateConflictDetector; }
    requirement def R171 { doc /* shall be certified against agreed reference scenarios before they are used for operational recommendations @S900 */ subject s : SectorLoadMonitor; }
    requirement def R172 { doc /* shall be certified against agreed reference scenarios before they are used for operational recommendations @S900 */ subject s : NorthRunwayMeter; }
    requirement def R173 { doc /* shall be certified against agreed reference scenarios before they are used for operational recommendations @S900 */ subject s : SouthRunwayMeter; }
    requirement def R174 { doc /* Certification results shall be recorded in the Collaborative Decision Log when they affect operational procedures and in the Audit Event Ledger when they affect access, configuration, or transaction traceability. @S901 */ subject s : CollaborativeDecisionLog; }
    requirement def R175 { doc /* Airport onboarding shall start with data discovery workshops that identify local tools, manual workarounds, unofficial spreadsheets, and locally maintained constraint registers. @S902 */ subject s : AirportOnboarding; }
    requirement def R176 { doc /* The migration plan shall classify each local tool as retired, retained for read-only reference, integrated through an approved interface, or replaced by a Regional Flow Platform function. @S903 */ subject s : MigrationPlan; }
    requirement def R177 { doc /* No local tool shall be retired until the responsible operational owner verifies that its essential decisions, timing assumptions, and audit needs are supported in the target process. @S904 */ subject s : LocalTool; }
    requirement def R178 { doc /* During shadow operations, local tools shall remain the authoritative source while the Regional Flow Platform produces parallel outputs for comparison by operational users. @S905 */ subject s : LocalTool; }
    requirement def R179 { doc /* The cutover decision shall be based on measured agreement between local practice and Regional Flow Platform outputs, user confidence, defect closure, and demonstrated recovery from simulated failures. @S906 */ subject s : CutoverDecision; }
    requirement def R180 { doc /* After cutover, local users shall enter operational decisions through the Airport CDM Portal and shall avoid reintroducing uncontrolled parallel records that undermine common situational awareness. @S907 */ subject s : LocalUsers; }
    requirement def R181 { doc /* The Contingency Operations Console shall be available at each onboarded airport before reliance on the Regional Flow Platform is declared for Normal Operations, Adverse Weather Mode, Capacity Reduction State, Recovery Phase, or Contingency Fallback State. @S908 */ subject s : ContingencyOperationsConsole; }
    requirement def R182 { doc /* Expansion beyond the pilot airports shall occur in waves that group airports by interface maturity, traffic dependency, stakeholder readiness, and available support capacity. @S909 */ subject s : RegionalFlowPlatform; }
    requirement def R183 { doc /* Each onboarding wave shall include a stabilization period in which the System Support Engineer and Data Governance Steward monitor defect trends, data quality, access changes, and user adoption. @S910 */ subject s : OnboardingWave; }
    requirement def R184 { doc /* Full regional deployment shall be declared only after the Regional Flow Manager confirms that operational benefits, safety constraints, cyber controls, and stakeholder obligations remain stable across multiple airports and traffic conditions. @S911 */ subject s : RegionalFlowManager; }
    requirement def R185 { doc /* Operational service management for the Regional Flow Platform shall begin when a deployed airport is accepted into steady state support after the regional stabilization period. @S912 */ subject s : RegionalFlowPlatform; }
    requirement def R186 { doc /* The service model shall distinguish continuous operational support from planned engineering support so that safety related traffic flow functions remain protected at all times. @S913 */ subject s : ServiceModel; }
    requirement def R187 { doc /* The System Support Engineer shall provide round the clock on call coverage for production incidents affecting the Regional Flow Platform, Airport CDM Portal, Slot Allocation Engine, Departure Metering Service, Arrival Regulation Console, and Alert Distribution Hub. @S914 */ subject s : SystemSupportEngineer; }
    requirement def R188 { doc /* Standard service desk coverage for access requests, reporting questions, configuration inquiries, and minor usability issues shall be available during normal regional administrative hours on business days. @S915 */ subject s : ServiceDesk; }
    requirement def R189 { doc /* During published peak traffic periods, Adverse Weather Mode, Capacity Reduction State, and Recovery Phase, the on call support posture shall be raised so that the System Support Engineer can join the Digital Briefing Room without delay. @S916 */ subject s : SystemSupportEngineer; }
    requirement def R190 { doc /* shall retain operational command authority during support activity @S917 */ subject s : RegionalFlowManager; }
    requirement def R191 { doc /* shall retain operational command authority during support activity @S917 */ subject s : TowerSupervisor; }
    requirement def R192 { doc /* shall retain operational command authority during support activity @S917 */ subject s : RampControlLead; }
    requirement def R193 { doc /* shall retain operational command authority during support activity @S917 */ subject s : AirportDutyManager; }
    requirement def R194 { doc /* shall retain operational command authority during support activity @S917 */ subject s : NetworkOperationsLiaison; }
    requirement def R195 { doc /* The System Support Engineer shall advise operational supervisors on technical status, known workarounds, data integrity concerns, and recovery options, but shall not issue traffic management instructions. @S918 */ subject s : SystemSupportEngineer; }
    requirement def R196 { doc /* Incidents shall be classified by operational effect, with the highest priority assigned to loss of common situational awareness, loss of slot computation, corruption of operational timing data, or failure of alert distribution during active traffic management. @S919 */ subject s : Incident; }
    requirement def R197 { doc /* A critical incident shall be acknowledged within fifteen minutes and shall have continuous technical ownership until service is restored or an agreed operational workaround is in place. @S920 */ subject s : CriticalIncident; }
    requirement def R198 { doc /* A high priority incident that degrades a major function without stopping tactical coordination shall be acknowledged within thirty minutes and shall be reviewed with the affected operational supervisor at least hourly. @S921 */ subject s : HighPriorityIncident; }
    requirement def R199 { doc /* Medium and low priority incidents shall be handled through the service queue, with target updates provided at intervals appropriate to their operational impact and planned resolution path. @S922 */ subject s : MediumAndLowPriorityIncidents; }
    requirement def R200 { doc /* The System Support Engineer shall maintain an incident record that captures the initial symptom, affected components, operational state, timeline, mitigation actions, data corrections, and supervisor decisions. @S923 */ subject s : SystemSupportEngineer; }
    requirement def R201 { doc /* Incident records shall reference the Audit Event Ledger where user actions, configuration changes, interface events, or automated decisions are relevant to the investigation. @S924 */ subject s : AuditEventLedger; }
    requirement def R202 { doc /* The Collaborative Decision Log shall be used to preserve the operational context of major incidents when traffic management decisions are made while a technical degradation is present. @S925 */ subject s : CollaborativeDecisionLog; }
    requirement def R203 { doc /* The System Support Engineer shall verify that fallback tools, exported operational data, and restoration checkpoints are available before advising that normal technical service can resume. @S927 */ subject s : SystemSupportEngineer; }
    requirement def R204 { doc /* Post incident review shall be required for critical incidents, repeated high priority incidents, security related events, and failures that occur during capacity constrained operations. @S928 */ subject s : PostIncidentReview; }
    requirement def R205 { doc /* The review shall identify technical root cause, operational contributing factors, effectiveness of workarounds, user communication quality, and corrective actions assigned to named owners. @S929 */ subject s : PostIncidentReview; }
    requirement def R206 { doc /* Planned change windows shall normally be scheduled during low demand night periods and shall be coordinated with the Regional Flow Manager, Airport Duty Manager, Tower Supervisor, and affected Aircraft Operator Representative groups before approval. @S930 */ subject s : PlannedChangeWindows; }
    requirement def R207 { doc /* Changes that modify the Business Rules Registry, Identity Access Service, Time Synchronization Service, Flight Data Exchange, or operational metering behavior shall require additional validation in a representative test environment before production release. @S931 */ subject s : BusinessRulesRegistry; }
    requirement def R208 { doc /* Emergency changes may be applied outside the standard window when needed to restore service, protect cyber security, or prevent material operational harm, but they shall be documented and retrospectively approved. @S932 */ subject s : EmergencyChanges; }
    requirement def R209 { doc /* Service level targets shall include monthly availability for critical production functions, incident response time, restoration time, data feed timeliness, and successful completion of scheduled operational reports. @S933 */ subject s : ServiceLevelTargets; }
    requirement def R210 { doc /* Availability targets shall exclude approved maintenance windows, customer network outages outside the managed boundary, and periods when operational supervisors have directed use of contingency procedures for nontechnical reasons. @S934 */ subject s : AvailabilityTargets; }
    requirement def R211 { doc /* Performance against service targets shall be reviewed with the Regional Flow Manager and Data Governance Steward so that service quality, operational benefit, data quality, and user confidence are managed as a single operating obligation. @S935 */ subject s : RegionalFlowManager; }
    requirement def R212 { doc /* Future enhancement of the Regional Flow Platform should be treated as an incremental extension of the operational service rather than as a replacement of the current concept. @S936 */ subject s : RegionalFlowPlatform; }
    requirement def R213 { doc /* Cross-border exchange should use standardized message structures where practical, but the Business Rules Registry should retain the local parameters needed for Meridian operations. @S939 */ subject s : BusinessRulesRegistry; }
    requirement def R214 { doc /* The Flight Data Exchange should be enhanced to accept richer intent data, including improved route options, expected cruise profiles, and updated departure readiness information. @S940 */ subject s : FlightDataExchange; }
    requirement def R215 { doc /* The Demand Prediction Service should use this data to create more stable demand pictures across longer planning horizons while still preserving tactical responsiveness. @S941 */ subject s : DemandPredictionService; }
    requirement def R216 { doc /* Trajectory prediction should also make greater use of weather features, sector configuration, runway direction, and surface movement status when estimating flight progress. @S942 */ subject s : TrajectoryPrediction; }
    requirement def R217 { doc /* should provide the common inputs needed to connect airspace capacity and airport capacity in the same prediction cycle @S943 */ subject s : WeatherIngestGateway; }
    requirement def R218 { doc /* should provide the common inputs needed to connect airspace capacity and airport capacity in the same prediction cycle @S943 */ subject s : SectorLoadMonitor; }
    requirement def R219 { doc /* The Capacity Assessment Module should evolve from a mainly rules-based assessment into a service that can compare planned capacity, observed throughput, and predicted constraint persistence. @S944 */ subject s : CapacityAssessmentModule; }
    requirement def R220 { doc /* Any use of learning models should be introduced with explainability requirements so that operational users can understand why a capacity or delay estimate has changed. @S945 */ subject s : LearningModels; }
    requirement def R221 { doc /* Advanced turnaround prediction should combine aircraft state, handling milestones, stand occupancy, crew readiness, passenger processing, and ramp congestion signals. @S946 */ subject s : AdvancedTurnaroundPrediction; }
    requirement def R222 { doc /* should provide the main operational inputs for this capability @S947 */ subject s : AirportCDMPortal; }
    requirement def R223 { doc /* should provide the main operational inputs for this capability @S947 */ subject s : AirlineInterfaceAdapter; }
    requirement def R224 { doc /* should provide the main operational inputs for this capability @S947 */ subject s : HandlingResourcePlanner; }
    requirement def R225 { doc /* should provide the main operational inputs for this capability @S947 */ subject s : RampMovementBoard; }
    requirement def R226 { doc /* Predicted changes to Target Off Block Time should be presented with confidence levels rather than as unconditional system corrections. @S948 */ subject s : TargetOffBlockTime; }
    requirement def R227 { doc /* The Slot Allocation Engine should use improved turnaround predictions to protect feasible Calculated Takeoff Time assignments and to reduce avoidable re-sequencing. @S949 */ subject s : SlotAllocationEngine; }
    requirement def R228 { doc /* should receive only the information needed for tactical sequencing, with detailed airline operational data controlled by policy @S950 */ subject s : TowerSequenceManager; }
    requirement def R229 { doc /* should receive only the information needed for tactical sequencing, with detailed airline operational data controlled by policy @S950 */ subject s : DepartureMeteringService; }
    requirement def R230 { doc /* Machine-assisted recovery options should support the Recovery Phase by proposing coordinated actions that balance runway throughput, sector loading, stand availability, and airline priorities. @S951 */ subject s : MachineAssistedRecoveryOptions; }
    requirement def R231 { doc /* These options should be generated by the Contingency Operations Console and reviewed through the Common Situation Display before any operational decision is applied. @S952 */ subject s : ContingencyOperationsConsole; }
    requirement def R232 { doc /* The system should not automatically impose a Ground Delay Program, change an Airport Acceptance Rate, or alter a tactical measure without authorized human confirmation. @S953 */ subject s : System; }
    requirement def R233 { doc /* Recovery recommendations should include the operational rationale, expected benefit, key assumptions, and possible secondary effects on connected flights and surface movements. @S954 */ subject s : RecoveryRecommendations; }
    requirement def R234 { doc /* should record each proposed option, the user response, and the final decision so that performance can be reviewed after operations @S955 */ subject s : CollaborativeDecisionLog; }
    requirement def R235 { doc /* should record each proposed option, the user response, and the final decision so that performance can be reviewed after operations @S955 */ subject s : AuditEventLedger; }
    requirement def R236 { doc /* Regional expansion should include a repeatable onboarding pattern for new airports, airspace sectors, airlines, and handling organizations. @S956 */ subject s : RegionalExpansion; }
    requirement def R237 { doc /* should be scaled early because they form shared foundations for a wider regional deployment @S957 */ subject s : IdentityAccessService; }
    requirement def R238 { doc /* should be scaled early because they form shared foundations for a wider regional deployment @S957 */ subject s : TimeSynchronizationService; }
    requirement def R239 { doc /* should be scaled early because they form shared foundations for a wider regional deployment @S957 */ subject s : PerformanceAnalyticsWarehouse; }
    requirement def R240 { doc /* Data governance should remain under the Data Governance Steward, with clear rules for retention, consent, quality thresholds, and permitted operational use. @S958 */ subject s : DataGovernanceSteward; }
    requirement def R241 { doc /* Future releases should be validated in shadow mode before operational activation so that the Regional Flow Manager, Airline Operations Coordinator, Tower Supervisor, and Airport Duty Manager can compare recommendations with actual outcomes. @S959 */ subject s : FutureReleases; }
    requirement def R242 { doc /* Sustained regional ATFM and A-CDM operation requires each participating organization to treat the operating picture as a shared operational asset rather than a local advisory product. @S960 */ subject s : ParticipatingOrganization; }
    requirement def R243 { doc /* The Common Situation Display is the shared baseline for time-critical coordination and should be kept consistent with the Regional Flow Platform and Airport CDM Portal. @S974 */ subject s : CommonSituationDisplay; }
    requirement def R244 { doc /* Calculated Takeoff Time and Target Off Block Time commitments should be treated as executable operating constraints unless they are revised through the agreed coordination process. @S976 */ subject s : CalculatedTakeoffTime; }
    requirement def R245 { doc /* Ground Delay Program decisions, Tactical Regulation Proposal review, and Airport Acceptance Rate changes should be visible to affected participants before they are applied whenever operational time permits. @S977 */ subject s : GroundDelayProgram; }
    requirement def R246 { doc /* must be operated with monitored data quality thresholds and clear fallback procedures @S979 */ subject s : FlightDataExchange; }
    requirement def R247 { doc /* must be operated with monitored data quality thresholds and clear fallback procedures @S979 */ subject s : AirlineInterfaceAdapter; }
    requirement def R248 { doc /* must be operated with monitored data quality thresholds and clear fallback procedures @S979 */ subject s : SurfaceSurveillanceAdapter; }
    requirement def R249 { doc /* must be operated with monitored data quality thresholds and clear fallback procedures @S979 */ subject s : WeatherIngestGateway; }
    requirement def R250 { doc /* must use the approved rules recorded in the Business Rules Registry @S980 */ subject s : SlotAllocationEngine; }
    requirement def R251 { doc /* must use the approved rules recorded in the Business Rules Registry @S980 */ subject s : DepartureMeteringService; }
    requirement def R252 { doc /* must use the approved rules recorded in the Business Rules Registry @S980 */ subject s : ArrivalRegulationConsole; }
    requirement def R253 { doc /* must use the approved rules recorded in the Business Rules Registry @S980 */ subject s : TowerSequenceManager; }
    requirement def R254 { doc /* must use the approved rules recorded in the Business Rules Registry @S980 */ subject s : RampMovementBoard; }
    requirement def R255 { doc /* must support traceability, least-privilege access, and after-action accountability for all operationally significant changes @S981 */ subject s : IdentityAccessService; }
    requirement def R256 { doc /* must support traceability, least-privilege access, and after-action accountability for all operationally significant changes @S981 */ subject s : AuditEventLedger; }
    requirement def R257 { doc /* The Performance Analytics Warehouse and Post Operations Report should be used to measure compliance, delay outcomes, capacity use, and the effectiveness of collaborative decisions. @S982 */ subject s : PerformanceAnalyticsWarehouse; }
    requirement def R258 { doc /* Governance should favor transparent decision making, timely challenge by affected parties, documented resolution of disputes, and continuous improvement through training, exercises, and post-operations review. @S983 */ subject s : Governance; }
}
