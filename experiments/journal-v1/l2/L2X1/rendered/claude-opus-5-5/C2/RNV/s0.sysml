package L2Model {
    item def AcceptedIntentDataItem { doc /* @S128 */ }
    item def AcceptedOrRejectedExemptionItem { doc /* @S239 */ }
    item def AcceptedSlotAdjustmentsRejectedSlotAdjustmentsAndUnresolvedSlotConflictsItem { doc /* @S161 */ }
    item def AcknowledgementsItem { doc /* @S405 */ }
    item def ActiveRestrictionStatusExpectedOperationalEffectAndRelatedCoordinationNotesItem { doc /* @S337,S338 */ }
    item def ActiveSpacingRulesItem { doc /* @S297 */ }
    item def AffectedRunwayQueueItem { doc /* @S366 */ }
    item def AgreedTargetOffBlockTimeValuesAndStakeholderRemarksItem { doc /* @S429 */ }
    item def AirportAcceptanceRateItem { doc /* @S226,S698 */ }
    item def AirportCapacityPlanItem { doc /* @S226,S252 */ }
    item def AirspaceAlertAcknowledgementAndDownstreamDecisionItem { doc /* @S333 */ }
    item def AlertItem { doc /* @S093,S210 */ }
    item def ApprovedOperationalResultItem { doc /* @S638 */ }
    item def ApprovedRulesItem { doc /* @S980 */ }
    item def ApronCongestionConditionItem { doc /* @S218 */ }
    item def ApronConstraintsItem { doc /* @S244 */ }
    item def ApronSweepCompletionNoteItem { doc /* @S678 */ }
    item def ArrivalPlanItem { doc /* @S405 */ }
    item def AuditRecordsItem { doc /* @S274 */ }
    item def AuthenticatedRoleItem { doc /* @S793 */ }
    item def BaseMapTimelineFlightListAndMeasureStatusPanelsItem { doc /* @S421 */ }
    item def BorderAndCustomsStatusItem { doc /* @S572 */ }
    item def BusinessRulesRegistryParametersItem { doc /* @S080 */ }
    item def CalculatedTakeoffTimeItem { doc /* @S254 */ }
    item def CandidatePushbackSpacingItem { doc /* @S456 */ }
    item def CapacityChangeNotificationItem { doc /* @S121 */ }
    item def ClosureItem { doc /* @S713 */ }
    item def CombinedTacticalViewItem { doc /* @S420 */ }
    item def CommonTimeBasisItem { doc /* @S824 */ }
    item def ConcurrenceItem { doc /* @S673 */ }
    item def ConditionsThatMayAffectRunwayTaxiwayStandOrApronAvailabilityItem { doc /* @S175 */ }
    item def ConstraintItem { doc /* @S318 */ }
    item def ConstraintsItem { doc /* @S135,S225 */ }
    item def CrewDutyExtensionLogItem { doc /* @S726 */ }
    item def CrewLegalityInputsItem { doc /* @S622 */ }
    item def CurrentCapacityAssumptionsItem { doc /* @S335 */ }
    item def CurrentMovementAreaOccupancyAndEquipmentStatusIndicatorsItem { doc /* @S445 */ }
    item def CurrentOperatingBasisItem { doc /* @S734 */ }
    item def CurrentOperatingScheduleItem { doc /* @S103 */ }
    item def CurrentRegionalDemandAndConstraintContextItem { doc /* @S164 */ }
    item def CustomsHoldReleaseNoteItem { doc /* @S679 */ }
    item def DataItem { doc /* @S086 */ }
    item def DelayAbsorptionIndicatorItem { doc /* @S842 */ }
    item def DemandItem { doc /* @S225 */ }
    item def DemandCurveItem { doc /* @S065 */ }
    item def DemandForecastItem { doc /* @S101,S132 */ }
    item def DemandProjectionsItem { doc /* @S107 */ }
    item def DepartureDemandProfileItem { doc /* @S351 */ }
    item def DispositionItem { doc /* @S833 */ }
    item def DiversionRationalePriorityClassificationResourceCommitmentAndAgreedRecoveryTargetItem { doc /* @S506 */ }
    item def DutyDeskConfirmationsItem { doc /* @S185 */ }
    item def EvidenceItem { doc /* @S835,S887 */ }
    item def ExceptionItem { doc /* @S671 */ }
    item def ExpectedServiceCompletionTimesItem { doc /* @S302 */ }
    item def ExternalCoordinationOutcomesItem { doc /* @S084 */ }
    item def FeasibilityResultAndTimingBoundaryItem { doc /* @S626 */ }
    item def FiledFlightInformationItem { doc /* @S103 */ }
    item def FlightIntentMessageItem { doc /* @S126,S131,S226 */ }
    item def ForecastConfidenceTimingRiskAndExpectedOperationalImpactItem { doc /* @S086 */ }
    item def ForecastDemandAssessedCapacityAndActiveGroundDelayProgramEffectsItem { doc /* @S117 */ }
    item def GateConflictItem { doc /* @S470 */ }
    item def InfrastructureEventsItem { doc /* @S695 */ }
    item def IntentDataItem { doc /* @S941 */ }
    item def LegalityStatusItem { doc /* @S621 */ }
    item def LoggedRationaleItem { doc /* @S760 */ }
    item def MandatoryFieldsPermissibleStatusValuesRetentionRulesAndDataQualityThresholdsItem { doc /* @S170 */ }
    item def MaterialDeviationsItem { doc /* @S091 */ }
    item def MedicalDiversionNoticeItem { doc /* @S576 */ }
    item def MorningPlanAvailabilityNotificationItem { doc /* @S073 */ }
    item def MorningWeatherOutlookItem { doc /* @S057 */ }
    item def MovementIndicationsItem { doc /* @S179 */ }
    item def MovementUpdatesItem { doc /* @S222 */ }
    item def NormalizedScheduleItem { doc /* @S053 */ }
    item def NotificationsItem { doc /* @S614 */ }
    item def OperationalBasisItem { doc /* @S400 */ }
    item def OperationalClockItem { doc /* @S422 */ }
    item def OperationalDecisionsItem { doc /* @S907 */ }
    item def OperationalReadinessInformationItem { doc /* @S016 */ }
    item def OperationalSignificanceOfTheConditionItem { doc /* @S447 */ }
    item def OperationalWeatherClassificationInputsItem { doc /* @S819 */ }
    item def OutputsItem { doc /* @S095 */ }
    item def ParallelOutputsItem { doc /* @S905 */ }
    item def PlannedRemoteStandOperatingPostureItem { doc /* @S544 */ }
    item def PositionUpdatesItem { doc /* @S179 */ }
    item def PredictedReadinessItem { doc /* @S593 */ }
    item def ProposedDepartureOpportunitiesAndCalculatedTakeoffTimeValuesItem { doc /* @S242 */ }
    item def ProposedSubstitutionItem { doc /* @S667 */ }
    item def PushbackWindowTokenItem { doc /* @S503 */ }
    item def RampMovementStatusItem { doc /* @S770 */ }
    item def RealizedMovementTimesItem { doc /* @S840 */ }
    item def ReconsiderationRequestItem { doc /* @S363 */ }
    item def RecordedRegulationHistoryItem { doc /* @S418 */ }
    item def RecoveryOptionsItem { doc /* @S952 */ }
    item def RegulatedDemandItem { doc /* @S840 */ }
    item def ResourceDrivenFeasibilityStatusItem { doc /* @S312 */ }
    item def RevisedInputsItem { doc /* @S699 */ }
    item def RoleProfilesItem { doc /* @S766 */ }
    item def RunwayAssignmentPressureAirborneSequenceSpacingAndExpectedCrossingPointsItem { doc /* @S425 */ }
    item def RunwayDeclarationItem { doc /* @S066 */ }
    item def RunwayDemandItem { doc /* @S283 */ }
    item def RunwaySpecificCapacityValuesItem { doc /* @S114 */ }
    item def ScheduledMovementsItem { doc /* @S593 */ }
    item def SectorDemandItem { doc /* @S432 */ }
    item def SectorValuesItem { doc /* @S593 */ }
    item def SensorDataItem { doc /* @S205 */ }
    item def SharedViewOfDemandCapacityConstraintsAndActiveTrafficManagementMeasuresItem { doc /* @S020 */ }
    item def SignificantDecisionsItem { doc /* @S883 */ }
    item def SlotComplianceEventsItem { doc /* @S789 */ }
    item def StaleMilestoneNotificationItem { doc /* @S166 */ }
    item def StandOccupancyPushbackSpacingAndTugAvailabilityItem { doc /* @S677 */ }
    item def StandReadinessInformationItem { doc /* @S063 */ }
    item def StormCellSnapshotItem { doc /* @S133 */ }
    item def SubscriptionRulesItem { doc /* @S332 */ }
    item def SupportingMovementEvidenceItem { doc /* @S474 */ }
    item def SurfaceEquipmentAndApronCongestionAdvisoriesItem { doc /* @S463 */ }
    item def SurfaceSurveillanceAdapterInputsItem { doc /* @S204 */ }
    item def SynchronizedTimestampsItem { doc /* @S098 */ }
    item def TargetOffBlockTimeItem { doc /* @S259 */ }
    item def TargetOffBlockTimeRevisionItem { doc /* @S260 */ }
    item def TechnicalStatusKnownWorkaroundsDataIntegrityConcernsAndRecoveryOptionsItem { doc /* @S918 */ }
    item def TheCrewBusDelaySlipItem { doc /* @S237 */ }
    item def TheDeicingPadQueueCardItem { doc /* @S378 */ }
    item def TheDepartureFixLoadSheetItem { doc /* @S598 */ }
    item def TheFuelTruckHoldAdviceItem { doc /* @S450 */ }
    item def TheGateReopeningMemoItem { doc /* @S472 */ }
    item def TheLateBaggageTagListItem { doc /* @S519 */ }
    item def ThePassengerMisconnectCountItem { doc /* @S851 */ }
    item def TheRemoteStandShuttleCountItem { doc /* @S648 */ }
    item def TheSlotSwapPermissionEmailItem { doc /* @S795 */ }
    item def TheStandTowRequestFormItem { doc /* @S304 */ }
    item def TheTemporaryRestrictionNoticeItem { doc /* @S399 */ }
    item def ThresholdsItem { doc /* @S600 */ }
    item def TimeItem { doc /* @S778 */ }
    item def TimeSourceItem { doc /* @S792 */ }
    item def TowbarShortageReportItem { doc /* @S556 */ }
    item def TraceFromIncomingForecastProductToCapacityValueItem { doc /* @S123 */ }
    item def TransactionItem { doc /* @S194 */ }
    item def UnavailableRunwayLightingElementsItem { doc /* @S693 */ }
    item def UnconstrainedDemandItem { doc /* @S840 */ }
    item def UnresolvedAssumptionsItem { doc /* @S071 */ }
    item def UrgentDiscrepanciesItem { doc /* @S834 */ }
    item def WeatherFeedItem { doc /* @S109 */ }
    item def WeatherImpactsItem { doc /* @S434 */ }
    item def WeatherInterpretationForecastConfidenceAndExpectedTimingOfOperationalImpactsItem { doc /* @S163 */ }
    item def WeatherOutlookItem { doc /* @S066 */ }
    part def AccessControl { doc /* @S786 */ }
    part def AccessLimitations { doc /* @S526 */ }
    part def AccessibleBoardingSupport { doc /* @S548 */ }
    part def AffectedResource { doc /* @S691 */ }
    part def AggregatedMetrics { doc /* @S805 */ }
    part def AirNavigationServiceParticipation { doc /* @S045 */ }
    part def AirTrafficControllers { doc /* @S865 */ }
    part def AircraftOperatorRepresentative { doc /* @S039,S055,S082,S215,S291,S312,S316,S363,S405,S437,S476,S620,S622,S630,S666,S673,S725,S726,S771,S797,S854,S868,S965 */ }
    part def AircraftRegistration { doc /* @S127 */ }
    part def AirlineInterfaceAdapter { doc /* @S018,S033,S103,S126,S128,S135,S235,S452,S478,S519,S618,S621,S622,S741,S829,S947,S979 */ }
    part def AirlineOperationsCentre { doc /* @S126,S135,S139 */ }
    part def AirlineOperationsCentreIntegration { doc /* @S124 */ }
    part def AirlineOperationsCentres { doc /* @S146 */ }
    part def AirlineOperationsCoordinator { doc /* @S011,S039,S054,S081,S121,S129,S138,S157,S214,S226,S237,S259,S260,S284,S312,S317,S338,S362,S385,S403,S437,S451,S472,S507,S521,S546,S554,S574,S604,S623,S630,S658,S667,S679,S725,S740,S766,S771,S795,S820,S851,S854,S868,S959,S965 */ }
    part def Airlines { doc /* @S043 */ }
    part def Airport { doc /* @S890 */ }
    part def AirportAcceptanceRateConstraints { doc /* @S046 */ }
    part def AirportCDMPortal { doc /* @S016,S031,S150,S163,S164,S166,S170,S172,S179,S185,S195,S260,S264,S270,S293,S312,S337,S363,S381,S405,S429,S447,S470,S485,S503,S527,S531,S544,S559,S572,S602,S622,S648,S649,S667,S668,S673,S681,S695,S713,S793,S812,S907,S947 */ }
    part def AirportCapacityPlan { doc /* @S599 */ }
    part def AirportCapacityPlanAssumptions { doc /* @S046 */ }
    part def AirportDutyDesk { doc /* @S177,S178,S185 */ }
    part def AirportDutyManager { doc /* @S040,S062,S088,S091,S116,S144,S162,S175,S177,S181,S183,S190,S196,S198,S218,S226,S252,S345,S368,S435,S447,S471,S496,S544,S563,S568,S576,S660,S678,S679,S692,S713,S716,S734,S750,S809,S816,S860,S872,S917,S959,S962 */ }
    part def AirportNetwork { doc /* @S003 */ }
    part def AirportOnboarding { doc /* @S902 */ }
    part def AirportParticipant { doc /* @S167,S168 */ }
    part def AirportStakeholders { doc /* @S016 */ }
    part def AirspacePlanningPersonnel { doc /* @S045 */ }
    part def AirspaceSectorPlanner { doc /* @S041,S058,S079,S326,S345,S402,S432,S501,S608,S871,S967 */ }
    part def AlertDistributionHub { doc /* @S033,S073,S121,S166,S193,S331,S332,S366,S440,S461,S463,S505,S529,S588,S614,S705,S834 */ }
    part def ApprovalLatency { doc /* @S689 */ }
    part def ApprovingAuthority { doc /* @S691 */ }
    part def ArrivalRegulationConsole { doc /* @S017,S032,S070,S095,S241,S336,S407,S423,S495,S535,S576,S596,S698,S729,S757,S980 */ }
    part def AuditEventLedger { doc /* @S021,S034,S098,S123,S149,S194,S222,S245,S271,S274,S289,S333,S369,S417,S418,S442,S466,S488,S515,S537,S636,S664,S683,S710,S777,S778,S779,S789,S792,S833,S887,S890,S901,S955,S981 */ }
    part def AuditOutputs { doc /* @S811 */ }
    part def AuditProcessing { doc /* @S788 */ }
    part def AuthorizedAirportAirlineAndFlowManagementUsers { doc /* @S695 */ }
    part def AuthorizedOperationalUsers { doc /* @S572 */ }
    part def AuthorizedUsers { doc /* @S020 */ }
    part def BasedCarriers { doc /* @S043 */ }
    part def BusinessRulesRegistry { doc /* @S034,S080,S297,S332,S436,S486,S534,S539,S586,S600,S631,S670,S706,S831,S849,S890,S939,S980 */ }
    part def CalculatedTakeoffTime { doc /* @S976 */ }
    part def CalculatedTakeoffTimeValues { doc /* @S046 */ }
    part def CandidateAirport { doc /* @S893 */ }
    part def CapacityAssessmentModule { doc /* @S014,S031,S057,S066,S094,S107,S114,S120,S132,S133,S192,S225,S226,S252,S328,S335,S341,S351,S373,S400,S431,S448,S494,S557,S584,S594,S600,S694,S697,S698,S803,S825,S853,S944,S973 */ }
    part def CapacityValues { doc /* @S120 */ }
    part def CargoAndGeneralAviationAerodromes { doc /* @S001 */ }
    part def CargoOperators { doc /* @S043 */ }
    part def ChangesMadeInsideTheFreezeHorizon { doc /* @S800 */ }
    part def CharterOperators { doc /* @S043 */ }
    part def CollaborativeDecisionLog { doc /* @S021,S071,S084,S122,S161,S169,S186,S221,S239,S267,S288,S321,S369,S392,S405,S442,S466,S487,S506,S531,S589,S615,S637,S682,S709,S759,S760,S794,S883,S901,S925,S955 */ }
    part def CollaborativeDecisionLogEntries { doc /* @S046 */ }
    part def CommonServices { doc /* @S030 */ }
    part def CommonSituationDisplay { doc /* @S020,S072,S095,S117,S153,S165,S265,S337,S338,S366,S391,S400,S421,S425,S462,S527,S560,S613,S627,S685,S704,S758,S822,S952,S974 */ }
    part def CommonSituationDisplayContent { doc /* @S046 */ }
    part def ComplianceWithRevisedTimes { doc /* @S689 */ }
    part def ConfidenceLevel { doc /* @S691 */ }
    part def ConfidenceRecord { doc /* @S119 */ }
    part def ContingencyFallbackState { doc /* @S735 */ }
    part def ContingencyOperationsConsole { doc /* @S032,S195,S247,S540,S719,S783,S908,S952 */ }
    part def ContractedHandlers { doc /* @S044 */ }
    part def CoreOperationalBaseline { doc /* @S890 */ }
    part def CrewReadiness { doc /* @S127 */ }
    part def DataGovernanceSteward { doc /* @S042,S098,S170,S240,S273,S490,S515,S541,S587,S711,S733,S742,S773,S780,S785,S806,S813,S833,S835,S861,S876,S910,S958,S970 */ }
    part def DecisionSupportFunctions { doc /* @S025 */ }
    part def DeicingCoordinator { doc /* @S040,S092,S294,S375,S378,S390,S875,S969 */ }
    part def DeicingInterfacePoint { doc /* @S295 */ }
    part def DeicingProviders { doc /* @S044 */ }
    part def DelayAbsorptionIndicator { doc /* @S841,S842 */ }
    part def DemandPredictionService { doc /* @S013,S031,S053,S065,S101,S103,S105,S107,S131,S132,S216,S225,S251,S350,S351,S395,S430,S493,S571,S593,S701,S743,S754,S825,S840,S900,S941,S942,S973 */ }
    part def DepartureMeteringService { doc /* @S017,S032,S069,S095,S242,S254,S278,S315,S335,S347,S348,S352,S379,S426,S456,S483,S534,S553,S601,S626,S656,S686,S699,S728,S747,S825,S851,S950,S980 */ }
    part def DesignatedMilitaryCoordinationFunction { doc /* @S045 */ }
    part def DigitalBriefingRoom { doc /* @S031,S071,S086,S345,S506,S734,S834 */ }
    part def DomesticAirports { doc /* @S001 */ }
    part def DoorCycleTime { doc /* @S549 */ }
    part def DownstreamServices { doc /* @S638 */ }
    part def Drivers { doc /* @S548 */ }
    part def EastApronSensor { doc /* @S019,S035,S063,S115,S179,S205,S282,S474,S578,S645,S845 */ }
    part def EffectiveTime { doc /* @S691 */ }
    part def EmergencyResponseCoordinator { doc /* @S041,S096,S414,S499,S874,S968 */ }
    part def EquipmentUnserviceability { doc /* @S526 */ }
    part def EquityConcerns { doc /* @S689 */ }
    part def Exercise { doc /* @S881,S882 */ }
    part def ExpectedDuration { doc /* @S691 */ }
    part def FindingsFromTheReview { doc /* @S810 */ }
    part def FirstIncrement { doc /* @S889 */ }
    part def Flight { doc /* @S265,S570 */ }
    part def FlightDataExchange { doc /* @S018,S033,S052,S053,S103,S128,S131,S278,S593,S638,S684,S827,S840,S940,S941,S979 */ }
    part def FlightIntentMessage { doc /* @S127 */ }
    part def FlightIntentMessageStatus { doc /* @S046 */ }
    part def FreshnessIndicator { doc /* @S823 */ }
    part def FuelingProviders { doc /* @S044 */ }
    part def FutureReleases { doc /* @S959 */ }
    part def GateConflictDetector { doc /* @S019,S035,S210,S364,S386,S439,S459,S468,S470,S472,S509,S558,S582,S657 */ }
    part def GroundDelayProgram { doc /* @S398,S977 */ }
    part def GroundHandlingDispatcher { doc /* @S040,S064,S091,S140,S158,S237,S261,S292,S302,S383,S438,S508,S519,S523,S550,S556,S643,S653,S869,S966 */ }
    part def GroundHandlingPersonnel { doc /* @S869 */ }
    part def GroundServiceProviders { doc /* @S044 */ }
    part def HandlerException { doc /* @S526 */ }
    part def HandlingResourcePlanner { doc /* @S065,S141,S212,S302,S303,S304,S318,S384,S460,S477,S522,S547,S648,S830,S947 */ }
    part def HarborEastAirport { doc /* @S026 */ }
    part def HumanFactorsSafeguards { doc /* @S884 */ }
    part def IdentityAccessService { doc /* @S034,S126,S152,S194,S272,S515,S635,S650,S766,S781,S783,S793,S890,S957,S981 */ }
    part def IncidentRecord { doc /* @S923,S924 */ }
    part def InformationServices { doc /* @S025 */ }
    part def InitialPilot { doc /* @S892 */ }
    part def InitialTraining { doc /* @S878 */ }
    part def IntegratedTacticalManagementPosition { doc /* @S419,S420,S421,S423,S429,S434 */ }
    part def Interface { doc /* @S898,S899 */ }
    part def LakesideRegionalAirport { doc /* @S026 */ }
    part def LoadingPositions { doc /* @S548 */ }
    part def LocalTool { doc /* @S903,S904,S905 */ }
    part def LocalUsers { doc /* @S907 */ }
    part def MaximumLoad { doc /* @S549 */ }
    part def MeridianInternationalAirport { doc /* @S026 */ }
    part def MeridianRegion { doc /* @S001 */ }
    part def MeridianRegionalATFMACDM { doc /* @S397,S415,S416,S435,S441,S489,S675 */ }
    part def MeridianRegionalATFMACDMSystem { doc /* @S162,S172,S909,S910,S911,S913,S915,S916,S919,S922,S937,S939,S945,S946,S948,S951,S953,S969 */ }
    part def MeridianRegionalAirTrafficFlowManagementAndAirportCollaborativeDecisionMakingSystem { doc /* @S838,S850,S863 */ }
    part def MeridianRegionalCapability { doc /* @S025 */ }
    part def MeteorologyBriefingOfficer { doc /* @S041,S056,S057,S085,S086,S087,S112,S133,S163,S372,S434,S512,S819,S858,S873,S967 */ }
    part def MigrationPlan { doc /* @S903 */ }
    part def MilitaryAirspaceLiaison { doc /* @S006,S041,S059,S093,S325,S345,S399,S433,S511,S609,S967 */ }
    part def MobilityAssistanceRequirements { doc /* @S549 */ }
    part def NamedOperationalUser { doc /* @S764 */ }
    part def NetworkOperationsLiaison { doc /* @S039,S083,S084,S339,S413,S480,S510,S614,S674,S871,S917,S938 */ }
    part def NorthRunwayMeter { doc /* @S019,S035,S114,S280,S359,S454,S845 */ }
    part def NorthValleyAirport { doc /* @S026 */ }
    part def OperationalConstraint { doc /* @S691 */ }
    part def OperationalOwner { doc /* @S904 */ }
    part def OperationalProcesses { doc /* @S025 */ }
    part def OperationalSupervisors { doc /* @S918 */ }
    part def OperationalUsers { doc /* @S905 */ }
    part def PadQueueControls { doc /* @S376 */ }
    part def ParticipatingAirport { doc /* @S027 */ }
    part def ParticipatingAirportNetwork { doc /* @S026 */ }
    part def ParticipatingOrganization { doc /* @S960 */ }
    part def ParticipatingRoles { doc /* @S073 */ }
    part def PassengerBusConstraints { doc /* @S549 */ }
    part def PassengerConnectionSensitivity { doc /* @S127 */ }
    part def PassengerTransportProviders { doc /* @S044 */ }
    part def PerformanceAnalyticsWarehouse { doc /* @S034,S074,S099,S123,S148,S173,S197,S248,S274,S322,S346,S370,S394,S418,S489,S514,S538,S565,S590,S616,S639,S665,S712,S737,S760,S776,S804,S836,S837,S839,S840,S856,S887,S890,S957,S982 */ }
    part def PilotAirportSelection { doc /* @S891 */ }
    part def PostExerciseReviews { doc /* @S887 */ }
    part def PostOperationsReport { doc /* @S074,S689,S862,S982 */ }
    part def PostOperationsReportOutputs { doc /* @S046 */ }
    part def PreferredRoute { doc /* @S127 */ }
    part def PrimaryInternationalHub { doc /* @S001 */ }
    part def RampControlLead { doc /* @S040,S063,S090,S142,S159,S184,S200,S202,S204,S205,S206,S208,S210,S211,S213,S218,S219,S244,S262,S283,S304,S357,S378,S387,S446,S473,S508,S545,S556,S614,S642,S647,S654,S677,S678,S749,S766,S770,S818,S867,S917,S966 */ }
    part def RampMovementBoard { doc /* @S017,S032,S063,S203,S216,S222,S244,S255,S311,S361,S377,S427,S445,S450,S458,S469,S525,S551,S581,S646,S677,S703,S770,S801,S844,S947,S980 */ }
    part def RampPersonnel { doc /* @S867 */ }
    part def RampServiceOrganizations { doc /* @S044 */ }
    part def ReadinessGate1 { doc /* @S894 */ }
    part def ReadinessGate2 { doc /* @S895 */ }
    part def ReadinessGate3 { doc /* @S896 */ }
    part def ReadinessGate4 { doc /* @S897 */ }
    part def RecoveryRecommendations { doc /* @S954 */ }
    part def RecurrentTraining { doc /* @S879 */ }
    part def RegionalExpansion { doc /* @S956 */ }
    part def RegionalFlowManagementPersonnel { doc /* @S045 */ }
    part def RegionalFlowManager { doc /* @S010,S038,S050,S077,S078,S093,S094,S117,S121,S137,S228,S246,S286,S327,S343,S345,S367,S393,S396,S399,S410,S411,S416,S420,S463,S479,S492,S513,S532,S555,S573,S598,S614,S634,S675,S687,S696,S698,S721,S729,S753,S766,S768,S800,S808,S814,S842,S864,S911,S917,S926,S938,S959,S961 */ }
    part def RegionalFlowPlatform { doc /* @S012,S022,S023,S028,S030,S031,S032,S033,S034,S035,S047,S051,S073,S075,S087,S101,S104,S109,S130,S147,S164,S191,S223,S228,S246,S247,S250,S259,S268,S302,S314,S318,S319,S320,S333,S344,S349,S367,S368,S371,S422,S444,S459,S464,S465,S513,S517,S539,S540,S563,S564,S593,S611,S612,S617,S621,S660,S661,S691,S706,S707,S708,S713,S714,S715,S716,S738,S752,S755,S756,S767,S775,S787,S789,S812,S824,S831,S882,S888,S897,S905,S906,S908,S912,S926,S936 */ }
    part def RejectionReasons { doc /* @S689 */ }
    part def RequestedDepartureTiming { doc /* @S127 */ }
    part def RunwayLightingOutageCard { doc /* @S693 */ }
    part def ScheduledPassengerOperators { doc /* @S043 */ }
    part def SectorLoadMonitor { doc /* @S019,S035,S106,S329,S408,S432,S484,S592,S593,S598,S943,S973 */ }
    part def SecuritySegregation { doc /* @S549 */ }
    part def ServiceSequencingConflicts { doc /* @S526 */ }
    part def SharedOperationalPicture { doc /* @S046 */ }
    part def ShuttleAvailability { doc /* @S548 */ }
    part def SimulationEvents { doc /* @S883 */ }
    part def SimulationExercises { doc /* @S880 */ }
    part def SlotAllocationEngine { doc /* @S015,S031,S080,S134,S135,S137,S223,S225,S226,S227,S234,S244,S253,S269,S342,S355,S374,S398,S428,S456,S503,S533,S575,S603,S625,S626,S659,S669,S671,S699,S700,S745,S825,S840,S949,S980 */ }
    part def SlotComplianceState { doc /* @S791,S850 */ }
    part def SlotCoordinator { doc /* @S039,S068,S080,S136,S161,S229,S239,S258,S285,S356,S404,S457,S481,S502,S614,S633,S671,S672,S722,S724,S726,S736,S766,S768,S795,S798,S815,S848,S870,S964 */ }
    part def SouthRunwayMeter { doc /* @S019,S035,S114,S280,S359,S455,S845 */ }
    part def SouthportAirport { doc /* @S026 */ }
    part def StaffingGaps { doc /* @S526 */ }
    part def StakeholderOrganization { doc /* @S048 */ }
    part def Stand { doc /* @S646,S652,S663 */ }
    part def StandAccessRouting { doc /* @S549 */ }
    part def StandReadinessIndication { doc /* @S655 */ }
    part def SurfaceSurveillanceAdapter { doc /* @S018,S033,S179,S204,S281,S360,S389,S445,S474,S580,S606,S802,S828,S979 */ }
    part def SwapVolume { doc /* @S689 */ }
    part def SweepTeam { doc /* @S647 */ }
    part def SystemSupportEngineer { doc /* @S042,S171,S688,S727,S732,S772,S780,S807,S835,S877,S910,S914,S916,S918,S920,S921,S923,S927,S971 */ }
    part def TacticalRegulationProposalStatus { doc /* @S046 */ }
    part def TargetOffBlockTimeValues { doc /* @S046 */ }
    part def TerminalCurbSpace { doc /* @S548 */ }
    part def TimeNeededToClearPassengersFromTheAircraftVicinity { doc /* @S549 */ }
    part def TimeSynchronizationService { doc /* @S034,S098,S110,S149,S187,S245,S256,S422,S585,S651,S778,S792,S824,S890,S957 */ }
    part def TowerSequenceManager { doc /* @S017,S032,S180,S217,S242,S254,S275,S279,S283,S297,S334,S380,S411,S445,S450,S536,S552,S583,S601,S702,S801,S844,S950,S980 */ }
    part def TowerSupervisor { doc /* @S040,S060,S061,S066,S089,S121,S143,S160,S175,S183,S189,S202,S218,S243,S263,S277,S280,S287,S296,S313,S345,S358,S368,S388,S401,S425,S475,S500,S605,S614,S676,S693,S748,S766,S769,S817,S866,S917,S959 */ }
    part def TowerSupervisoryPersonnel { doc /* @S045 */ }
    part def TowingProviders { doc /* @S044 */ }
    part def TrainingAssessments { doc /* @S886 */ }
    part def TurnaroundStatus { doc /* @S127 */ }
    part def Users { doc /* @S883,S886 */ }
    part def Vehicles { doc /* @S548 */ }
    part def WeatherFeed { doc /* @S111 */ }
    part def WeatherIngestGateway { doc /* @S018,S033,S057,S066,S086,S102,S108,S109,S111,S182,S409,S434,S610,S819,S943,S979 */ }
    part def WestApronSensor { doc /* @S019,S035,S063,S115,S179,S205,S282,S474,S579,S645,S845 */ }
    part def WorkstationLayouts { doc /* @S885 */ }
    part system {
        part accessControl : AccessControl {
            perform action a0 { doc /* enforce role separation @S786 */ }
        }
        part accessLimitations : AccessLimitations;
        part accessibleBoardingSupport : AccessibleBoardingSupport;
        part affectedResource : AffectedResource;
        part aggregatedMetrics : AggregatedMetrics;
        part airNavigationServiceParticipation : AirNavigationServiceParticipation;
        part airTrafficControllers : AirTrafficControllers {
            perform action a0 { doc /* be trained to understand how flow measures, sequencing changes, and calculated times affect sector workload @S865 */ }
        }
        part aircraftOperatorRepresentative : AircraftOperatorRepresentative {
            perform action a0 { doc /* align airline intentions, schedule constraints, and slot management decisions with the shared plan @S039 */ }
            perform action a1 { doc /* validates that operator priorities are visible @S055 */ }
            perform action a2 { doc /* provides aircraft-specific constraints when requested @S082 */ }
            perform action a3 { doc /* ensuring that operator commitments entered in the Airport CDM Portal are operationally achievable @S082 */ }
            perform action a4 { doc /* remains accountable for operator acceptance of any revised off-block expectation @S215 */ }
            perform action a5 { doc /* keeping aircraft readiness information current @S291 */ }
            perform action a6 { doc /* declare whether the operator can accept a later off-block time @S316 */ }
            perform action a7 { doc /* requests reconsideration through the Airport CDM Portal @S363 */ }
            perform action a8 { doc /* review proposed timing changes @S437 */ }
            perform action a9 { doc /* confirms whether the aircraft can accept a revised stand assignment @S476 */ }
            perform action a10 { doc /* sends the Crew Duty Extension Log @S620 */ }
            perform action a11 { doc /* remains responsible for the correctness of crew legality inputs @S622 */ }
            perform action a12 { doc /* provided the ranking @S630 */ }
            perform action a13 { doc /* identifies a flight that can exchange its assigned demand position @S666 */ }
            perform action a14 { doc /* records concurrence in the Airport CDM Portal @S673 */ }
            perform action a15 { doc /* acknowledge manual slot assignments through recorded voice readback or an agreed written channel @S725 */ }
            perform action a16 { doc /* view airline-relevant planning data @S771 */ }
            perform action a17 { doc /* submit coordination inputs @S771 */ }
            perform action a18 { doc /* proposes a substitution @S797 */ }
            perform action a19 { doc /* challenge cancellation avoidance results through the Collaborative Decision Log @S854 */ }
            perform action a20 { doc /* submit, review, and update Flight Intent Message data @S868 */ }
            perform action a21 { doc /* assess the operational effect of Calculated Takeoff Time and Target Off Block Time changes @S868 */ }
            perform action a22 { doc /* providing operationally realistic airline intentions @S965 */ }
            perform action a23 { doc /* honoring agreed times @S965 */ }
        }
        part aircraftRegistration : AircraftRegistration;
        part airlineInterfaceAdapter : AirlineInterfaceAdapter {
            perform action a0 { doc /* provide the data feeds @S018 */ }
            perform action a1 { doc /* provide managed integration points with external systems @S033 */ }
            perform action a2 { doc /* validates message structure @S128 */ }
            perform action a3 { doc /* maps carrier codes to the Business Rules Registry @S128 */ }
            perform action a4 { doc /* forwards accepted intent data to the Flight Data Exchange @S128 */ }
            perform action a5 { doc /* supplies operator preferences @S235 */ }
            perform action a6 { doc /* produces the Late Baggage Tag List @S452 */ }
            perform action a7 { doc /* maintains airline-provided connection exposure @S478 */ }
            perform action a8 { doc /* accepts legality indicators @S618 */ }
            perform action a9 { doc /* validates the timeliness, flight association, and airline ownership of connection-risk data @S741 */ }
            perform action a10 { doc /* apply carrier-specific format checks @S829 */ }
            perform action a11 { doc /* preserving the common operational meaning @S829 */ }
        }
        part airlineOperationsCentre : AirlineOperationsCentre {
            perform action a0 { doc /* submits a Flight Intent Message through the Airline Interface Adapter @S126 */ }
            perform action a1 { doc /* receive those constraints through the Airline Interface Adapter @S135 */ }
            perform action a2 { doc /* view them in the Airport CDM Portal @S135 */ }
            perform action a3 { doc /* proposes a retime, cancellation, aircraft substitution, or route change @S139 */ }
            perform action a4 { doc /* submits an updated Flight Intent Message @S139 */ }
        }
        part airlineOperationsCentreIntegration : AirlineOperationsCentreIntegration {
            perform action a0 { doc /* provides the operational bridge between carrier recovery planning and the Meridian Regional Air Traffic Flow Management and Airport Collaborative Decision-Making System @S124 */ }
        }
        part airlineOperationsCentres : AirlineOperationsCentres {
            perform action a0 { doc /* submit conservative intents @S146 */ }
        }
        part airlineOperationsCoordinator : AirlineOperationsCoordinator {
            perform action a0 { doc /* align airline intentions, schedule constraints, and slot management decisions with the shared plan @S039 */ }
            perform action a1 { doc /* reviews material deviations from filed intent @S054 */ }
            perform action a2 { doc /* represents carrier operating priorities @S081 */ }
            perform action a3 { doc /* confirms that Flight Intent Message updates are complete, timely, and traceable @S081 */ }
            perform action a4 { doc /* correct them without informal voice coordination @S129 */ }
            perform action a5 { doc /* evaluates each constraint against crew legality, aircraft rotation continuity, maintenance positioning, and passenger recovery commitments @S138 */ }
            perform action a6 { doc /* keeping the Flight Intent Message status, Target Off Block Time, passenger readiness indicator, and aircraft operational constraint notes current @S157 */ }
            perform action a7 { doc /* uses the delay slip @S237 */ }
            perform action a8 { doc /* requesting an exemption review for a crew connectivity constraint @S237 */ }
            perform action a9 { doc /* reviews the proposed Target Off Block Time against aircraft readiness, crew availability, passenger connection risk, and operator recovery priorities @S259 */ }
            perform action a10 { doc /* confirm any operator-requested Target Off Block Time revision in the Airport CDM Portal @S260 */ }
            perform action a11 { doc /* request a sequence review @S284 */ }
            perform action a12 { doc /* decide whether a swap between company flights is operationally meaningful @S317 */ }
            perform action a13 { doc /* uses the shared display to identify flights that may need rerouting, delayed pushback planning, or revised operator intent @S338 */ }
            perform action a14 { doc /* confirms whether each affected aircraft can absorb the assigned delay at stand @S362 */ }
            perform action a15 { doc /* reviews aircraft readiness @S385 */ }
            perform action a16 { doc /* request a later pad entry @S385 */ }
            perform action a17 { doc /* reviews the proposed treatment for network impact @S403 */ }
            perform action a18 { doc /* identifies flights where upstream delay would create a disproportionate connection or aircraft rotation penalty @S403 */ }
            perform action a19 { doc /* review proposed timing changes @S437 */ }
            perform action a20 { doc /* confirming whether the affected flight should keep its Target Off Block Time, request a new value, or accept a later Calculated Takeoff Time @S451 */ }
            perform action a21 { doc /* uses the Gate Reopening Memo to confirm when a previously unavailable gate can be planned again for arrival handling, boarding, and connection recovery @S472 */ }
            perform action a22 { doc /* supplies passenger, crew, maintenance, and aircraft rotation impacts @S507 */ }
            perform action a23 { doc /* confirms whether the aircraft can remain on plan, accept a short readiness deferral, or require a revised departure intent @S521 */ }
            perform action a24 { doc /* uses remote stands to protect connection banks @S546 */ }
            perform action a25 { doc /* request revision of the Target Off Block Time @S554 */ }
            perform action a26 { doc /* uses customs hold visibility to adjust connection protection, passenger messaging assumptions, and expected aircraft turnaround timing @S574 */ }
            perform action a27 { doc /* reviews the airport-level result @S604 */ }
            perform action a28 { doc /* mark a flight as non-recoverable by delay after a specified time @S623 */ }
            perform action a29 { doc /* prevents automated suggestions that would create an infeasible rotation @S623 */ }
            perform action a30 { doc /* provided the ranking @S630 */ }
            perform action a31 { doc /* propose a revised Target Off Block Time @S658 */ }
            perform action a32 { doc /* enters the proposed substitution in the Airport CDM Portal @S667 */ }
            perform action a33 { doc /* uses the release note to confirm that a candidate substitution is eligible for customs release @S679 */ }
            perform action a34 { doc /* requesting a slot swap @S679 */ }
            perform action a35 { doc /* acknowledge manual slot assignments through recorded voice readback or an agreed written channel @S725 */ }
            perform action a36 { doc /* sends the Passenger Misconnect Count @S740 */ }
            perform action a37 { doc /* view airline-relevant planning data @S771 */ }
            perform action a38 { doc /* submit coordination inputs @S771 */ }
            perform action a39 { doc /* uses the permission email to justify an approved slot substitution @S795 */ }
            perform action a40 { doc /* submitted schedule intent, readiness status, and Target Off Block Time updates through approved interfaces @S820 */ }
            perform action a41 { doc /* challenge cancellation avoidance results through the Collaborative Decision Log @S854 */ }
            perform action a42 { doc /* submit, review, and update Flight Intent Message data @S868 */ }
            perform action a43 { doc /* assess the operational effect of Calculated Takeoff Time and Target Off Block Time changes @S868 */ }
            perform action a44 { doc /* compare recommendations with actual outcomes @S959 */ }
            perform action a45 { doc /* providing operationally realistic airline intentions @S965 */ }
            perform action a46 { doc /* honoring agreed times @S965 */ }
        }
        part airlines : Airlines;
        part airport : Airport {
            perform action a0 { doc /* exchange operational data @S890 */ }
        }
        part airportAcceptanceRateConstraints : AirportAcceptanceRateConstraints;
        part airportCDMPortal : AirportCDMPortal {
            perform action a0 { doc /* provides airport stakeholders with a controlled interface @S016 */ }
            perform action a1 { doc /* sharing operational readiness information @S016 */ }
            perform action a2 { doc /* confirming decisions that affect the surface and terminal sequence @S016 */ }
            perform action a3 { doc /* support planning and collaborative assessment @S031 */ }
            perform action a4 { doc /* provides the shared operational workspace @S150 */ }
            perform action a5 { doc /* highlight the affected flight @S166 */ }
            perform action a6 { doc /* notify the role accountable for the next update through the Alert Distribution Hub @S166 */ }
            perform action a7 { doc /* preserve the last synchronized milestone set @S172 */ }
            perform action a8 { doc /* clearly mark any updates entered under degraded operating procedures @S172 */ }
            perform action a9 { doc /* records duty desk confirmations as operational annotations @S185 */ }
            perform action a10 { doc /* presents each proposed value with its confidence status, last update time, and the reason code @S264 */ }
            perform action a11 { doc /* requires a revised reason code @S270 */ }
            perform action a12 { doc /* marks the earlier value as superseded rather than deleted @S270 */ }
            perform action a13 { doc /* publish tower readiness changes @S293 */ }
            perform action a14 { doc /* presents the resource-driven feasibility status @S312 */ }
            perform action a15 { doc /* displays the active restriction status, expected operational effect, and any related coordination notes @S337 */ }
            perform action a16 { doc /* records the selected fluid type, mixture ratio, treatment start time, treatment completion time, and expected holdover reference for each treated aircraft @S381 */ }
            perform action a17 { doc /* presents the resulting arrival plan to Aircraft Operator Representative users @S405 */ }
            perform action a18 { doc /* records acknowledgements in the Collaborative Decision Log @S405 */ }
            perform action a19 { doc /* exposes agreed Target Off Block Time values and stakeholder remarks to the tactical position @S429 */ }
            perform action a20 { doc /* presents each gate conflict with the affected flights, passenger connection exposure, aircraft size compatibility, and the latest feasible off-block time @S470 */ }
            perform action a21 { doc /* shows downstream departure-fix pressure @S485 */ }
            perform action a22 { doc /* uses the window token to preserve the agreed pushback opportunity @S503 */ }
            perform action a23 { doc /* keeps detailed handler notes available to authorized users @S527 */ }
            perform action a24 { doc /* prompts the accountable role to record the proposed mitigation in the Collaborative Decision Log @S531 */ }
            perform action a25 { doc /* records the operational reason, affected flights, expected passenger transfer duration, and responsible control position @S559 */ }
            perform action a26 { doc /* displays border and customs status in a controlled view @S572 */ }
            perform action a27 { doc /* adjusted Target Off Block Time values published @S602 */ }
            perform action a28 { doc /* uses the shuttle count @S648 */ }
            perform action a29 { doc /* confirm that remote-stand passenger transfer demand is consistent with stand readiness timing @S648 */ }
            perform action a30 { doc /* records each stand readiness confirmation with the stand identifier, responsible organization, inspection time, readiness constraint, and confirming user identity @S649 */ }
            perform action a31 { doc /* validates the submitting user through the Identity Access Service @S668 */ }
            perform action a32 { doc /* blocks any proposal from a party without delegated operator authority @S668 */ }
            perform action a33 { doc /* keeps the proposal pending @S681 */ }
            perform action a34 { doc /* prevents the Slot Allocation Engine from publishing the revised slot assignment @S681 */ }
            perform action a35 { doc /* presents infrastructure events @S695 */ }
            exhibit state modes {
                state s0 { doc /* unavailable @S195 */ }
            }
        }
        part airportCapacityPlan : AirportCapacityPlan;
        part airportCapacityPlanAssumptions : AirportCapacityPlanAssumptions;
        part airportDutyDesk : AirportDutyDesk {
            perform action a0 { doc /* reviews tower inputs, airport operations reports, and surveillance indications @S178 */ }
            perform action a1 { doc /* confirming whether a local condition should be reflected in the Airport Capacity Plan @S178 */ }
            exhibit state modes {
                state s0 { doc /* Adverse Weather Mode @S177 */ }
                state s1 { doc /* Capacity Reduction State @S177 */ }
                state s2 { doc /* Normal Operations @S177 */ }
                state s3 { doc /* Recovery Phase @S177 */ }
            }
        }
        part airportDutyManager : AirportDutyManager {
            perform action a0 { doc /* represent local airport, tower, ramp, handling, and winter operations considerations @S040 */ }
            perform action a1 { doc /* confirms terminal opening status, essential facility readiness, and airport service constraints @S062 */ }
            perform action a2 { doc /* confirms that airport-side constraints are reflected consistently across the Airport CDM Portal and the Common Situation Display @S088 */ }
            perform action a3 { doc /* request a manual capacity review @S116 */ }
            perform action a4 { doc /* monitors the Common Situation Display @S144 */ }
            perform action a5 { doc /* maintaining the Airport Capacity Plan @S162 */ }
            perform action a6 { doc /* declaring local operating impacts @S162 */ }
            perform action a7 { doc /* confirming transitions between Normal Operations, Adverse Weather Mode, Capacity Reduction State, and Recovery Phase @S162 */ }
            perform action a8 { doc /* maintains the airport duty desk @S177 */ }
            perform action a9 { doc /* confirm that the duty desk has a current record of pavement status @S181 */ }
            perform action a10 { doc /* endorsing any declared capacity change @S181 */ }
            perform action a11 { doc /* agree on the operational interpretation @S183 */ }
            perform action a12 { doc /* verifies that airfield operations checks have been completed @S190 */ }
            perform action a13 { doc /* requesting changes to Airport Acceptance Rate values or departure metering assumptions @S190 */ }
            perform action a14 { doc /* briefs open safety checks, unresolved surveillance discrepancies, and any tower coordination points that remain active @S196 */ }
            perform action a15 { doc /* handover has identified active surface constraints @S198 */ }
            perform action a16 { doc /* confirm the active interpretation of the restriction @S345 */ }
            perform action a17 { doc /* agree whether the metering horizon should be extended @S368 */ }
            perform action a18 { doc /* declare Normal Operations, Adverse Weather Mode, Capacity Reduction State, Recovery Phase, or Contingency Fallback State @S435 */ }
            perform action a19 { doc /* records the operational significance of the condition in the Airport CDM Portal @S447 */ }
            perform action a20 { doc /* sets the recovery priority for stands that can be reopened quickly @S471 */ }
            perform action a21 { doc /* sends the Medical Diversion Notice @S496 */ }
            perform action a22 { doc /* publishes the planned remote stand operating posture in the Airport CDM Portal @S544 */ }
            perform action a23 { doc /* reduce planned remote stand use @S563 */ }
            perform action a24 { doc /* produces the Customs Hold Release Note @S568 */ }
            perform action a25 { doc /* declare a localized Capacity Reduction State @S660 */ }
            perform action a26 { doc /* uses the Apron Sweep Completion Note to confirm that apron availability constraints do not invalidate an approved substitution @S678 */ }
            perform action a27 { doc /* ensuring that declared service reductions are entered promptly @S692 */ }
            perform action a28 { doc /* confirms closure in the Airport CDM Portal @S713 */ }
            perform action a29 { doc /* declaring the Contingency Fallback State @S716 */ }
            perform action a30 { doc /* consultation with the Regional Flow Manager, Tower Supervisor, and System Support Engineer @S716 */ }
            perform action a31 { doc /* conducts fallback briefings at intervals appropriate to the traffic level @S734 */ }
            perform action a32 { doc /* publishes the current operating basis through the Digital Briefing Room @S734 */ }
            perform action a33 { doc /* uses the Airport CDM Portal to see whether airline recovery actions are concentrated in one bank @S750 */ }
            perform action a34 { doc /* review late airport-driven changes @S809 */ }
            perform action a35 { doc /* record whether the operational justification was valid @S809 */ }
            perform action a36 { doc /* own airport capacity declarations @S816 */ }
            perform action a37 { doc /* receive benefit summaries @S860 */ }
            perform action a38 { doc /* recognize when an Airport Capacity Plan requires revision @S872 */ }
            perform action a39 { doc /* retain operational command authority @S917 */ }
            perform action a40 { doc /* compare recommendations with actual outcomes @S959 */ }
            perform action a41 { doc /* confirm capacity assumptions used for airport-level coordination @S962 */ }
        }
        part airportNetwork : AirportNetwork {
            perform action a0 { doc /* operates near declared capacity @S003 */ }
            exhibit state modes {
                state s0 { doc /* Normal Operations @S003 */ }
            }
        }
        part airportOnboarding : AirportOnboarding;
        part airportParticipant : AirportParticipant {
            perform action a0 { doc /* update a material change @S167 */ }
            perform action a1 { doc /* enter a provisional value with an uncertainty flag @S168 */ }
        }
        part airportStakeholders : AirportStakeholders;
        part airspacePlanningPersonnel : AirspacePlanningPersonnel;
        part airspaceSectorPlanner : AirspaceSectorPlanner {
            perform action a0 { doc /* participate @S041 */ }
            perform action a1 { doc /* declares expected sector constraints, route availability assumptions, and any planned staffing limitations @S058 */ }
            perform action a2 { doc /* supports the Regional Flow Manager @S079 */ }
            perform action a3 { doc /* validating sector constraints in the Sector Load Monitor @S079 */ }
            perform action a4 { doc /* advising whether demand smoothing is required before tactical execution @S079 */ }
            perform action a5 { doc /* converts confirmed restricted area information into sector availability assumptions @S326 */ }
            perform action a6 { doc /* checks whether existing flight plans require rerouting, metering, or ground delay action @S326 */ }
            perform action a7 { doc /* confirm the active interpretation of the restriction @S345 */ }
            perform action a8 { doc /* confirms whether terminal and en-route sector loads can absorb the regulated stream @S402 */ }
            perform action a9 { doc /* monitors sector demand @S432 */ }
            perform action a10 { doc /* confirms whether proposed measures are compatible with en route capacity @S432 */ }
            perform action a11 { doc /* protects sector margins @S501 */ }
            perform action a12 { doc /* request a Tactical Regulation Proposal @S501 */ }
            perform action a13 { doc /* validates the operational meaning of each constraint @S608 */ }
            perform action a14 { doc /* coordinate regional constraints, sector load conditions, and network measures @S871 */ }
            perform action a15 { doc /* timely disclosure of weather, sector, and airspace constraints @S967 */ }
        }
        part alertDistributionHub : AlertDistributionHub {
            perform action a0 { doc /* provide managed integration points with external systems @S033 */ }
            perform action a1 { doc /* notifies participating roles that the morning plan is available @S073 */ }
            perform action a2 { doc /* notifies the Regional Flow Manager, Tower Supervisor, and Airline Operations Coordinator that the capacity picture may change @S121 */ }
            perform action a3 { doc /* distributes approved duty coordination alerts to affected operational roles @S193 */ }
            perform action a4 { doc /* applies subscription rules from the Business Rules Registry @S332 */ }
            perform action a5 { doc /* highlights the affected runway queue on the Common Situation Display @S366 */ }
            perform action a6 { doc /* routed through the Alert Distribution Hub for stakeholder acknowledgement @S440 */ }
            perform action a7 { doc /* distribute surface equipment and apron congestion advisories to subscribed operational roles @S461 */ }
            perform action a8 { doc /* provides role-specific alert summaries @S505 */ }
            perform action a9 { doc /* routes notifications according to severity, time to milestone, and subscribed operational role @S529 */ }
            perform action a10 { doc /* issues targeted alerts @S588 */ }
            perform action a11 { doc /* sends notifications @S614 */ }
            perform action a12 { doc /* sends notifications @S705 */ }
            perform action a13 { doc /* raised urgent discrepancies @S834 */ }
        }
        part approvalLatency : ApprovalLatency;
        part approvingAuthority : ApprovingAuthority;
        part arrivalRegulationConsole : ArrivalRegulationConsole {
            perform action a0 { doc /* support the transition from regional planning decisions to executable airport and tower actions @S017 */ }
            perform action a1 { doc /* support tactical airport and regional coordination @S032 */ }
            perform action a2 { doc /* highlights inbound demand periods where holding, speed control, or upstream sequencing may be needed @S070 */ }
            perform action a3 { doc /* presents proposed arrival opportunities @S241 */ }
            perform action a4 { doc /* applies airspace capacity reductions to inbound flows @S336 */ }
            perform action a5 { doc /* issues alerts before predicted holding stacks form @S407 */ }
            perform action a6 { doc /* presents diversion options with estimated holding exposure, likely gate or stand impact @S495 */ }
            perform action a7 { doc /* suppress handler-exception annotations for arriving flights @S535 */ }
            perform action a8 { doc /* uses the Medical Diversion Notice to protect arrival priority, stand assignment timing, and downstream border coordination @S576 */ }
            perform action a9 { doc /* applies the revised Airport Acceptance Rate @S698 */ }
            perform action a10 { doc /* display arrival demand @S729 */ }
            perform action a11 { doc /* show inbound connection pressure @S757 */ }
        }
        part auditEventLedger : AuditEventLedger {
            perform action a0 { doc /* preserve the rationale, timing, and authorization of material operational decisions @S021 */ }
            perform action a1 { doc /* provide governance, security, traceability, and performance measurement capabilities @S034 */ }
            perform action a2 { doc /* retains the trace from incoming forecast product to capacity value @S123 */ }
            perform action a3 { doc /* retains movement updates from the Ramp Movement Board @S222 */ }
            perform action a4 { doc /* stores the previous value, new value, responsible user or automated function, timestamp, authority basis, and applicable operating state for every target time change @S271 */ }
            perform action a5 { doc /* preserves the sequence history @S289 */ }
            perform action a6 { doc /* preserves the same decision history @S488 */ }
            perform action a7 { doc /* retain traceability of who viewed, changed, or approved diversion decisions @S515 */ }
            perform action a8 { doc /* records who raised, changed, acknowledged, or closed each escalated exception @S537 */ }
            perform action a9 { doc /* records who entered or changed a recovery choice, the effective time, the affected flight reference, and the reason category @S636 */ }
            perform action a10 { doc /* stores readiness changes, user acknowledgements, hazard closures, and release decisions @S664 */ }
            perform action a11 { doc /* records each approval, rejection, cancellation, and override @S683 */ }
            perform action a12 { doc /* preserves the technical record of submission, validation, publication, acknowledgement, and withdrawal @S710 */ }
            perform action a13 { doc /* capture successful and failed authentication attempts, role changes, privilege elevations, operational approvals, configuration changes, data exports, and emergency access activations @S777 */ }
            perform action a14 { doc /* preserve the time source @S792 */ }
            perform action a15 { doc /* Certification results shall be recorded @S901 */ }
            perform action a16 { doc /* record each proposed option, the user response, and the final decision @S955 */ }
            perform action a17 { doc /* support traceability, least-privilege access, and after-action accountability @S981 */ }
        }
        part auditOutputs : AuditOutputs;
        part auditProcessing : AuditProcessing {
            perform action a0 { doc /* treat reconciled contingency actions as part of the same operational record @S788 */ }
        }
        part authorizedAirportAirlineAndFlowManagementUsers : AuthorizedAirportAirlineAndFlowManagementUsers;
        part authorizedOperationalUsers : AuthorizedOperationalUsers;
        part authorizedUsers : AuthorizedUsers;
        part basedCarriers : BasedCarriers;
        part businessRulesRegistry : BusinessRulesRegistry {
            perform action a0 { doc /* provide governance, security, traceability, and performance measurement capabilities @S034 */ }
            perform action a1 { doc /* supplies the applicable thresholds for alerting, approval routing, and measure publication @S436 */ }
            perform action a2 { doc /* holds the local rules for connection protection, gate compatibility, towing priority, stand reopening approval, and minimum turnaround recovery margins @S486 */ }
            perform action a3 { doc /* confirms that the condition is operationally material @S534 */ }
            perform action a4 { doc /* tighten escalation thresholds for flights close to departure @S539 */ }
            perform action a5 { doc /* suppress low-impact local issues @S539 */ }
            perform action a6 { doc /* defines which border and customs states block sequencing @S586 */ }
            perform action a7 { doc /* defines which preference fields are mandatory, optional, or hidden from other participants @S631 */ }
            perform action a8 { doc /* provides the governing parameters for precedence, equity, customs eligibility, minimum notification time, and prohibited trades @S670 */ }
            perform action a9 { doc /* defines which infrastructure events require approval @S706 */ }
            perform action a10 { doc /* hold the current validation thresholds, allowable reason codes, and exception rules @S831 */ }
            perform action a11 { doc /* retain the local parameters needed for Meridian operations @S939 */ }
        }
        part calculatedTakeoffTime : CalculatedTakeoffTime;
        part calculatedTakeoffTimeValues : CalculatedTakeoffTimeValues;
        part candidateAirport : CandidateAirport {
            perform action a0 { doc /* provide evidence @S893 */ }
        }
        part capacityAssessmentModule : CapacityAssessmentModule {
            perform action a0 { doc /* supports the assessment of declared and tactical capacity @S014 */ }
            perform action a1 { doc /* support planning and collaborative assessment @S031 */ }
            perform action a2 { doc /* combines the runway declaration, weather outlook, airspace constraints, stand readiness, and ground resource assumptions into a proposed Airport Acceptance Rate by period @S066 */ }
            perform action a3 { doc /* indicates that declared capacity no longer matches observed conditions @S094 */ }
            perform action a4 { doc /* combines demand projections with the Airport Capacity Plan @S107 */ }
            perform action a5 { doc /* determine whether a published Airport Acceptance Rate remains feasible @S107 */ }
            perform action a6 { doc /* applies the current wind, visibility, and precipitation assumptions @S114 */ }
            perform action a7 { doc /* flags the associated capacity values as provisional @S120 */ }
            perform action a8 { doc /* compares that demand with the Airport Capacity Plan and the current Airport Acceptance Rate @S132 */ }
            perform action a9 { doc /* recommending operating limits @S132 */ }
            perform action a10 { doc /* uses the Storm Cell Snapshot to qualify capacity confidence during convective weather impacts @S133 */ }
            perform action a11 { doc /* use the confirmed airport position to recalculate available capacity @S192 */ }
            perform action a12 { doc /* applies the active Airport Capacity Plan and Airport Acceptance Rate @S252 */ }
            perform action a13 { doc /* determine whether the proposed demand pattern remains operationally feasible @S252 */ }
            perform action a14 { doc /* treats a restriction as a time-bounded reduction in route, sector, or airport throughput @S328 */ }
            perform action a15 { doc /* recalculates the effective Airport Acceptance Rate @S341 */ }
            perform action a16 { doc /* passes the revised assumption into the operational planning cycle @S341 */ }
            perform action a17 { doc /* compares that demand with the active Airport Acceptance Rate, runway configuration, taxiway constraints, and sector limits @S351 */ }
            perform action a18 { doc /* reduces practical departure capacity @S373 */ }
            perform action a19 { doc /* calculates candidate Airport Acceptance Rate values @S400 */ }
            perform action a20 { doc /* exposes the operational basis for each value on the Common Situation Display @S400 */ }
            perform action a21 { doc /* recalculates available capacity @S431 */ }
            perform action a22 { doc /* converts persistent surface constraints into reduced stand throughput, extended turn buffers, or modified taxi-out assumptions @S448 */ }
            perform action a23 { doc /* evaluates runway availability, stand availability, sector load, handling capacity, and service constraints @S494 */ }
            perform action a24 { doc /* reflects persistent remote stand service limits as a reduction in practical gate throughput @S557 */ }
            perform action a25 { doc /* applies persistent apron congestion as a local capacity factor @S584 */ }
            perform action a26 { doc /* evaluates whether the affected traffic is dominated by departures, arrivals, or mixed flows @S594 */ }
            perform action a27 { doc /* applies Business Rules Registry thresholds @S600 */ }
            perform action a28 { doc /* converts the limit into a runway configuration constraint @S694 */ }
            perform action a29 { doc /* calculates the operational effect @S697 */ }
            perform action a30 { doc /* reject data that lacks a trusted timestamp @S825 */ }
            perform action a31 { doc /* record the available Airport Acceptance Rate used in each baseline @S853 */ }
            perform action a32 { doc /* compare planned capacity, observed throughput, and predicted constraint persistence @S944 */ }
            exhibit state modes {
                state s0 { doc /* Adverse Weather Mode @S584 */ }
                state s1 { doc /* Normal Operations @S584 */ }
            }
        }
        part capacityValues : CapacityValues {
            exhibit state modes {
                state s0 { doc /* provisional @S120 */ }
            }
        }
        part cargoAndGeneralAviationAerodromes : CargoAndGeneralAviationAerodromes;
        part cargoOperators : CargoOperators;
        part changesMadeInsideTheFreezeHorizon : ChangesMadeInsideTheFreezeHorizon;
        part charterOperators : CharterOperators;
        part collaborativeDecisionLog : CollaborativeDecisionLog {
            perform action a0 { doc /* preserve the rationale, timing, and authorization of material operational decisions @S021 */ }
            perform action a1 { doc /* records who changed a value, when the change was made, whether the change was provisional or confirmed, and what operational decision relied on it @S169 */ }
            perform action a2 { doc /* captures the time, origin, and rationale for each local coordination decision @S186 */ }
            perform action a3 { doc /* records each challenge, counterproposal, acceptance, rejection, and reason code associated with the Target Off Block Time and Calculated Takeoff Time @S267 */ }
            perform action a4 { doc /* captures winter-mode decisions @S392 */ }
            perform action a5 { doc /* records each accepted conflict resolution @S487 */ }
            perform action a6 { doc /* records the operational reason @S589 */ }
            perform action a7 { doc /* records the constraint, chosen conversion rule, responsible actor, and time of approval @S615 */ }
            perform action a8 { doc /* records any agreed operational outcome @S637 */ }
            perform action a9 { doc /* captures the proposed flights, the reason code, the user confirmations, the governance outcome, and the final decision time @S682 */ }
            perform action a10 { doc /* records the time of publication, approving role, capacity effect, affected services, and any later amendment @S709 */ }
            perform action a11 { doc /* retain the stated reason, decision time, affected flight, and visible operational context @S794 */ }
            perform action a12 { doc /* Certification results shall be recorded @S901 */ }
            perform action a13 { doc /* preserve the operational context of major incidents @S925 */ }
            perform action a14 { doc /* record each proposed option, the user response, and the final decision @S955 */ }
        }
        part collaborativeDecisionLogEntries : CollaborativeDecisionLogEntries;
        part commonServices : CommonServices {
            perform action a0 { doc /* support regional flow management and Airport Collaborative Decision-Making participation @S030 */ }
        }
        part commonSituationDisplay : CommonSituationDisplay {
            perform action a0 { doc /* give authorized users a shared view of demand, capacity, constraints, and active traffic management measures @S020 */ }
            perform action a1 { doc /* presents the approved pre-tactical baseline @S072 */ }
            perform action a2 { doc /* distinguishes values supplied by connected services, values confirmed by users, and values that have exceeded the configured freshness threshold @S165 */ }
            perform action a3 { doc /* shows the current agreed target set @S265 */ }
            perform action a4 { doc /* highlights expired treatments, pad closures, fluid shortages, and ramp blockages @S391 */ }
            perform action a5 { doc /* provides the base map, timeline, flight list, and measure status panels @S421 */ }
            perform action a6 { doc /* highlights active surface advisories with the affected stands, taxi segments, runway meters, and flight identifiers @S462 */ }
            perform action a7 { doc /* shows only the flight impact, severity, and expected recovery window @S527 */ }
            perform action a8 { doc /* presents remote stand status in time order @S560 */ }
            perform action a9 { doc /* displayed converted measures @S613 */ }
            perform action a10 { doc /* shows crew legality impacts as coded operational states @S627 */ }
            perform action a11 { doc /* presents the updated Calculated Takeoff Time and Target Off Block Time @S685 */ }
            perform action a12 { doc /* shows the affected resource, start time, review time, and current decision status @S704 */ }
            perform action a13 { doc /* presents passenger disruption cues with clear labeling @S758 */ }
            perform action a14 { doc /* displayed freshness indicators @S822 */ }
            exhibit state modes {
                state s0 { doc /* feasible @S627 */ }
                state s1 { doc /* infeasible @S627 */ }
                state s2 { doc /* operator review required @S627 */ }
                state s3 { doc /* time critical @S627 */ }
            }
        }
        part commonSituationDisplayContent : CommonSituationDisplayContent;
        part complianceWithRevisedTimes : ComplianceWithRevisedTimes;
        part confidenceLevel : ConfidenceLevel;
        part confidenceRecord : ConfidenceRecord {
            perform action a0 { doc /* stores the originating feed, the processing time, the transformation version, and any manual override @S119 */ }
        }
        part contingencyFallbackState : ContingencyFallbackState;
        part contingencyOperationsConsole : ContingencyOperationsConsole {
            perform action a0 { doc /* support tactical airport and regional coordination @S032 */ }
            perform action a1 { doc /* provides a degraded channel for recording tower and duty desk decisions @S195 */ }
            perform action a2 { doc /* preserves the last valid allocation @S247 */ }
            perform action a3 { doc /* supports manual amendments @S247 */ }
            perform action a4 { doc /* marks the resulting Slot Compliance State as provisional @S247 */ }
            perform action a5 { doc /* provides a protected operating position with independent access to the Flight Data Exchange, Alert Distribution Hub, Audit Event Ledger, and Digital Briefing Room @S719 */ }
            perform action a6 { doc /* accept emergency access activations @S783 */ }
            perform action a7 { doc /* generated recovery options @S952 */ }
        }
        part contractedHandlers : ContractedHandlers;
        part coreOperationalBaseline : CoreOperationalBaseline;
        part crewReadiness : CrewReadiness;
        part dataGovernanceSteward : DataGovernanceSteward {
            perform action a0 { doc /* maintain data quality, access control, operational continuity, and controlled configuration of the Regional Flow Platform @S042 */ }
            perform action a1 { doc /* verifies that operational decisions, role acknowledgements, and exception handling are captured in the Audit Event Ledger @S098 */ }
            perform action a2 { doc /* defines the mandatory fields, permissible status values, retention rules, and data quality thresholds @S170 */ }
            perform action a3 { doc /* ensures that exemption categories, priority codes, and fairness metrics are versioned in the Business Rules Registry @S240 */ }
            perform action a4 { doc /* reviews audit samples @S273 */ }
            perform action a5 { doc /* ensures that passenger connection information used for prioritization is aggregated or role-restricted @S490 */ }
            perform action a6 { doc /* ensures that sensitive operational and passenger information remains role-restricted @S515 */ }
            perform action a7 { doc /* ensures that baggage and handler data exposed outside the local operation is limited to operational necessity @S541 */ }
            perform action a8 { doc /* maintains the access rules and retention rules for border and customs data @S587 */ }
            perform action a9 { doc /* monitors data quality for infrastructure events @S711 */ }
            perform action a10 { doc /* confirms which data sets may be trusted @S733 */ }
            perform action a11 { doc /* marks any later synchronization from fallback records for reconciliation review @S733 */ }
            perform action a12 { doc /* defines the acceptable aggregation level @S742 */ }
            perform action a13 { doc /* manage data retention rules, reference data ownership, and audit review processes @S773 */ }
            perform action a14 { doc /* post-event review @S785 */ }
            perform action a15 { doc /* verify that audit fields remain complete, immutable, and traceable @S806 */ }
            perform action a16 { doc /* maintain the data ownership register @S813 */ }
            perform action a17 { doc /* coordinate updates through the Business Rules Registry @S813 */ }
            perform action a18 { doc /* coordinate discrepancy resolution with the responsible operational owner @S833 */ }
            perform action a19 { doc /* record the disposition in the Audit Event Ledger @S833 */ }
            perform action a20 { doc /* ensure that published performance measures identify data sources, calculation versions, confidence limits, and known exclusions @S861 */ }
            perform action a21 { doc /* train operational users on data quality responsibilities, privacy expectations, and the correct interpretation of audit records @S876 */ }
            perform action a22 { doc /* monitor defect trends, data quality, access changes, and user adoption @S910 */ }
            perform action a23 { doc /* is accountable for data quality rules, retention policy, access controls, and permitted operational use of shared data @S970 */ }
        }
        part decisionSupportFunctions : DecisionSupportFunctions;
        part deicingCoordinator : DeicingCoordinator {
            perform action a0 { doc /* represent local airport, tower, ramp, handling, and winter operations considerations @S040 */ }
            perform action a1 { doc /* provides pre-tactical and tactical advice @S092 */ }
            perform action a2 { doc /* sends the Deicing Pad Queue Card @S294 */ }
            perform action a3 { doc /* maintains the active pad configuration @S375 */ }
            perform action a4 { doc /* marks the treatment as expired @S390 */ }
            perform action a5 { doc /* returns the aircraft to the appropriate queue state @S390 */ }
            perform action a6 { doc /* receive seasonal refresher training @S875 */ }
            perform action a7 { doc /* confirm deicing constraints that affect achievable departure throughput @S969 */ }
        }
        part deicingInterfacePoint : DeicingInterfacePoint {
            perform action a0 { doc /* exposes whether a flight still requires treatment, is waiting for pad access, is under treatment, or has been released for taxi @S295 */ }
        }
        part deicingProviders : DeicingProviders;
        part delayAbsorptionIndicator : DelayAbsorptionIndicator {
            perform action a0 { doc /* report minutes absorbed at origin, minutes remaining in the arrival stream, and minutes transferred to surface queues @S841 */ }
        }
        part demandPredictionService : DemandPredictionService {
            perform action a0 { doc /* estimates expected demand @S013 */ }
            perform action a1 { doc /* support planning and collaborative assessment @S031 */ }
            perform action a2 { doc /* converts the normalized schedule into expected arrival and departure demand by time band, runway direction, terminal area, and major traffic flow @S053 */ }
            perform action a3 { doc /* generates the demand forecast @S101 */ }
            perform action a4 { doc /* receives filed flight information @S103 */ }
            perform action a5 { doc /* compares it with the current operating schedule @S103 */ }
            perform action a6 { doc /* estimate arrival and departure loads by planning interval @S105 */ }
            perform action a7 { doc /* uses current airline intents to refine departure demand, arrival demand, and recovery demand by time band @S131 */ }
            perform action a8 { doc /* refresh stand demand forecasts @S216 */ }
            perform action a9 { doc /* estimates demand pressure over the next planning horizon @S251 */ }
            perform action a10 { doc /* marks flights whose proposed Target Off Block Time values are likely to cause runway or sector imbalance @S251 */ }
            perform action a11 { doc /* estimates the departure demand profile by stand, apron area, runway, and departure fix @S350 */ }
            perform action a12 { doc /* shows that inbound demand will exceed the Airport Acceptance Rate @S395 */ }
            perform action a13 { doc /* continuously updates short-term traffic forecasts @S430 */ }
            perform action a14 { doc /* compares amended Flight Intent Message data with the Airport Capacity Plan and the current Airport Acceptance Rate @S493 */ }
            perform action a15 { doc /* show whether a diversion can be absorbed without creating unsafe demand peaks @S493 */ }
            perform action a16 { doc /* treats the turnaround milestone as uncertain @S571 */ }
            perform action a17 { doc /* recalculates short-term demand against the constrained capacity @S701 */ }
            perform action a18 { doc /* combines connection-risk indicators with aircraft readiness, scheduled bank structure, and forecast arrival variability @S743 */ }
            perform action a19 { doc /* estimate the sensitivity of selected departures @S743 */ }
            perform action a20 { doc /* discounts the associated connection benefit @S754 */ }
            perform action a21 { doc /* reject data that lacks a trusted timestamp @S825 */ }
            perform action a22 { doc /* predicted unconstrained demand @S840 */ }
            perform action a23 { doc /* create more stable demand pictures across longer planning horizons @S941 */ }
            perform action a24 { doc /* provide planning evidence @S973 */ }
        }
        part departureMeteringService : DepartureMeteringService {
            perform action a0 { doc /* support the transition from regional planning decisions to executable airport and tower actions @S017 */ }
            perform action a1 { doc /* support tactical airport and regional coordination @S032 */ }
            perform action a2 { doc /* estimates provisional Target Off Block Time sensitivity @S069 */ }
            perform action a3 { doc /* presents proposed departure opportunities and associated Calculated Takeoff Time values @S242 */ }
            perform action a4 { doc /* aligns each Target Off Block Time with the applicable Calculated Takeoff Time @S278 */ }
            perform action a5 { doc /* absorb a small ground handling variation @S315 */ }
            perform action a6 { doc /* uses the current capacity assumptions @S335 */ }
            perform action a7 { doc /* adjust departure release guidance @S335 */ }
            perform action a8 { doc /* preserving previously coordinated Calculated Takeoff Time values @S335 */ }
            perform action a9 { doc /* deciding where delay is best absorbed before aircraft begin taxi @S347 */ }
            perform action a10 { doc /* converts runway demand into controlled stand delay @S348 */ }
            perform action a11 { doc /* derives a feasible Target Off Block Time @S352 */ }
            perform action a12 { doc /* withholds further push clearances @S379 */ }
            perform action a13 { doc /* sends revised departure metering advisories @S426 */ }
            perform action a14 { doc /* translates runway metering limits into candidate pushback spacing @S456 */ }
            perform action a15 { doc /* sequences recovered departures @S483 */ }
            perform action a16 { doc /* applies exception status @S534 */ }
            perform action a17 { doc /* incorporates remote stand constraints @S553 */ }
            perform action a18 { doc /* estimating whether a Target Off Block Time remains achievable @S553 */ }
            perform action a19 { doc /* limited departure metering adjustment @S601 */ }
            perform action a20 { doc /* receives only the feasibility result and timing boundary @S626 */ }
            perform action a21 { doc /* suppresses release recommendations for flights whose assigned stand is not marked ready or whose access route is blocked by an unresolved apron condition @S656 */ }
            perform action a22 { doc /* recalculates metering advisories @S686 */ }
            perform action a23 { doc /* prevents the swap from creating a new demand peak at a departure fix @S686 */ }
            perform action a24 { doc /* updates metering rates @S699 */ }
            perform action a25 { doc /* provides revised inputs to the Slot Allocation Engine @S699 */ }
            perform action a26 { doc /* recommend a minor hold, release, or resequencing action @S747 */ }
            perform action a27 { doc /* reject data that lacks a trusted timestamp @S825 */ }
            perform action a28 { doc /* weight departure sequencing decisions @S851 */ }
            exhibit state modes {
                state s0 { doc /* monitoring mode @S728 */ }
            }
        }
        part designatedMilitaryCoordinationFunction : DesignatedMilitaryCoordinationFunction;
        part digitalBriefingRoom : DigitalBriefingRoom {
            perform action a0 { doc /* support planning and collaborative assessment @S031 */ }
            perform action a1 { doc /* displays the emerging Airport Capacity Plan @S071 */ }
            perform action a2 { doc /* records unresolved assumptions in the Collaborative Decision Log @S071 */ }
            perform action a3 { doc /* provides a common venue @S345 */ }
            perform action a4 { doc /* records the diversion rationale, priority classification, resource commitment, and agreed recovery target in the Collaborative Decision Log @S506 */ }
        }
        part domesticAirports : DomesticAirports;
        part doorCycleTime : DoorCycleTime;
        part downstreamServices : DownstreamServices;
        part drivers : Drivers;
        part eastApronSensor : EastApronSensor {
            perform action a0 { doc /* provide additional indicators of emerging capacity loss and operational imbalance @S019 */ }
            perform action a1 { doc /* detecting aircraft movement @S282 */ }
            perform action a2 { doc /* improve queue accuracy @S282 */ }
            perform action a3 { doc /* provide supporting movement evidence for the reopened area @S474 */ }
            perform action a4 { doc /* reports stand occupancy transitions, pushback lane blockage durations, and sensor confidence values @S578 */ }
            perform action a5 { doc /* provide supporting surveillance cues @S645 */ }
            perform action a6 { doc /* support independent checks of queue length @S845 */ }
        }
        part effectiveTime : EffectiveTime;
        part emergencyResponseCoordinator : EmergencyResponseCoordinator {
            perform action a0 { doc /* participate @S041 */ }
            perform action a1 { doc /* confirms rescue, medical, and airport safety readiness with the Airport Duty Manager @S499 */ }
            perform action a2 { doc /* participate in recurrent training @S874 */ }
            perform action a3 { doc /* require protective operating measures @S968 */ }
        }
        part equipmentUnserviceability : EquipmentUnserviceability;
        part equityConcerns : EquityConcerns;
        part exercise : Exercise;
        part expectedDuration : ExpectedDuration;
        part findingsFromTheReview : FindingsFromTheReview;
        part firstIncrement : FirstIncrement {
            perform action a0 { doc /* establish the core operational baseline @S889 */ }
        }
        part flight : Flight {
            exhibit state modes {
                state s0 { doc /* customs hold @S570 */ }
                state s1 { doc /* exempted from compliance monitoring @S265 */ }
                state s2 { doc /* frozen @S265 */ }
                state s3 { doc /* proposed @S265 */ }
                state s4 { doc /* under negotiation @S265 */ }
            }
        }
        part flightDataExchange : FlightDataExchange {
            perform action a0 { doc /* provide the data feeds @S018 */ }
            perform action a1 { doc /* provide managed integration points with external systems @S033 */ }
            perform action a2 { doc /* normalizes flight identifiers, aircraft types, routing fields, and planned operating times @S052 */ }
            perform action a3 { doc /* provides current flight intent data @S278 */ }
            perform action a4 { doc /* distributes only the approved operational result to downstream services @S638 */ }
            perform action a5 { doc /* publishes revised Flight Intent Message content @S684 */ }
            perform action a6 { doc /* validate Flight Intent Message content @S827 */ }
            perform action a7 { doc /* captured realized movement times @S840 */ }
            perform action a8 { doc /* accept richer intent data @S940 */ }
        }
        part flightIntentMessage : FlightIntentMessage;
        part flightIntentMessageStatus : FlightIntentMessageStatus;
        part freshnessIndicator : FreshnessIndicator {
            exhibit state modes {
                state s0 { doc /* aging @S823 */ }
                state s1 { doc /* current @S823 */ }
                state s2 { doc /* stale @S823 */ }
                state s3 { doc /* unavailable @S823 */ }
            }
        }
        part fuelingProviders : FuelingProviders;
        part futureReleases : FutureReleases {
            exhibit state modes {
                state s0 { doc /* shadow mode @S959 */ }
            }
        }
        part gateConflictDetector : GateConflictDetector {
            perform action a0 { doc /* provide additional indicators of emerging capacity loss and operational imbalance @S019 */ }
            perform action a1 { doc /* alerts the Ramp Control Lead @S210 */ }
            perform action a2 { doc /* warns when continued stand holding would block an inbound allocation or create a conflict with a planned equipment move @S364 */ }
            perform action a3 { doc /* produces the Gate Reopening Memo @S386 */ }
            perform action a4 { doc /* highlights stand conflicts @S439 */ }
            perform action a5 { doc /* checks whether the congestion can be relieved by resequencing adjacent stands @S459 */ }
            perform action a6 { doc /* compares planned arrivals, planned departures, assigned gates, towing availability, and published stand status @S468 */ }
            perform action a7 { doc /* identify conflicts that would otherwise be hidden inside local spreadsheets @S468 */ }
            perform action a8 { doc /* flags conflicts between diversion parking requirements and planned turnarounds @S509 */ }
            perform action a9 { doc /* identifies cases where an aircraft assigned to a contact gate would cause less overall delay @S558 */ }
            perform action a10 { doc /* distinguish a true gate conflict from a temporary clearance delay @S582 */ }
            perform action a11 { doc /* checks readiness status against aircraft allocation, towing activity, and adjacent stand occupancy @S657 */ }
            perform action a12 { doc /* identify conflicts before ground movement begins @S657 */ }
        }
        part groundDelayProgram : GroundDelayProgram {
            perform action a0 { doc /* meters selected arrivals @S398 */ }
        }
        part groundHandlingDispatcher : GroundHandlingDispatcher {
            perform action a0 { doc /* represent local airport, tower, ramp, handling, and winter operations considerations @S040 */ }
            perform action a1 { doc /* confirms whether planned handling teams and equipment coverage are sufficient @S064 */ }
            perform action a2 { doc /* confirms that handling resource assumptions are current in the Handling Resource Planner @S091 */ }
            perform action a3 { doc /* escalates material deviations through the Airport Duty Manager @S091 */ }
            perform action a4 { doc /* sends the Crew Bus Delay Slip @S140 */ }
            perform action a5 { doc /* updating servicing completion, baggage readiness, staffing limitation, and equipment availability milestones @S158 */ }
            perform action a6 { doc /* updates handling milestones @S261 */ }
            perform action a7 { doc /* updates boarding, loading, door closure, and tow readiness milestones @S292 */ }
            perform action a8 { doc /* updates the Handling Resource Planner with expected service completion times @S302 */ }
            perform action a9 { doc /* updates remaining fluid inventory and truck serviceability @S383 */ }
            perform action a10 { doc /* compare planned off-block demand with available servicing capacity at affected stands @S438 */ }
            perform action a11 { doc /* confirm stand access, towing resources, refueling constraints, and unloading capacity through the Handling Resource Planner @S508 */ }
            perform action a12 { doc /* uses the tag list to confirm which flights require baggage reconciliation @S519 */ }
            perform action a13 { doc /* sends the Towbar Shortage Report @S523 */ }
            perform action a14 { doc /* verifies that bus assignments do not conflict with baggage, catering, fueling, or crew transport movements @S550 */ }
            perform action a15 { doc /* assigns qualified personnel to perform apron sweeps @S643 */ }
            perform action a16 { doc /* updates the Handling Resource Planner @S653 */ }
            perform action a17 { doc /* trained on the Handling Resource Planner @S869 */ }
            perform action a18 { doc /* maintaining accurate surface and handling status @S966 */ }
        }
        part groundHandlingPersonnel : GroundHandlingPersonnel {
            perform action a0 { doc /* confirming that resource constraints are represented accurately @S869 */ }
        }
        part groundServiceProviders : GroundServiceProviders;
        part handlerException : HandlerException;
        part handlingResourcePlanner : HandlingResourcePlanner {
            perform action a0 { doc /* compares the demand curve with available ground resources @S065 */ }
            perform action a1 { doc /* flags time bands where aircraft turn performance is likely to reduce stand availability @S065 */ }
            perform action a2 { doc /* correlated ground handling impacts with stand occupancy, baggage readiness, catering status, and boarding progress @S141 */ }
            perform action a3 { doc /* provides the shared planning basis for baggage, catering, cleaning, boarding support, and towing resources @S212 */ }
            perform action a4 { doc /* maintains the operational view of dispatch teams, tow teams, ramp buses, belt loaders, high loaders, stairs, ground power units, air start units, and potable water equipment @S303 */ }
            perform action a5 { doc /* uses the Stand Tow Request Form to reserve towing capacity @S304 */ }
            perform action a6 { doc /* test whether the requested movement can be completed before the proposed Target Off Block Time @S304 */ }
            perform action a7 { doc /* compares fluid inventory with scheduled deicing demand @S384 */ }
            perform action a8 { doc /* warns when a planned bank cannot be supported without resequencing @S384 */ }
            perform action a9 { doc /* evaluates whether additional ground handling resources can remove the constraint faster than a flow management measure would absorb it @S460 */ }
            perform action a10 { doc /* estimates whether the proposed turnaround can be recovered @S477 */ }
            perform action a11 { doc /* assigns a severity level to the handler exception @S522 */ }
            perform action a12 { doc /* suppresses duplicate updates @S522 */ }
            perform action a13 { doc /* produces the Remote Stand Shuttle Count @S547 */ }
            perform action a14 { doc /* validate resource quantities, task timing, and allocation identifiers against active operational reference data @S830 */ }
        }
        part harborEastAirport : HarborEastAirport;
        part humanFactorsSafeguards : HumanFactorsSafeguards;
        part identityAccessService : IdentityAccessService {
            perform action a0 { doc /* provide governance, security, traceability, and performance measurement capabilities @S034 */ }
            perform action a1 { doc /* manages authenticated system account @S126 */ }
            perform action a2 { doc /* controls access to the Airport CDM Portal @S152 */ }
            perform action a3 { doc /* restricts entry of duty desk confirmations to authorized airport operations staff @S194 */ }
            perform action a4 { doc /* records each transaction in the Audit Event Ledger @S194 */ }
            perform action a5 { doc /* ensures that only users with the assigned operational role can approve frozen-time changes, manual exemptions, or retrospective corrections @S272 */ }
            perform action a6 { doc /* retain traceability of who viewed, changed, or approved diversion decisions @S515 */ }
            perform action a7 { doc /* enforces these visibility rules for Airport CDM Portal, Digital Briefing Room, and application programming interfaces @S635 */ }
            perform action a8 { doc /* restricts readiness confirmation privileges to approved ramp, handling, and airport operations roles @S650 */ }
            perform action a9 { doc /* support rapid suspension of accounts @S781 */ }
            perform action a10 { doc /* records the authorizing incident reference and expiry time @S783 */ }
            perform action a11 { doc /* support traceability, least-privilege access, and after-action accountability @S981 */ }
        }
        part incidentRecord : IncidentRecord {
            perform action a0 { doc /* captures the initial symptom, affected components, operational state, timeline, mitigation actions, data corrections, and supervisor decisions @S923 */ }
            perform action a1 { doc /* reference the Audit Event Ledger @S924 */ }
        }
        part informationServices : InformationServices;
        part initialPilot : InitialPilot;
        part initialTraining : InitialTraining;
        part integratedTacticalManagementPosition : IntegratedTacticalManagementPosition {
            perform action a0 { doc /* real-time coordination of Meridian departure flow, arrival flow, airport capacity, and airspace constraints @S419 */ }
            perform action a1 { doc /* presents a combined tactical view @S420 */ }
            perform action a2 { doc /* applies weather-driven capacity values @S434 */ }
            exhibit state modes {
                state s0 { doc /* read-only mode @S429 */ }
            }
        }
        part interfacePart : Interface;
        part lakesideRegionalAirport : LakesideRegionalAirport;
        part loadingPositions : LoadingPositions;
        part localTool : LocalTool {
            perform action a0 { doc /* remain the authoritative source @S905 */ }
            exhibit state modes {
                state s0 { doc /* integrated through an approved interface @S903 */ }
                state s1 { doc /* replaced by a Regional Flow Platform function @S903 */ }
                state s2 { doc /* retained for read-only reference @S903 */ }
                state s3 { doc /* retired @S903 */ }
            }
        }
        part localUsers : LocalUsers {
            perform action a0 { doc /* enter operational decisions through the Airport CDM Portal @S907 */ }
            perform action a1 { doc /* avoid reintroducing uncontrolled parallel records @S907 */ }
        }
        part maximumLoad : MaximumLoad;
        part meridianInternationalAirport : MeridianInternationalAirport;
        part meridianRegion : MeridianRegion;
        part meridianRegionalATFMACDM : MeridianRegionalATFMACDM {
            exhibit state modes {
                state s0 { doc /* Adverse Weather @S415 */ }
                state s1 { doc /* Adverse Weather Mode @S435 */ }
                state s2 { doc /* Capacity Reduction State @S416,S435,S675 */ }
                state s3 { doc /* Contingency Fallback State @S435 */ }
                state s4 { doc /* Normal Operations @S397,S435 */ }
                state s5 { doc /* Recovery Phase @S435,S489 */ }
                state s6 { doc /* Slot Compliance State @S441 */ }
            }
        }
        part meridianRegionalATFMACDMSystem : MeridianRegionalATFMACDMSystem {
            exhibit state modes {
                state s0 { doc /* Adverse Weather Mode @S162,S916 */ }
                state s1 { doc /* Capacity Reduction State @S162,S916 */ }
                state s2 { doc /* Contingency Fallback State @S172 */ }
                state s3 { doc /* Normal Operations @S162 */ }
                state s4 { doc /* Recovery Phase @S162,S916,S951 */ }
                state s5 { doc /* Winter @S969 */ }
            }
        }
        part meridianRegionalAirTrafficFlowManagementAndAirportCollaborativeDecisionMakingSystem : MeridianRegionalAirTrafficFlowManagementAndAirportCollaborativeDecisionMakingSystem {
            perform action a0 { doc /* convert operational events into repeatable indicators @S838 */ }
            exhibit state modes {
                state s0 { doc /* Slot Compliance State @S850 */ }
            }
        }
        part meridianRegionalCapability : MeridianRegionalCapability;
        part meteorologyBriefingOfficer : MeteorologyBriefingOfficer {
            perform action a0 { doc /* participate @S041 */ }
            perform action a1 { doc /* provides the morning weather outlook @S056 */ }
            perform action a2 { doc /* produces the Storm Cell Snapshot @S085 */ }
            perform action a3 { doc /* briefs forecast confidence, timing risk, and expected operational impact in the Digital Briefing Room @S086 */ }
            perform action a4 { doc /* states the trigger conditions @S087 */ }
            perform action a5 { doc /* reviews degraded weather inputs @S112 */ }
            perform action a6 { doc /* attach weather interpretation, forecast confidence, and expected timing of operational impacts @S163 */ }
            perform action a7 { doc /* confirms the trigger conditions in the Digital Briefing Room @S372 */ }
            perform action a8 { doc /* verifies weather impacts shown from the Weather Ingest Gateway @S434 */ }
            perform action a9 { doc /* maintains rapidly updated forecast information @S512 */ }
            perform action a10 { doc /* own operational weather classification inputs @S819 */ }
            perform action a11 { doc /* support interpretation of emissions results @S858 */ }
            perform action a12 { doc /* identifying periods when weather routing or convective avoidance dominated fuel performance @S858 */ }
            perform action a13 { doc /* explain weather uncertainty in operational terms @S873 */ }
            perform action a14 { doc /* verify that the Weather Ingest Gateway supports the assumptions used during briefings @S873 */ }
            perform action a15 { doc /* timely disclosure of weather, sector, and airspace constraints @S967 */ }
        }
        part migrationPlan : MigrationPlan {
            perform action a0 { doc /* classify each local tool @S903 */ }
        }
        part militaryAirspaceLiaison : MilitaryAirspaceLiaison {
            perform action a0 { doc /* close coordination @S006 */ }
            perform action a1 { doc /* participate @S041 */ }
            perform action a2 { doc /* confirms whether shared airspace assumptions remain valid for the morning @S059 */ }
            perform action a3 { doc /* identifies any conditional availability that must be treated as uncertain @S059 */ }
            perform action a4 { doc /* confirms military airspace availability assumptions @S093 */ }
            perform action a5 { doc /* alerts the Regional Flow Manager @S093 */ }
            perform action a6 { doc /* confirming the activation window, affected volume, controlling authority, and any published contingency conditions @S325 */ }
            perform action a7 { doc /* sends the Temporary Restriction Notice @S325 */ }
            perform action a8 { doc /* confirm the active interpretation of the restriction @S345 */ }
            perform action a9 { doc /* mark an airspace release or closure assumption for review @S433 */ }
            perform action a10 { doc /* states whether flexible use airspace can be adjusted @S511 */ }
            perform action a11 { doc /* confirms whether conditional route availability changes the effective capacity @S609 */ }
            perform action a12 { doc /* timely disclosure of weather, sector, and airspace constraints @S967 */ }
        }
        part mobilityAssistanceRequirements : MobilityAssistanceRequirements;
        part namedOperationalUser : NamedOperationalUser {
            perform action a0 { doc /* authenticate with an individually assigned identity @S764 */ }
        }
        part networkOperationsLiaison : NetworkOperationsLiaison {
            perform action a0 { doc /* align airline intentions, schedule constraints, and slot management decisions with the shared plan @S039 */ }
            perform action a1 { doc /* coordinates with adjacent network units @S083 */ }
            perform action a2 { doc /* confirms that regional measures remain compatible with upstream and downstream flow constraints @S083 */ }
            perform action a3 { doc /* records external coordination outcomes in the Collaborative Decision Log @S084 */ }
            perform action a4 { doc /* coordinates with external network positions @S339 */ }
            perform action a5 { doc /* coordinates with affected airline control centers @S413 */ }
            perform action a6 { doc /* reviews whether protecting a connecting passenger group supports wider network recovery @S480 */ }
            perform action a7 { doc /* coordinates downstream network effects @S510 */ }
            perform action a8 { doc /* monitors aggregate displacement from approved substitutions @S674 */ }
            perform action a9 { doc /* coordinate regional constraints, sector load conditions, and network measures @S871 */ }
            perform action a10 { doc /* retain operational command authority @S917 */ }
            perform action a11 { doc /* negotiate measures before local capacity is saturated @S938 */ }
        }
        part northRunwayMeter : NorthRunwayMeter {
            perform action a0 { doc /* provide additional indicators of emerging capacity loss and operational imbalance @S019 */ }
            perform action a1 { doc /* receive runway-specific capacity values @S114 */ }
            perform action a2 { doc /* maintain separate queues @S280 */ }
            perform action a3 { doc /* maintain independent queue counts @S359 */ }
            perform action a4 { doc /* reduces the departure release rate @S454 */ }
            perform action a5 { doc /* support independent checks of queue length @S845 */ }
        }
        part northValleyAirport : NorthValleyAirport;
        part operationalConstraint : OperationalConstraint;
        part operationalOwner : OperationalOwner {
            perform action a0 { doc /* verifies that its essential decisions, timing assumptions, and audit needs are supported in the target process @S904 */ }
        }
        part operationalProcesses : OperationalProcesses;
        part operationalSupervisors : OperationalSupervisors;
        part operationalUsers : OperationalUsers;
        part padQueueControls : PadQueueControls {
            perform action a0 { doc /* assign aircraft to a deicing lane @S376 */ }
        }
        part participatingAirport : ParticipatingAirport {
            perform action a0 { doc /* remains responsible for its local safety management, aerodrome certification obligations, and operational command authority @S027 */ }
        }
        part participatingAirportNetwork : ParticipatingAirportNetwork;
        part participatingOrganization : ParticipatingOrganization {
            perform action a0 { doc /* treat the operating picture as a shared operational asset @S960 */ }
        }
        part participatingRoles : ParticipatingRoles;
        part passengerBusConstraints : PassengerBusConstraints;
        part passengerConnectionSensitivity : PassengerConnectionSensitivity;
        part passengerTransportProviders : PassengerTransportProviders;
        part performanceAnalyticsWarehouse : PerformanceAnalyticsWarehouse {
            perform action a0 { doc /* provide governance, security, traceability, and performance measurement capabilities @S034 */ }
            perform action a1 { doc /* retains the baseline inputs, capacity declarations, and approval timestamps @S074 */ }
            perform action a2 { doc /* reconstruct the decision basis after operations @S123 */ }
            perform action a3 { doc /* compares submitted intents, issued constraints, actual off-block times, and achieved arrival outcomes @S148 */ }
            perform action a4 { doc /* compare planned outcomes with actual off-block, takeoff, landing, and stand events @S173 */ }
            perform action a5 { doc /* compares recorded duty coordination events with actual movement data @S197 */ }
            perform action a6 { doc /* compares proposed opportunities, actual movement times, exemption usage, and operator-level delay equity @S248 */ }
            perform action a7 { doc /* uses frozen targets, actual milestone timestamps, and audit records @S274 */ }
            perform action a8 { doc /* measure compliance, delay attribution, negotiation effectiveness, and rule quality @S274 */ }
            perform action a9 { doc /* compares predicted and actual handling constraints @S322 */ }
            perform action a10 { doc /* identify chronic equipment shortages by stand group @S322 */ }
            perform action a11 { doc /* compares planned capacity, issued alerts, operator acknowledgements, and realized delay @S346 */ }
            perform action a12 { doc /* determine whether the restriction handling process supported timely and consistent decisions @S346 */ }
            perform action a13 { doc /* compares planned stand absorption, actual off block performance, and runway queue length @S370 */ }
            perform action a14 { doc /* verify that the agreed thresholds were not exceeded @S370 */ }
            perform action a15 { doc /* compares planned treatment throughput, actual pad occupancy, and departure compliance @S394 */ }
            perform action a16 { doc /* compare predicted holding, actual airborne delay, diversion outcomes, and achieved landing rates @S418 */ }
            perform action a17 { doc /* measures whether recovered gate assignments reduced missed connections @S489 */ }
            perform action a18 { doc /* compares actual handling times, sector load, connection outcomes, and regulation changes against the recorded diversion plan @S514 */ }
            perform action a19 { doc /* compares escalated exceptions with actual off-block performance @S538 */ }
            perform action a20 { doc /* tune severity thresholds @S538 */ }
            perform action a21 { doc /* reduce nuisance alerts over time @S538 */ }
            perform action a22 { doc /* retains remote stand timing measures @S565 */ }
            perform action a23 { doc /* compares planned clearance assumptions with actual border release timing and apron availability @S590 */ }
            perform action a24 { doc /* compares predicted sector pressure, actual airborne delay, and airport departure compliance @S616 */ }
            perform action a25 { doc /* tune Demand Prediction Service and Capacity Assessment Module @S616 */ }
            perform action a26 { doc /* analyze anonymized patterns of legality constraints and recovery selections @S639 */ }
            perform action a27 { doc /* uses aggregated readiness and contamination timing data @S665 */ }
            perform action a28 { doc /* identify recurring debris locations, inefficient sweep patterns, and opportunities for preventive maintenance @S665 */ }
            perform action a29 { doc /* uses completed infrastructure events to measure delay attribution, capacity recovery time, and the accuracy of initial duration estimates @S712 */ }
            perform action a30 { doc /* receives the outage timeline, manual intervention record, and recovery milestones @S737 */ }
            perform action a31 { doc /* compares later delay outcomes with the logged rationale @S760 */ }
            perform action a32 { doc /* aggregate compliance outcomes @S804 */ }
            perform action a33 { doc /* retain data quality measures @S836 */ }
            perform action a34 { doc /* calculate delay absorption @S839 */ }
            perform action a35 { doc /* apply approved fuel burn and emissions factors @S856 */ }
        }
        part pilotAirportSelection : PilotAirportSelection;
        part postExerciseReviews : PostExerciseReviews {
            perform action a0 { doc /* improve procedures @S887 */ }
            perform action a1 { doc /* refine training materials @S887 */ }
            perform action a2 { doc /* confirm that human performance concerns are assigned to accountable owners @S887 */ }
        }
        part postOperationsReport : PostOperationsReport {
            perform action a0 { doc /* compare planned performance with actual outcomes @S074 */ }
            perform action a1 { doc /* present regional benefits alongside operational trade-offs @S862 */ }
        }
        part postOperationsReportOutputs : PostOperationsReportOutputs;
        part preferredRoute : PreferredRoute;
        part primaryInternationalHub : PrimaryInternationalHub;
        part rampControlLead : RampControlLead {
            perform action a0 { doc /* represent local airport, tower, ramp, handling, and winter operations considerations @S040 */ }
            perform action a1 { doc /* reviews early stand readiness @S063 */ }
            perform action a2 { doc /* maintains the Ramp Movement Board in a state that supports reliable departure metering @S090 */ }
            perform action a3 { doc /* uses the Ramp Movement Board to identify whether the proposed recovery action can be supported without creating surface congestion @S142 */ }
            perform action a4 { doc /* maintaining stand release readiness, apron movement conflicts, tug availability, and local pushback sequencing inputs in the portal @S159 */ }
            perform action a5 { doc /* reviews apron movement constraints with the duty desk @S184 */ }
            perform action a6 { doc /* maintains the operational sequence for pushbacks, stand exits, stand entries, and towing movements @S200 */ }
            perform action a7 { doc /* release a pushback @S202 */ }
            perform action a8 { doc /* reconciling sensor data with visual and operational reports @S205 */ }
            perform action a9 { doc /* assigns priority to towing movements @S206 */ }
            perform action a10 { doc /* sends the Stand Tow Request Form @S208 */ }
            perform action a11 { doc /* coordinates with the Ground Handling Dispatcher @S211 */ }
            perform action a12 { doc /* reviews Handling Resource Planner constraints @S213 */ }
            perform action a13 { doc /* committing to a pushback sequence @S213 */ }
            perform action a14 { doc /* escalates the condition to the Tower Supervisor and Airport Duty Manager @S218 */ }
            perform action a15 { doc /* increases spacing between pushbacks and towing movements @S219 */ }
            perform action a16 { doc /* identify apron constraints through the Ramp Movement Board @S244 */ }
            perform action a17 { doc /* assesses whether the proposed off-block pattern is compatible with apron access, stand conflicts, and local movement restrictions @S262 */ }
            perform action a18 { doc /* coordinates pushback release priorities against stand conflicts, taxi lane constraints, and the runway demand @S283 */ }
            perform action a19 { doc /* reviews the proposed windows against apron congestion, towing activity, and aircraft readiness @S357 */ }
            perform action a20 { doc /* accepting them for local execution @S357 */ }
            perform action a21 { doc /* uses the queue card to verify pad entry order @S378 */ }
            perform action a22 { doc /* authorizing a movement from the staging area @S378 */ }
            perform action a23 { doc /* coordinate every pad release with the Tower Supervisor @S387 */ }
            perform action a24 { doc /* verifies whether the condition blocks a single movement, a stand group, or a wider apron route @S446 */ }
            perform action a25 { doc /* coordinates stand reopening with the Ground Handling Dispatcher @S473 */ }
            perform action a26 { doc /* confirm stand access, towing resources, refueling constraints, and unloading capacity through the Handling Resource Planner @S508 */ }
            perform action a27 { doc /* confirms that each planned remote stand has an assigned aircraft route, safe passenger transfer path, and defined contingency for blocked apron movement @S545 */ }
            perform action a28 { doc /* uses the Towbar Shortage Report to determine whether remote stand aircraft can be repositioned @S556 */ }
            perform action a29 { doc /* defines the sweep areas by stand, taxilane, service road interface, and equipment staging zone @S642 */ }
            perform action a30 { doc /* sends the Apron Sweep Completion Note @S647 */ }
            perform action a31 { doc /* reviews unresolved hazards against active turnaround demand @S654 */ }
            perform action a32 { doc /* allowing pushback planning to continue for the affected stand @S654 */ }
            perform action a33 { doc /* confirms that the revised sequence remains compatible with stand occupancy, pushback spacing, and tug availability @S677 */ }
            perform action a34 { doc /* uses the Ramp Movement Board to determine whether a proposed metering adjustment can be supported @S749 */ }
            perform action a35 { doc /* update ramp movement status through the Ramp Movement Board @S770 */ }
            perform action a36 { doc /* own ramp movement status data @S818 */ }
            perform action a37 { doc /* trained to use the Ramp Movement Board @S867 */ }
            perform action a38 { doc /* retain operational command authority @S917 */ }
            perform action a39 { doc /* maintaining accurate surface and handling status @S966 */ }
        }
        part rampMovementBoard : RampMovementBoard {
            perform action a0 { doc /* support the transition from regional planning decisions to executable airport and tower actions @S017 */ }
            perform action a1 { doc /* support tactical airport and regional coordination @S032 */ }
            perform action a2 { doc /* is the primary working view for planned apron movements, active conflicts, towing tasks, and occupied stand intervals @S203 */ }
            perform action a3 { doc /* records a material change in planned off-block timing @S216 */ }
            perform action a4 { doc /* maintains milestone timestamps for stand readiness, boarding completion, doors closed, start approval readiness, taxi start, and other locally configured departure events @S255 */ }
            perform action a5 { doc /* shows occupied stands, blocked service roads, and pending pushback areas @S311 */ }
            perform action a6 { doc /* produces the Fuel Truck Hold Advice @S361 */ }
            perform action a7 { doc /* displays each aircraft as pending push, taxi to pad, in treatment, awaiting release, or returning to stand @S377 */ }
            perform action a8 { doc /* refresh the apron movement layer @S427 */ }
            perform action a9 { doc /* shows conflicting pushbacks, blocked lead-in lines, saturated holding points, or insufficient room for safe wingtip clearance @S458 */ }
            perform action a10 { doc /* maintains the operational view of occupied, blocked, cleaning, boarding, and tow-ready positions @S469 */ }
            perform action a11 { doc /* displays the resulting constraint as a stand-level exception with a time band @S525 */ }
            perform action a12 { doc /* displays remote stand occupancy, expected towing actions, and bus service readiness @S551 */ }
            perform action a13 { doc /* presents apron sensor events as operational evidence @S581 */ }
            perform action a14 { doc /* displays stand readiness status @S646 */ }
            perform action a15 { doc /* receives the same operational status @S703 */ }
            perform action a16 { doc /* provide actual movement milestones @S801 */ }
            perform action a17 { doc /* provide surface queue counts @S844 */ }
        }
        part rampPersonnel : RampPersonnel {
            perform action a0 { doc /* use the Ramp Movement Board @S867 */ }
        }
        part rampServiceOrganizations : RampServiceOrganizations;
        part readinessGate1 : ReadinessGate1 {
            perform action a0 { doc /* confirm that governance, security approvals, user role definitions, operating hours, and support escalation paths are documented and accepted by local stakeholders @S894 */ }
        }
        part readinessGate2 : ReadinessGate2 {
            perform action a0 { doc /* confirm that the Flight Data Exchange, Airline Interface Adapter, Surface Surveillance Adapter, and Weather Ingest Gateway can be connected @S895 */ }
        }
        part readinessGate3 : ReadinessGate3 {
            perform action a0 { doc /* confirm that local procedures have been mapped @S896 */ }
        }
        part readinessGate4 : ReadinessGate4 {
            perform action a0 { doc /* confirm that training, shadow operations, contingency procedures, and operational acceptance criteria have been completed @S897 */ }
        }
        part recoveryRecommendations : RecoveryRecommendations;
        part recurrentTraining : RecurrentTraining;
        part regionalExpansion : RegionalExpansion;
        part regionalFlowManagementPersonnel : RegionalFlowManagementPersonnel;
        part regionalFlowManager : RegionalFlowManager {
            perform action a0 { doc /* balancing demand against capacity @S010 */ }
            perform action a1 { doc /* coordinating regional traffic management actions @S010 */ }
            perform action a2 { doc /* balancing demand and capacity at the regional level @S038 */ }
            perform action a3 { doc /* owns the baseline process @S050 */ }
            perform action a4 { doc /* confirms that the planning horizon, cutover time, and review checkpoints are understood by the participating operational roles @S050 */ }
            perform action a5 { doc /* owns the regional operating intent @S077 */ }
            perform action a6 { doc /* confirms that planned demand, declared capacity, and coordination milestones are aligned @S077 */ }
            perform action a7 { doc /* reviews the Airport Capacity Plan, the Ground Delay Program status, and any Tactical Regulation Proposal @S078 */ }
            perform action a8 { doc /* chairs decision checkpoints @S094 */ }
            perform action a9 { doc /* authorizes changes to flow measures @S094 */ }
            perform action a10 { doc /* uses the Common Situation Display to compare forecast demand, assessed capacity, and any active Ground Delay Program effects @S117 */ }
            perform action a11 { doc /* confirms airline recovery priorities @S137 */ }
            perform action a12 { doc /* owns the final operating policy for priority classes @S228 */ }
            perform action a13 { doc /* authorize temporary rule changes @S228 */ }
            perform action a14 { doc /* approved shorter recalculation cycles @S246 */ }
            perform action a15 { doc /* assesses whether the effect is localized to one stream or requires a broader Ground Delay Program @S327 */ }
            perform action a16 { doc /* decides whether to absorb the impact through metering, targeted delay, reroute coordination, or a wider regulation @S343 */ }
            perform action a17 { doc /* confirm the active interpretation of the restriction @S345 */ }
            perform action a18 { doc /* increase stand absorption @S367 */ }
            perform action a19 { doc /* authorizes a controlled transition from Capacity Reduction State toward Recovery Phase @S393 */ }
            perform action a20 { doc /* evaluates regulation options in the Arrival Regulation Console @S396 */ }
            perform action a21 { doc /* uses the restriction notice to bound the arrival regulation timeline @S399 */ }
            perform action a22 { doc /* committing new landing-rate values in the Arrival Regulation Console @S399 */ }
            perform action a23 { doc /* apply a tactical landing-rate reduction for a defined review interval @S410 */ }
            perform action a24 { doc /* approve a staged landing-rate increase @S411 */ }
            perform action a25 { doc /* combine arrival regulation with departure metering @S416 */ }
            perform action a26 { doc /* compare planned demand, measured throughput, and active control measures @S420 */ }
            perform action a27 { doc /* uses these advisories to decide whether the tactical plan should retain normal sequencing, shift to local metering, or support a Tactical Regulation Proposal @S463 */ }
            perform action a28 { doc /* balances passenger connection pressure against network fairness @S479 */ }
            perform action a29 { doc /* uses the Regional Flow Platform to maintain a ranked view of candidate diversions @S492 */ }
            perform action a30 { doc /* shifts from acceptance decisions to recovery coordination @S513 */ }
            perform action a31 { doc /* balancing restored arrival capacity, departure release opportunities, and stand clearance timing @S513 */ }
            perform action a32 { doc /* sees aggregated impact by departure bank, runway stream, and airline group @S532 */ }
            perform action a33 { doc /* considers repeated remote stand transfer delays as an input to tactical capacity assessment @S555 */ }
            perform action a34 { doc /* uses aggregated border delay exposure to decide whether an arrival regulation should be adjusted @S573 */ }
            perform action a35 { doc /* uses the load sheet to confirm whether a departure fix constraint should be represented as an airport departure measure @S598 */ }
            perform action a36 { doc /* see aggregate recovery pressure across operators @S634 */ }
            perform action a37 { doc /* suspend collaborative substitution @S675 */ }
            perform action a38 { doc /* reviews the published constraint @S696 */ }
            perform action a39 { doc /* confirmation @S698 */ }
            perform action a40 { doc /* applies the last verified Airport Capacity Plan @S721 */ }
            perform action a41 { doc /* adjusts it by direct coordination with the Airspace Sector Planner and Meteorology Briefing Officer @S721 */ }
            perform action a42 { doc /* approves any arrival regulation changes through direct coordination @S729 */ }
            perform action a43 { doc /* consider a recovery action credible @S753 */ }
            perform action a44 { doc /* authorize regional traffic management measures @S768 */ }
            perform action a45 { doc /* use the Post Operations Report to identify whether noncompliance resulted @S808 */ }
            perform action a46 { doc /* own flow management policy data @S814 */ }
            perform action a47 { doc /* verify that a Ground Delay Program reduced airborne holding @S842 */ }
            perform action a48 { doc /* receive advanced instruction @S864 */ }
            perform action a49 { doc /* authorizing operational measures in the Regional Flow Platform @S864 */ }
            perform action a50 { doc /* confirms that operational benefits, safety constraints, cyber controls, and stakeholder obligations remain stable @S911 */ }
            perform action a51 { doc /* retain operational command authority @S917 */ }
            perform action a52 { doc /* direct transition to Contingency Fallback State @S926 */ }
            perform action a53 { doc /* see upstream demand pressure earlier @S938 */ }
            perform action a54 { doc /* compare recommendations with actual outcomes @S959 */ }
            perform action a55 { doc /* activate, amend, or terminate regional flow measures @S961 */ }
        }
        part regionalFlowPlatform : RegionalFlowPlatform {
            perform action a0 { doc /* integrate planning, tactical regulation, airport readiness, and post-event analysis @S012 */ }
            perform action a1 { doc /* support rapid development of a Tactical Regulation Proposal @S022 */ }
            perform action a2 { doc /* consistent communication of the resulting Ground Delay Program @S022 */ }
            perform action a3 { doc /* help stakeholders restore scheduled flow @S023 */ }
            perform action a4 { doc /* monitoring Target Off Block Time, Calculated Takeoff Time, and Slot Compliance State performance @S023 */ }
            perform action a5 { doc /* provides a shared coordination layer @S028 */ }
            perform action a6 { doc /* does not replace statutory air traffic control, airport operator control rooms, airline operational control centers, or ground handling dispatch systems @S028 */ }
            perform action a7 { doc /* creates the initial demand picture from published schedules, approved seasonal allocations, overnight schedule changes, and received Flight Intent Message data @S051 */ }
            perform action a8 { doc /* detects a material difference from the published schedule @S104 */ }
            perform action a9 { doc /* reconciles them with airport and airspace constraints @S130 */ }
            perform action a10 { doc /* permits more frequent intent updates @S147 */ }
            perform action a11 { doc /* retaining the previous values needed for audit and performance review @S147 */ }
            perform action a12 { doc /* expose the current regional demand and constraint context to the shared workspace @S164 */ }
            perform action a13 { doc /* receives confirmed capacity impacts through normal system interfaces @S191 */ }
            perform action a14 { doc /* creates the initial Target Off Block Time proposal @S250 */ }
            perform action a15 { doc /* locks the Target Off Block Time @S268 */ }
            perform action a16 { doc /* distinguish an air traffic delay from a local handling delay @S302 */ }
            perform action a17 { doc /* marks a proposed Target Off Block Time as conditional @S314 */ }
            perform action a18 { doc /* assumes that typical service durations remain valid @S318 */ }
            perform action a19 { doc /* does not release every aircraft as soon as it becomes ready @S320 */ }
            perform action a20 { doc /* records each airspace alert, acknowledgement, and downstream decision in the Audit Event Ledger @S333 */ }
            perform action a21 { doc /* normalizes each Flight Intent Message against the current Airport Capacity Plan @S349 */ }
            perform action a22 { doc /* synchronizes the tactical display with the Time Synchronization Service @S422 */ }
            perform action a23 { doc /* correlates surface equipment conditions with flight intent, stand assignment, and runway plan data @S444 */ }
            perform action a24 { doc /* recommending any change to the active tactical plan @S444 */ }
            perform action a25 { doc /* proposes a broader departure delay @S459 */ }
            perform action a26 { doc /* prioritizes removal of surface holds that constrain multiple rotations @S465 */ }
            perform action a27 { doc /* optimizing isolated punctuality impacts @S465 */ }
            perform action a28 { doc /* treats these conditions as operational exceptions @S517 */ }
            perform action a29 { doc /* filtered, grouped, and escalated @S517 */ }
            perform action a30 { doc /* aligns these sector values with scheduled movements and predicted readiness @S593 */ }
            perform action a31 { doc /* represents crew legality as operational constraints @S617 */ }
            perform action a32 { doc /* treats the received legality status as an operator assertion @S621 */ }
            perform action a33 { doc /* does not independently calculate labor agreement compliance @S621 */ }
            perform action a34 { doc /* records each event as an operational constraint @S691 */ }
            perform action a35 { doc /* maintains the infrastructure event as a controlling assumption @S708 */ }
            perform action a36 { doc /* returns the affected resource to Normal Operations or Recovery Phase handling @S713 */ }
            perform action a37 { doc /* cannot provide trusted automation @S714 */ }
            perform action a38 { doc /* treats passenger disruption information as a secondary planning signal @S738 */ }
            perform action a39 { doc /* records these actions as operational context @S752 */ }
            perform action a40 { doc /* record the initiating user, the approving user, the affected operational object, and the effective time of the decision @S775 */ }
            perform action a41 { doc /* reconcile contingency actions with the Collaborative Decision Log @S787 */ }
            perform action a42 { doc /* record slot compliance events in the Audit Event Ledger @S789 */ }
            perform action a43 { doc /* proceed through phased increments @S888 */ }
            perform action a44 { doc /* live collaborative decisions are made @S897 */ }
            perform action a45 { doc /* produces parallel outputs @S905 */ }
            exhibit state modes {
                state s0 { doc /* Adverse Weather @S246,S319,S344,S464 */ }
                state s1 { doc /* Adverse Weather Mode @S022,S047,S087,S367,S539,S563,S612,S661,S707,S755,S831,S882,S908 */ }
                state s2 { doc /* Capacity Reduction State @S022,S047,S228,S344,S368,S539,S612,S660,S706,S831,S882,S908 */ }
                state s3 { doc /* Contingency Fallback State @S047,S247,S540,S716,S831,S882,S908,S926 */ }
                state s4 { doc /* Normal Operations @S047,S087,S246,S318,S611,S713,S831,S882,S908 */ }
                state s5 { doc /* Recovery Phase @S023,S047,S246,S320,S465,S513,S564,S713,S756,S831,S882,S908 */ }
                state s6 { doc /* Slot Compliance State @S047,S247,S882 */ }
                state s7 { doc /* degraded operation @S715 */ }
                state s8 { doc /* shadow operations @S905 */ }
                state s9 { doc /* winter operating mode @S371 */ }
            }
        }
        part rejectionReasons : RejectionReasons;
        part requestedDepartureTiming : RequestedDepartureTiming;
        part runwayLightingOutageCard : RunwayLightingOutageCard;
        part scheduledPassengerOperators : ScheduledPassengerOperators;
        part sectorLoadMonitor : SectorLoadMonitor {
            perform action a0 { doc /* provide additional indicators of emerging capacity loss and operational imbalance @S019 */ }
            perform action a1 { doc /* contributes airspace demand indicators @S106 */ }
            perform action a2 { doc /* provides the operational view of expected demand against the reduced sector capacity @S329 */ }
            perform action a3 { doc /* highlights intervals where overload is likely @S329 */ }
            perform action a4 { doc /* contributes early warnings @S408 */ }
            perform action a5 { doc /* produces the Departure Fix Load Sheet @S484 */ }
            perform action a6 { doc /* supplies time-bucketed counts, predicted occupancy, and overload flags @S592 */ }
            perform action a7 { doc /* provide the common inputs @S943 */ }
        }
        part securitySegregation : SecuritySegregation;
        part serviceSequencingConflicts : ServiceSequencingConflicts;
        part sharedOperationalPicture : SharedOperationalPicture;
        part shuttleAvailability : ShuttleAvailability;
        part simulationEvents : SimulationEvents;
        part simulationExercises : SimulationExercises;
        part slotAllocationEngine : SlotAllocationEngine {
            perform action a0 { doc /* supports fair and traceable allocation of constrained departure and arrival opportunities @S015 */ }
            perform action a1 { doc /* support planning and collaborative assessment @S031 */ }
            perform action a2 { doc /* applies the current Business Rules Registry parameters @S080 */ }
            perform action a3 { doc /* converts accepted constraints into Calculated Takeoff Time values and Target Off Block Time guidance for affected flights @S134 */ }
            perform action a4 { doc /* publishes a revised constraint set @S137 */ }
            perform action a5 { doc /* proposes regulated departure and arrival opportunities @S225 */ }
            perform action a6 { doc /* matching demand from the Demand Prediction Service to constraints @S225 */ }
            perform action a7 { doc /* derives a Calculated Takeoff Time or arrival opportunity @S227 */ }
            perform action a8 { doc /* recalculating the regulated opportunity @S244 */ }
            perform action a9 { doc /* derives the Calculated Takeoff Time by combining runway metering constraints, departure fix loading, and applicable Ground Delay Program rules @S253 */ }
            perform action a10 { doc /* receives a capacity update @S269 */ }
            perform action a11 { doc /* revise slot outcomes @S342 */ }
            perform action a12 { doc /* adjust allocated departure times @S355 */ }
            perform action a13 { doc /* recalculates affected Calculated Takeoff Time values @S374 */ }
            perform action a14 { doc /* support a Ground Delay Program @S398 */ }
            perform action a15 { doc /* produces the Pushback Window Token @S428 */ }
            perform action a16 { doc /* uses the sanitized readiness state @S533 */ }
            perform action a17 { doc /* evaluating whether a regulated flight can keep its allocated departure opportunity @S533 */ }
            perform action a18 { doc /* avoid assigning an aggressive departure sequence position to the affected flight @S575 */ }
            perform action a19 { doc /* preserves equity by distributing delay across operators @S603 */ }
            perform action a20 { doc /* uses these constraints when evaluating whether a Calculated Takeoff Time should be offered, retained, exchanged, or released @S625 */ }
            perform action a21 { doc /* retains the Calculated Takeoff Time @S659 */ }
            perform action a22 { doc /* evaluates the candidate swap against active Ground Delay Program constraints, Calculated Takeoff Time integrity, Target Off Block Time dependencies, and Airport Acceptance Rate commitments @S669 */ }
            perform action a23 { doc /* raised exception @S671 */ }
            perform action a24 { doc /* uses the reduced capacity value to protect fairness @S700 */ }
            perform action a25 { doc /* continues to apply the approved sequencing policy, runway capacity, airspace constraints, and published Ground Delay Program parameters @S745 */ }
            perform action a26 { doc /* reject data that lacks a trusted timestamp @S825 */ }
            perform action a27 { doc /* produced regulated demand @S840 */ }
            perform action a28 { doc /* protect feasible Calculated Takeoff Time assignments @S949 */ }
            perform action a29 { doc /* reduce avoidable re-sequencing @S949 */ }
            exhibit state modes {
                state s0 { doc /* Ground Delay Program @S227 */ }
            }
        }
        part slotComplianceState : SlotComplianceState;
        part slotCoordinator : SlotCoordinator {
            perform action a0 { doc /* align airline intentions, schedule constraints, and slot management decisions with the shared plan @S039 */ }
            perform action a1 { doc /* uses the Slot Allocation Engine to prepare an initial slot feasibility view @S068 */ }
            perform action a2 { doc /* does not publish binding Calculated Takeoff Time values during baseline construction @S068 */ }
            perform action a3 { doc /* maintains accountability for Calculated Takeoff Time allocation policy @S080 */ }
            perform action a4 { doc /* confirms that the Slot Allocation Engine applies the current Business Rules Registry parameters @S080 */ }
            perform action a5 { doc /* reviews airline requests for priority handling against published equity and operational feasibility rules @S136 */ }
            perform action a6 { doc /* checking Calculated Takeoff Time feasibility @S161 */ }
            perform action a7 { doc /* recording accepted slot adjustments, rejected slot adjustments, and unresolved slot conflicts in the Collaborative Decision Log @S161 */ }
            perform action a8 { doc /* administers the allocation run @S229 */ }
            perform action a9 { doc /* reviews exceptions @S229 */ }
            perform action a10 { doc /* confirms that proposed results are ready for publication through the Airport CDM Portal @S229 */ }
            perform action a11 { doc /* records each accepted or rejected exemption in the Collaborative Decision Log @S239 */ }
            perform action a12 { doc /* reviews proposed Calculated Takeoff Time values against network constraints @S258 */ }
            perform action a13 { doc /* requests adjustment @S258 */ }
            perform action a14 { doc /* verifies that any proposed resequencing remains compatible with the Calculated Takeoff Time tolerance and the current Slot Compliance State @S285 */ }
            perform action a15 { doc /* records the agreed pushback window rationale in the coordination notes @S356 */ }
            perform action a16 { doc /* uses the Slot Allocation Engine to distribute arrival times @S404 */ }
            perform action a17 { doc /* reviews the relationship between the Calculated Takeoff Time and the proposed surface release time @S457 */ }
            perform action a18 { doc /* accepting the change @S457 */ }
            perform action a19 { doc /* protects constrained rotations @S481 */ }
            perform action a20 { doc /* checking that a recovered gate plan remains compatible with the applicable Calculated Takeoff Time @S481 */ }
            perform action a21 { doc /* reviews the effect of diversion acceptance on Calculated Takeoff Time and Target Off Block Time commitments @S502 */ }
            perform action a22 { doc /* evaluate the operational acceptability of a requested change @S633 */ }
            perform action a23 { doc /* reviews any exception raised by the Slot Allocation Engine @S671 */ }
            perform action a24 { doc /* confirms whether the swap remains consistent with regional flow objectives @S671 */ }
            perform action a25 { doc /* sends the Slot Swap Permission Email @S672 */ }
            perform action a26 { doc /* initiates manual slot procedures using a time-ordered control sheet maintained at the Contingency Operations Console @S722 */ }
            perform action a27 { doc /* assigns any revised Calculated Takeoff Time @S724 */ }
            perform action a28 { doc /* confirming runway capacity with the Tower Supervisor @S724 */ }
            perform action a29 { doc /* confirming surface feasibility with the Ramp Control Lead @S724 */ }
            perform action a30 { doc /* uses the Crew Duty Extension Log to check whether manually issued slot times remain operationally achievable @S726 */ }
            perform action a31 { doc /* reconciles the manual slot record with the Slot Allocation Engine @S736 */ }
            perform action a32 { doc /* resolves any conflict in the Collaborative Decision Log @S736 */ }
            perform action a33 { doc /* administer slot allocation functions @S768 */ }
            perform action a34 { doc /* review substitution activity @S798 */ }
            perform action a35 { doc /* own slot allocation reference data @S815 */ }
            perform action a36 { doc /* review slot adherence @S848 */ }
            perform action a37 { doc /* detect recurring causes of noncompliance @S848 */ }
            perform action a38 { doc /* receive training on the Slot Allocation Engine, Airport CDM Portal, and applicable Business Rules Registry entries @S870 */ }
            perform action a39 { doc /* owns slot fairness, slot compliance monitoring, and exception handling @S964 */ }
        }
        part southRunwayMeter : SouthRunwayMeter {
            perform action a0 { doc /* provide additional indicators of emerging capacity loss and operational imbalance @S019 */ }
            perform action a1 { doc /* receive runway-specific capacity values @S114 */ }
            perform action a2 { doc /* maintain separate queues @S280 */ }
            perform action a3 { doc /* maintain independent queue counts @S359 */ }
            perform action a4 { doc /* applies the same planning principle to its assigned runway stream @S455 */ }
            perform action a5 { doc /* preserving separation from arrival regulation actions @S455 */ }
            perform action a6 { doc /* support independent checks of queue length @S845 */ }
        }
        part southportAirport : SouthportAirport;
        part staffingGaps : StaffingGaps;
        part stakeholderOrganization : StakeholderOrganization {
            perform action a0 { doc /* assign accountable representatives @S048 */ }
            perform action a1 { doc /* maintain current contact details @S048 */ }
            perform action a2 { doc /* follow agreed data use rules @S048 */ }
            perform action a3 { doc /* support post-operational review of decisions made through the Regional Flow Platform @S048 */ }
        }
        part stand : Stand {
            exhibit state modes {
                state s0 { doc /* blocked @S646 */ }
                state s1 { doc /* cleaned @S646 */ }
                state s2 { doc /* inspection-required state @S663 */ }
                state s3 { doc /* ready @S646 */ }
                state s4 { doc /* unavailable @S652 */ }
                state s5 { doc /* unchecked @S646 */ }
                state s6 { doc /* under inspection @S646 */ }
            }
        }
        part standAccessRouting : StandAccessRouting;
        part standReadinessIndication : StandReadinessIndication {
            perform action a0 { doc /* supports coordinated surface planning @S655 */ }
            perform action a1 { doc /* prevents premature sequencing @S655 */ }
        }
        part surfaceSurveillanceAdapter : SurfaceSurveillanceAdapter {
            perform action a0 { doc /* provide the data feeds @S018 */ }
            perform action a1 { doc /* provide managed integration points with external systems @S033 */ }
            perform action a2 { doc /* consolidates position updates from the East Apron Sensor and West Apron Sensor @S179 */ }
            perform action a3 { doc /* presents movement indications to the Airport CDM Portal @S179 */ }
            perform action a4 { doc /* confirming aircraft position, stand occupancy, and blocking conditions on critical apron lanes @S204 */ }
            perform action a5 { doc /* confirms whether an aircraft is still at stand, entering the movement area, holding short, or already committed to the departure stream @S281 */ }
            perform action a6 { doc /* confirms that aircraft leaving the pad follow the assigned route and do not block inbound traffic to the same treatment complex @S389 */ }
            perform action a7 { doc /* provides current movement area occupancy and equipment status indicators @S445 */ }
            perform action a8 { doc /* verifies that the apron position is physically clear @S474 */ }
            perform action a9 { doc /* normalizes apron sensing data into movement, occupancy, and blockage events @S580 */ }
            perform action a10 { doc /* produces the Runway Lighting Outage Card @S606 */ }
            perform action a11 { doc /* apply position quality checks @S828 */ }
            perform action a12 { doc /* mark uncertain observations @S828 */ }
        }
        part swapVolume : SwapVolume;
        part sweepTeam : SweepTeam {
            perform action a0 { doc /* confirms that the assigned apron area is clean, safe, and free of observed foreign object debris @S647 */ }
        }
        part systemSupportEngineer : SystemSupportEngineer {
            perform action a0 { doc /* maintain data quality, access control, operational continuity, and controlled configuration of the Regional Flow Platform @S042 */ }
            perform action a1 { doc /* monitors portal availability, interface latency, user session faults, and synchronization status against the Time Synchronization Service @S171 */ }
            perform action a2 { doc /* investigates technical failures in submission, validation, or publication @S688 */ }
            perform action a3 { doc /* confirmed data quality @S727 */ }
            perform action a4 { doc /* classifies the technical condition @S732 */ }
            perform action a5 { doc /* isolates failed components @S732 */ }
            perform action a6 { doc /* advises whether partial restoration is safe for operational use @S732 */ }
            perform action a7 { doc /* maintain infrastructure components @S772 */ }
            perform action a8 { doc /* investigate technical faults @S772 */ }
            perform action a9 { doc /* investigate technical gaps @S807 */ }
            perform action a10 { doc /* investigate technical causes of missing, delayed, duplicated, or transformed records @S835 */ }
            perform action a11 { doc /* provide evidence needed for stewardship decisions @S835 */ }
            perform action a12 { doc /* train superusers on service status checks, access fault escalation, and safe use of the Contingency Operations Console @S877 */ }
            perform action a13 { doc /* monitor defect trends, data quality, access changes, and user adoption @S910 */ }
            perform action a14 { doc /* provide round the clock on call coverage for production incidents @S914 */ }
            perform action a15 { doc /* join the Digital Briefing Room without delay @S916 */ }
            perform action a16 { doc /* advise operational supervisors on technical status, known workarounds, data integrity concerns, and recovery options @S918 */ }
            perform action a17 { doc /* maintain an incident record @S923 */ }
            perform action a18 { doc /* verify that fallback tools, exported operational data, and restoration checkpoints are available @S927 */ }
            perform action a19 { doc /* advising that normal technical service can resume @S927 */ }
            perform action a20 { doc /* is accountable for technical availability, fault response, configuration control, and coordinated restoration of the operational services @S971 */ }
        }
        part tacticalRegulationProposalStatus : TacticalRegulationProposalStatus;
        part targetOffBlockTimeValues : TargetOffBlockTimeValues;
        part terminalCurbSpace : TerminalCurbSpace;
        part timeNeededToClearPassengersFromTheAircraftVicinity : TimeNeededToClearPassengersFromTheAircraftVicinity;
        part timeSynchronizationService : TimeSynchronizationService {
            perform action a0 { doc /* provide governance, security, traceability, and performance measurement capabilities @S034 */ }
            perform action a1 { doc /* provides the reference clock used to compare forecast issue times with operational decision times @S110 */ }
            perform action a2 { doc /* time-stamped all airline integration transactions @S149 */ }
            perform action a3 { doc /* keep tower, duty desk, surveillance, and portal event times aligned @S187 */ }
            perform action a4 { doc /* time stamped allocation runs @S245 */ }
            perform action a5 { doc /* provides the reference clock for all target time calculations @S256 */ }
            perform action a6 { doc /* provides the common time reference for sweep records, readiness confirmations, and safety-related release decisions @S651 */ }
            perform action a7 { doc /* provide the common time basis @S824 */ }
        }
        part towerSequenceManager : TowerSequenceManager {
            perform action a0 { doc /* support the transition from regional planning decisions to executable airport and tower actions @S017 */ }
            perform action a1 { doc /* support tactical airport and regional coordination @S032 */ }
            perform action a2 { doc /* support local sequencing decisions @S180 */ }
            perform action a3 { doc /* receives the current ramp intent through system synchronization @S217 */ }
            perform action a4 { doc /* maintains the tactical runway sequence expectation @S254 */ }
            perform action a5 { doc /* highlights cases where the Calculated Takeoff Time is inconsistent with the local departure order @S254 */ }
            perform action a6 { doc /* translates the frozen operational targets into an executable runway order for departures @S275 */ }
            perform action a7 { doc /* builds a provisional order by runway, departure fix, aircraft wake category, and locally configured spacing rule @S279 */ }
            perform action a8 { doc /* applies the active spacing rules from the Business Rules Registry @S297 */ }
            perform action a9 { doc /* highlights flights that may miss their Calculated Takeoff Time @S297 */ }
            perform action a10 { doc /* refresh affected departure sequence advisories @S334 */ }
            perform action a11 { doc /* reserves departure sequence positions only for aircraft with an achievable pad release time and a valid runway taxi path @S380 */ }
            perform action a12 { doc /* confirms stable spacing and runway occupancy performance @S411 */ }
            perform action a13 { doc /* uses the hold advice to prevent a departure from being sequenced ahead of a fueling constraint @S450 */ }
            perform action a14 { doc /* receives a stable readiness indicator and an escalation flag @S536 */ }
            perform action a15 { doc /* advance an aircraft toward an active departure sequence @S552 */ }
            perform action a16 { doc /* considers confirmed apron blockage @S583 */ }
            perform action a17 { doc /* sequence advisory @S601 */ }
            perform action a18 { doc /* displays the accepted constraint @S702 */ }
            perform action a19 { doc /* provide actual movement milestones @S801 */ }
            perform action a20 { doc /* provide runway sequence counts @S844 */ }
        }
        part towerSupervisor : TowerSupervisor {
            perform action a0 { doc /* represent local airport, tower, ramp, handling, and winter operations considerations @S040 */ }
            perform action a1 { doc /* sends the Runway Inspection Note @S060 */ }
            perform action a2 { doc /* declares anticipated runway configuration, usable operating length assumptions, and any local sequencing constraints @S061 */ }
            perform action a3 { doc /* confirms that the Tower Sequence Manager reflects the current runway configuration @S089 */ }
            perform action a4 { doc /* reviews metering effects in the Tower Sequence Manager @S143 */ }
            perform action a5 { doc /* reviewing runway configuration assumptions, departure sequence feasibility, and tactical tower constraints @S160 */ }
            perform action a6 { doc /* keeps the Airport Duty Manager informed of conditions @S175 */ }
            perform action a7 { doc /* agree on the operational interpretation @S183 */ }
            perform action a8 { doc /* verifies that any proposed reduction in declared runway use is consistent with observed traffic, controller workload, and the current safety position @S189 */ }
            perform action a9 { doc /* confirmed that the movement can be integrated with the active ground route and runway plan @S202 */ }
            perform action a10 { doc /* reject a proposed departure opportunity @S243 */ }
            perform action a11 { doc /* challenge a proposed Calculated Takeoff Time @S263 */ }
            perform action a12 { doc /* uses the Tower Sequence Manager to confirm that each flight can be advanced without creating unsafe surface compression @S277 */ }
            perform action a13 { doc /* view both queues together @S280 */ }
            perform action a14 { doc /* intervene @S287 */ }
            perform action a15 { doc /* compares pad release expectations with runway queue gaps @S296 */ }
            perform action a16 { doc /* accepting an aircraft into the active departure stream @S296 */ }
            perform action a17 { doc /* confirm that any revised off-block sequence remains compatible with the Departure Metering Service @S313 */ }
            perform action a18 { doc /* confirm the active interpretation of the restriction @S345 */ }
            perform action a19 { doc /* monitors whether the planned release rate remains compatible with departure spacing and runway crossing demand @S358 */ }
            perform action a20 { doc /* agree whether the metering horizon should be extended @S368 */ }
            perform action a21 { doc /* protects runway departure spacing @S388 */ }
            perform action a22 { doc /* confirms whether the proposed landing rate is compatible with runway occupancy, missed approach protection, and local spacing constraints @S401 */ }
            perform action a23 { doc /* uses the display to see runway assignment pressure, airborne sequence spacing, and expected crossing points @S425 */ }
            perform action a24 { doc /* coordinates airborne sequencing with the Airspace Sector Planner @S500 */ }
            perform action a25 { doc /* uses the same result to understand whether a runway queue is being held @S605 */ }
            perform action a26 { doc /* reject a swap @S676 */ }
            perform action a27 { doc /* confirm which runway lighting elements are unavailable @S693 */ }
            perform action a28 { doc /* approving the operational status shown in the Tower Sequence Manager @S693 */ }
            perform action a29 { doc /* retains authority over tactical runway sequencing @S748 */ }
            perform action a30 { doc /* reject any advisory that would impair safe separation, wake spacing, or local controller workload @S748 */ }
            perform action a31 { doc /* operate the Tower Sequence Manager @S769 */ }
            perform action a32 { doc /* view runway metering information @S769 */ }
            perform action a33 { doc /* own tower sequence status data @S817 */ }
            perform action a34 { doc /* receive practical training on the Tower Sequence Manager, Departure Metering Service, Arrival Regulation Console, North Runway Meter, and South Runway Meter @S866 */ }
            perform action a35 { doc /* retain operational command authority @S917 */ }
            perform action a36 { doc /* compare recommendations with actual outcomes @S959 */ }
        }
        part towerSupervisoryPersonnel : TowerSupervisoryPersonnel;
        part towingProviders : TowingProviders;
        part trainingAssessments : TrainingAssessments {
            perform action a0 { doc /* verify that users can identify stale data, time synchronization problems, duplicate flights, conflicting constraints, and inappropriate automation reliance @S886 */ }
        }
        part turnaroundStatus : TurnaroundStatus;
        part users : Users {
            perform action a0 { doc /* compare automated recommendations with local knowledge @S883 */ }
            perform action a1 { doc /* document significant decisions in the Collaborative Decision Log @S883 */ }
            perform action a2 { doc /* explain departures from system proposals @S883 */ }
            perform action a3 { doc /* identify stale data, time synchronization problems, duplicate flights, conflicting constraints, and inappropriate automation reliance @S886 */ }
        }
        part vehicles : Vehicles;
        part weatherFeed : WeatherFeed {
            exhibit state modes {
                state s0 { doc /* degraded @S111 */ }
            }
        }
        part weatherIngestGateway : WeatherIngestGateway {
            perform action a0 { doc /* provide the data feeds @S018 */ }
            perform action a1 { doc /* provide managed integration points with external systems @S033 */ }
            perform action a2 { doc /* makes the outlook available to the Capacity Assessment Module @S057 */ }
            perform action a3 { doc /* preserves the forecast issue time for audit and later performance review @S057 */ }
            perform action a4 { doc /* data supplied through the Weather Ingest Gateway @S086 */ }
            perform action a5 { doc /* normalizes external and local meteorological feeds @S102 */ }
            perform action a6 { doc /* accepts aviation forecasts, radar-derived precipitation fields, lightning alerts, wind forecasts, ceiling and visibility forecasts, and runway condition weather inputs from approved sources @S108 */ }
            perform action a7 { doc /* marks the feed as degraded @S111 */ }
            perform action a8 { doc /* issue time-stamped weather condition updates @S182 */ }
            perform action a9 { doc /* updates the arrival model @S409 */ }
            perform action a10 { doc /* accepted operational weather classification inputs @S819 */ }
            perform action a11 { doc /* provide the common inputs @S943 */ }
        }
        part westApronSensor : WestApronSensor {
            perform action a0 { doc /* provide additional indicators of emerging capacity loss and operational imbalance @S019 */ }
            perform action a1 { doc /* detecting aircraft movement @S282 */ }
            perform action a2 { doc /* improve queue accuracy @S282 */ }
            perform action a3 { doc /* provide supporting movement evidence for the reopened area @S474 */ }
            perform action a4 { doc /* provide supporting surveillance cues @S645 */ }
            perform action a5 { doc /* support independent checks of queue length @S845 */ }
        }
        part workstationLayouts : WorkstationLayouts {
            perform action a0 { doc /* support rapid comparison between the Common Situation Display, Airport CDM Portal, Tower Sequence Manager, Ramp Movement Board, and relevant advisory messages @S885 */ }
        }
        flow f0 of OperationalReadinessInformationItem from airportCDMPortal to airportStakeholders { doc /* @S016 */ }
        flow f1 of SharedViewOfDemandCapacityConstraintsAndActiveTrafficManagementMeasuresItem from commonSituationDisplay to authorizedUsers { doc /* @S020 */ }
        flow f2 of NormalizedScheduleItem from flightDataExchange to demandPredictionService { doc /* @S053 */ }
        flow f3 of MorningWeatherOutlookItem from weatherIngestGateway to capacityAssessmentModule { doc /* @S057 */ }
        flow f4 of MorningWeatherOutlookItem from meteorologyBriefingOfficer to weatherIngestGateway { doc /* @S057 */ }
        flow f5 of StandReadinessInformationItem from rampMovementBoard to rampControlLead { doc /* @S063 */ }
        flow f6 of StandReadinessInformationItem from eastApronSensor to rampControlLead { doc /* @S063 */ }
        flow f7 of StandReadinessInformationItem from westApronSensor to rampControlLead { doc /* @S063 */ }
        flow f8 of DemandCurveItem from demandPredictionService to handlingResourcePlanner { doc /* @S065 */ }
        flow f9 of WeatherOutlookItem from weatherIngestGateway to capacityAssessmentModule { doc /* @S066 */ }
        flow f10 of RunwayDeclarationItem from towerSupervisor to capacityAssessmentModule { doc /* @S066 */ }
        flow f11 of UnresolvedAssumptionsItem from digitalBriefingRoom to collaborativeDecisionLog { doc /* @S071 */ }
        flow f12 of MorningPlanAvailabilityNotificationItem from alertDistributionHub to participatingRoles { doc /* @S073 */ }
        flow f13 of BusinessRulesRegistryParametersItem from businessRulesRegistry to slotAllocationEngine { doc /* @S080 */ }
        flow f14 of ExternalCoordinationOutcomesItem from networkOperationsLiaison to collaborativeDecisionLog { doc /* @S084 */ }
        flow f15 of ForecastConfidenceTimingRiskAndExpectedOperationalImpactItem from meteorologyBriefingOfficer to digitalBriefingRoom { doc /* @S086 */ }
        flow f16 of DataItem from weatherIngestGateway to meteorologyBriefingOfficer { doc /* @S086 */ }
        flow f17 of MaterialDeviationsItem from groundHandlingDispatcher to airportDutyManager { doc /* @S091 */ }
        flow f18 of AlertItem from militaryAirspaceLiaison to regionalFlowManager { doc /* @S093 */ }
        flow f19 of OutputsItem from departureMeteringService to commonSituationDisplay { doc /* @S095 */ }
        flow f20 of OutputsItem from arrivalRegulationConsole to commonSituationDisplay { doc /* @S095 */ }
        flow f21 of SynchronizedTimestampsItem from timeSynchronizationService to auditEventLedger { doc /* @S098 */ }
        flow f22 of DemandForecastItem from demandPredictionService to regionalFlowPlatform { doc /* @S101 */ }
        flow f23 of FiledFlightInformationItem from flightDataExchange to demandPredictionService { doc /* @S103 */ }
        flow f24 of CurrentOperatingScheduleItem from airlineInterfaceAdapter to demandPredictionService { doc /* @S103 */ }
        flow f25 of DemandProjectionsItem from demandPredictionService to capacityAssessmentModule { doc /* @S107 */ }
        flow f26 of WeatherFeedItem from weatherIngestGateway to regionalFlowPlatform { doc /* @S109 */ }
        flow f27 of RunwaySpecificCapacityValuesItem from capacityAssessmentModule to northRunwayMeter { doc /* @S114 */ }
        flow f28 of RunwaySpecificCapacityValuesItem from capacityAssessmentModule to southRunwayMeter { doc /* @S114 */ }
        flow f29 of ForecastDemandAssessedCapacityAndActiveGroundDelayProgramEffectsItem from commonSituationDisplay to regionalFlowManager { doc /* @S117 */ }
        flow f30 of CapacityChangeNotificationItem from alertDistributionHub to regionalFlowManager { doc /* @S121 */ }
        flow f31 of CapacityChangeNotificationItem from alertDistributionHub to towerSupervisor { doc /* @S121 */ }
        flow f32 of CapacityChangeNotificationItem from alertDistributionHub to airlineOperationsCoordinator { doc /* @S121 */ }
        flow f33 of TraceFromIncomingForecastProductToCapacityValueItem from auditEventLedger to performanceAnalyticsWarehouse { doc /* @S123 */ }
        flow f34 of FlightIntentMessageItem from airlineOperationsCentre to airlineInterfaceAdapter { doc /* @S126 */ }
        flow f35 of AcceptedIntentDataItem from airlineInterfaceAdapter to flightDataExchange { doc /* @S128 */ }
        flow f36 of FlightIntentMessageItem from flightDataExchange to demandPredictionService { doc /* @S131 */ }
        flow f37 of DemandForecastItem from demandPredictionService to capacityAssessmentModule { doc /* @S132 */ }
        flow f38 of StormCellSnapshotItem from meteorologyBriefingOfficer to capacityAssessmentModule { doc /* @S133 */ }
        flow f39 of ConstraintsItem from airlineInterfaceAdapter to airlineOperationsCentre { doc /* @S135 */ }
        flow f40 of ConstraintsItem from slotAllocationEngine to airlineInterfaceAdapter { doc /* @S135 */ }
        flow f41 of AcceptedSlotAdjustmentsRejectedSlotAdjustmentsAndUnresolvedSlotConflictsItem from slotCoordinator to collaborativeDecisionLog { doc /* @S161 */ }
        flow f42 of WeatherInterpretationForecastConfidenceAndExpectedTimingOfOperationalImpactsItem from meteorologyBriefingOfficer to airportCDMPortal { doc /* @S163 */ }
        flow f43 of CurrentRegionalDemandAndConstraintContextItem from regionalFlowPlatform to airportCDMPortal { doc /* @S164 */ }
        flow f44 of StaleMilestoneNotificationItem from airportCDMPortal to alertDistributionHub { doc /* @S166 */ }
        flow f45 of MandatoryFieldsPermissibleStatusValuesRetentionRulesAndDataQualityThresholdsItem from dataGovernanceSteward to airportCDMPortal { doc /* @S170 */ }
        flow f46 of ConditionsThatMayAffectRunwayTaxiwayStandOrApronAvailabilityItem from towerSupervisor to airportDutyManager { doc /* @S175 */ }
        flow f47 of PositionUpdatesItem from eastApronSensor to surfaceSurveillanceAdapter { doc /* @S179 */ }
        flow f48 of PositionUpdatesItem from westApronSensor to surfaceSurveillanceAdapter { doc /* @S179 */ }
        flow f49 of MovementIndicationsItem from surfaceSurveillanceAdapter to airportCDMPortal { doc /* @S179 */ }
        flow f50 of DutyDeskConfirmationsItem from airportDutyDesk to airportCDMPortal { doc /* @S185 */ }
        flow f51 of TransactionItem from identityAccessService to auditEventLedger { doc /* @S194 */ }
        flow f52 of SurfaceSurveillanceAdapterInputsItem from surfaceSurveillanceAdapter to rampControlLead { doc /* @S204 */ }
        flow f53 of SensorDataItem from eastApronSensor to rampControlLead { doc /* @S205 */ }
        flow f54 of SensorDataItem from westApronSensor to rampControlLead { doc /* @S205 */ }
        flow f55 of AlertItem from gateConflictDetector to rampControlLead { doc /* @S210 */ }
        flow f56 of ApronCongestionConditionItem from rampControlLead to towerSupervisor { doc /* @S218 */ }
        flow f57 of ApronCongestionConditionItem from rampControlLead to airportDutyManager { doc /* @S218 */ }
        flow f58 of MovementUpdatesItem from rampMovementBoard to auditEventLedger { doc /* @S222 */ }
        flow f59 of DemandItem from demandPredictionService to slotAllocationEngine { doc /* @S225 */ }
        flow f60 of ConstraintsItem from capacityAssessmentModule to slotAllocationEngine { doc /* @S225 */ }
        flow f61 of FlightIntentMessageItem from airlineOperationsCoordinator to slotAllocationEngine { doc /* @S226 */ }
        flow f62 of AirportCapacityPlanItem from airportDutyManager to slotAllocationEngine { doc /* @S226 */ }
        flow f63 of AcceptedOrRejectedExemptionItem from slotCoordinator to collaborativeDecisionLog { doc /* @S239 */ }
        flow f64 of ProposedDepartureOpportunitiesAndCalculatedTakeoffTimeValuesItem from departureMeteringService to towerSequenceManager { doc /* @S242 */ }
        flow f65 of ApronConstraintsItem from rampControlLead to rampMovementBoard { doc /* @S244 */ }
        flow f66 of AirportCapacityPlanItem from airportDutyManager to capacityAssessmentModule { doc /* @S252 */ }
        flow f67 of CalculatedTakeoffTimeItem from departureMeteringService to towerSequenceManager { doc /* @S254 */ }
        flow f68 of TargetOffBlockTimeItem from regionalFlowPlatform to airlineOperationsCoordinator { doc /* @S259 */ }
        flow f69 of TargetOffBlockTimeRevisionItem from airlineOperationsCoordinator to airportCDMPortal { doc /* @S260 */ }
        flow f70 of AuditRecordsItem from auditEventLedger to performanceAnalyticsWarehouse { doc /* @S274 */ }
        flow f71 of RunwayDemandItem from towerSequenceManager to rampControlLead { doc /* @S283 */ }
        flow f72 of ActiveSpacingRulesItem from businessRulesRegistry to towerSequenceManager { doc /* @S297 */ }
        flow f73 of ExpectedServiceCompletionTimesItem from groundHandlingDispatcher to handlingResourcePlanner { doc /* @S302 */ }
        flow f74 of ResourceDrivenFeasibilityStatusItem from airportCDMPortal to airlineOperationsCoordinator { doc /* @S312 */ }
        flow f75 of ResourceDrivenFeasibilityStatusItem from airportCDMPortal to aircraftOperatorRepresentative { doc /* @S312 */ }
        flow f76 of ConstraintItem from handlingResourcePlanner to regionalFlowPlatform { doc /* @S318 */ }
        flow f77 of SubscriptionRulesItem from businessRulesRegistry to alertDistributionHub { doc /* @S332 */ }
        flow f78 of AirspaceAlertAcknowledgementAndDownstreamDecisionItem from regionalFlowPlatform to auditEventLedger { doc /* @S333 */ }
        flow f79 of CurrentCapacityAssumptionsItem from capacityAssessmentModule to departureMeteringService { doc /* @S335 */ }
        flow f80 of ActiveRestrictionStatusExpectedOperationalEffectAndRelatedCoordinationNotesItem from airportCDMPortal to commonSituationDisplay { doc /* @S337 */ }
        flow f81 of ActiveRestrictionStatusExpectedOperationalEffectAndRelatedCoordinationNotesItem from commonSituationDisplay to airlineOperationsCoordinator { doc /* @S338 */ }
        flow f82 of DepartureDemandProfileItem from demandPredictionService to capacityAssessmentModule { doc /* @S351 */ }
        flow f83 of ReconsiderationRequestItem from aircraftOperatorRepresentative to airportCDMPortal { doc /* @S363 */ }
        flow f84 of AffectedRunwayQueueItem from alertDistributionHub to commonSituationDisplay { doc /* @S366 */ }
        flow f85 of OperationalBasisItem from capacityAssessmentModule to commonSituationDisplay { doc /* @S400 */ }
        flow f86 of ArrivalPlanItem from airportCDMPortal to aircraftOperatorRepresentative { doc /* @S405 */ }
        flow f87 of AcknowledgementsItem from airportCDMPortal to collaborativeDecisionLog { doc /* @S405 */ }
        flow f88 of RecordedRegulationHistoryItem from auditEventLedger to performanceAnalyticsWarehouse { doc /* @S418 */ }
        flow f89 of CombinedTacticalViewItem from integratedTacticalManagementPosition to regionalFlowManager { doc /* @S420 */ }
        flow f90 of BaseMapTimelineFlightListAndMeasureStatusPanelsItem from commonSituationDisplay to integratedTacticalManagementPosition { doc /* @S421 */ }
        flow f91 of OperationalClockItem from timeSynchronizationService to regionalFlowPlatform { doc /* @S422 */ }
        flow f92 of RunwayAssignmentPressureAirborneSequenceSpacingAndExpectedCrossingPointsItem from commonSituationDisplay to towerSupervisor { doc /* @S425 */ }
        flow f93 of AgreedTargetOffBlockTimeValuesAndStakeholderRemarksItem from airportCDMPortal to integratedTacticalManagementPosition { doc /* @S429 */ }
        flow f94 of SectorDemandItem from sectorLoadMonitor to airspaceSectorPlanner { doc /* @S432 */ }
        flow f95 of WeatherImpactsItem from weatherIngestGateway to integratedTacticalManagementPosition { doc /* @S434 */ }
        flow f96 of CurrentMovementAreaOccupancyAndEquipmentStatusIndicatorsItem from surfaceSurveillanceAdapter to rampMovementBoard { doc /* @S445 */ }
        flow f97 of CurrentMovementAreaOccupancyAndEquipmentStatusIndicatorsItem from surfaceSurveillanceAdapter to towerSequenceManager { doc /* @S445 */ }
        flow f98 of OperationalSignificanceOfTheConditionItem from airportDutyManager to airportCDMPortal { doc /* @S447 */ }
        flow f99 of CandidatePushbackSpacingItem from departureMeteringService to slotAllocationEngine { doc /* @S456 */ }
        flow f100 of SurfaceEquipmentAndApronCongestionAdvisoriesItem from alertDistributionHub to regionalFlowManager { doc /* @S463 */ }
        flow f101 of GateConflictItem from gateConflictDetector to airportCDMPortal { doc /* @S470 */ }
        flow f102 of SupportingMovementEvidenceItem from eastApronSensor to surfaceSurveillanceAdapter { doc /* @S474 */ }
        flow f103 of SupportingMovementEvidenceItem from westApronSensor to surfaceSurveillanceAdapter { doc /* @S474 */ }
        flow f104 of PushbackWindowTokenItem from slotAllocationEngine to airportCDMPortal { doc /* @S503 */ }
        flow f105 of DiversionRationalePriorityClassificationResourceCommitmentAndAgreedRecoveryTargetItem from digitalBriefingRoom to collaborativeDecisionLog { doc /* @S506 */ }
        flow f106 of PlannedRemoteStandOperatingPostureItem from airportDutyManager to airportCDMPortal { doc /* @S544 */ }
        flow f107 of TowbarShortageReportItem from groundHandlingDispatcher to rampControlLead { doc /* @S556 */ }
        flow f108 of BorderAndCustomsStatusItem from airportCDMPortal to authorizedOperationalUsers { doc /* @S572 */ }
        flow f109 of MedicalDiversionNoticeItem from airportDutyManager to arrivalRegulationConsole { doc /* @S576 */ }
        flow f110 of SectorValuesItem from sectorLoadMonitor to regionalFlowPlatform { doc /* @S593 */ }
        flow f111 of ScheduledMovementsItem from flightDataExchange to regionalFlowPlatform { doc /* @S593 */ }
        flow f112 of PredictedReadinessItem from demandPredictionService to regionalFlowPlatform { doc /* @S593 */ }
        flow f113 of ThresholdsItem from businessRulesRegistry to capacityAssessmentModule { doc /* @S600 */ }
        flow f114 of NotificationsItem from alertDistributionHub to regionalFlowManager { doc /* @S614 */ }
        flow f115 of NotificationsItem from alertDistributionHub to towerSupervisor { doc /* @S614 */ }
        flow f116 of NotificationsItem from alertDistributionHub to rampControlLead { doc /* @S614 */ }
        flow f117 of NotificationsItem from alertDistributionHub to slotCoordinator { doc /* @S614 */ }
        flow f118 of NotificationsItem from alertDistributionHub to networkOperationsLiaison { doc /* @S614 */ }
        flow f119 of LegalityStatusItem from airlineInterfaceAdapter to regionalFlowPlatform { doc /* @S621 */ }
        flow f120 of CrewLegalityInputsItem from aircraftOperatorRepresentative to airlineInterfaceAdapter { doc /* @S622 */ }
        flow f121 of CrewLegalityInputsItem from aircraftOperatorRepresentative to airportCDMPortal { doc /* @S622 */ }
        flow f122 of FeasibilityResultAndTimingBoundaryItem from slotAllocationEngine to departureMeteringService { doc /* @S626 */ }
        flow f123 of ApprovedOperationalResultItem from flightDataExchange to downstreamServices { doc /* @S638 */ }
        flow f124 of ProposedSubstitutionItem from airlineOperationsCoordinator to airportCDMPortal { doc /* @S667 */ }
        flow f125 of ExceptionItem from slotAllocationEngine to slotCoordinator { doc /* @S671 */ }
        flow f126 of ConcurrenceItem from aircraftOperatorRepresentative to airportCDMPortal { doc /* @S673 */ }
        flow f127 of StandOccupancyPushbackSpacingAndTugAvailabilityItem from rampMovementBoard to rampControlLead { doc /* @S677 */ }
        flow f128 of ApronSweepCompletionNoteItem from rampControlLead to airportDutyManager { doc /* @S678 */ }
        flow f129 of CustomsHoldReleaseNoteItem from airportDutyManager to airlineOperationsCoordinator { doc /* @S679 */ }
        flow f130 of UnavailableRunwayLightingElementsItem from runwayLightingOutageCard to towerSupervisor { doc /* @S693 */ }
        flow f131 of InfrastructureEventsItem from airportCDMPortal to authorizedAirportAirlineAndFlowManagementUsers { doc /* @S695 */ }
        flow f132 of RevisedInputsItem from departureMeteringService to slotAllocationEngine { doc /* @S699 */ }
        flow f133 of ClosureItem from airportDutyManager to airportCDMPortal { doc /* @S713 */ }
        flow f134 of CrewDutyExtensionLogItem from aircraftOperatorRepresentative to slotCoordinator { doc /* @S726 */ }
        flow f135 of CurrentOperatingBasisItem from airportDutyManager to digitalBriefingRoom { doc /* @S734 */ }
        flow f136 of LoggedRationaleItem from collaborativeDecisionLog to performanceAnalyticsWarehouse { doc /* @S760 */ }
        flow f137 of RoleProfilesItem from identityAccessService to regionalFlowManager { doc /* @S766 */ }
        flow f138 of RoleProfilesItem from identityAccessService to towerSupervisor { doc /* @S766 */ }
        flow f139 of RoleProfilesItem from identityAccessService to rampControlLead { doc /* @S766 */ }
        flow f140 of RoleProfilesItem from identityAccessService to slotCoordinator { doc /* @S766 */ }
        flow f141 of RoleProfilesItem from identityAccessService to airlineOperationsCoordinator { doc /* @S766 */ }
        flow f142 of RampMovementStatusItem from rampControlLead to rampMovementBoard { doc /* @S770 */ }
        flow f143 of TimeItem from timeSynchronizationService to auditEventLedger { doc /* @S778 */ }
        flow f144 of SlotComplianceEventsItem from regionalFlowPlatform to auditEventLedger { doc /* @S789 */ }
        flow f145 of TimeSourceItem from timeSynchronizationService to auditEventLedger { doc /* @S792 */ }
        flow f146 of AuthenticatedRoleItem from identityAccessService to airportCDMPortal { doc /* @S793 */ }
        flow f147 of OperationalWeatherClassificationInputsItem from meteorologyBriefingOfficer to weatherIngestGateway { doc /* @S819 */ }
        flow f148 of CommonTimeBasisItem from timeSynchronizationService to regionalFlowPlatform { doc /* @S824 */ }
        flow f149 of DispositionItem from dataGovernanceSteward to auditEventLedger { doc /* @S833 */ }
        flow f150 of UrgentDiscrepanciesItem from alertDistributionHub to digitalBriefingRoom { doc /* @S834 */ }
        flow f151 of EvidenceItem from systemSupportEngineer to dataGovernanceSteward { doc /* @S835 */ }
        flow f152 of UnconstrainedDemandItem from demandPredictionService to performanceAnalyticsWarehouse { doc /* @S840 */ }
        flow f153 of RegulatedDemandItem from slotAllocationEngine to performanceAnalyticsWarehouse { doc /* @S840 */ }
        flow f154 of RealizedMovementTimesItem from flightDataExchange to performanceAnalyticsWarehouse { doc /* @S840 */ }
        flow f155 of DelayAbsorptionIndicatorItem from delayAbsorptionIndicator to regionalFlowManager { doc /* @S842 */ }
        flow f156 of SignificantDecisionsItem from users to collaborativeDecisionLog { doc /* @S883 */ }
        flow f157 of EvidenceItem from performanceAnalyticsWarehouse to postExerciseReviews { doc /* @S887 */ }
        flow f158 of EvidenceItem from auditEventLedger to postExerciseReviews { doc /* @S887 */ }
        flow f159 of ParallelOutputsItem from regionalFlowPlatform to operationalUsers { doc /* @S905 */ }
        flow f160 of OperationalDecisionsItem from localUsers to airportCDMPortal { doc /* @S907 */ }
        flow f161 of TechnicalStatusKnownWorkaroundsDataIntegrityConcernsAndRecoveryOptionsItem from systemSupportEngineer to operationalSupervisors { doc /* @S918 */ }
        flow f162 of IntentDataItem from flightDataExchange to demandPredictionService { doc /* @S941 */ }
        flow f163 of RecoveryOptionsItem from contingencyOperationsConsole to commonSituationDisplay { doc /* @S952 */ }
        flow f164 of ApprovedRulesItem from businessRulesRegistry to slotAllocationEngine { doc /* @S980 */ }
        flow f165 of ApprovedRulesItem from businessRulesRegistry to departureMeteringService { doc /* @S980 */ }
        flow f166 of ApprovedRulesItem from businessRulesRegistry to arrivalRegulationConsole { doc /* @S980 */ }
        flow f167 of ApprovedRulesItem from businessRulesRegistry to towerSequenceManager { doc /* @S980 */ }
        flow f168 of ApprovedRulesItem from businessRulesRegistry to rampMovementBoard { doc /* @S980 */ }
        flow f169 of AirportAcceptanceRateItem from capacityAssessmentModule to slotAllocationEngine { doc /* joined @S341,S226 */ }
        flow f170 of TheCrewBusDelaySlipItem from groundHandlingDispatcher to airlineOperationsCoordinator { doc /* joined @S140,S237 */ }
        flow f171 of TheStandTowRequestFormItem from rampControlLead to handlingResourcePlanner { doc /* joined @S208,S304 */ }
        flow f172 of TheDeicingPadQueueCardItem from deicingCoordinator to rampControlLead { doc /* joined @S294,S378 */ }
        flow f173 of TheTemporaryRestrictionNoticeItem from militaryAirspaceLiaison to regionalFlowManager { doc /* joined @S325,S399 */ }
        flow f174 of TheFuelTruckHoldAdviceItem from rampMovementBoard to towerSequenceManager { doc /* joined @S361,S450 */ }
        flow f175 of TheGateReopeningMemoItem from gateConflictDetector to airlineOperationsCoordinator { doc /* joined @S386,S472 */ }
        flow f176 of TheLateBaggageTagListItem from airlineInterfaceAdapter to groundHandlingDispatcher { doc /* joined @S452,S519 */ }
        flow f177 of TheDepartureFixLoadSheetItem from sectorLoadMonitor to regionalFlowManager { doc /* joined @S484,S598 */ }
        flow f178 of TheRemoteStandShuttleCountItem from handlingResourcePlanner to airportCDMPortal { doc /* joined @S547,S648 */ }
        flow f179 of AirportAcceptanceRateItem from capacityAssessmentModule to arrivalRegulationConsole { doc /* joined @S341,S698 */ }
        flow f180 of TheSlotSwapPermissionEmailItem from slotCoordinator to airlineOperationsCoordinator { doc /* joined @S672,S795 */ }
        flow f181 of ThePassengerMisconnectCountItem from airlineOperationsCoordinator to departureMeteringService { doc /* joined @S740,S851 */ }
    }
    requirement def R0 { doc /* sector loading constraints require close coordination with the Military Airspace Liaison @S006 */ subject s : MilitaryAirspaceLiaison; }
    requirement def R1 { doc /* require a common basis for decisions rather than separate local views of the same operational picture @S011 */ subject s : AirlineOperationsCoordinator; }
    requirement def R2 { doc /* The Common Situation Display is expected to give authorized users a shared view of demand, capacity, constraints, and active traffic management measures. @S020 */ subject s : CommonSituationDisplay; }
    requirement def R3 { doc /* The Collaborative Decision Log and Audit Event Ledger are expected to preserve the rationale, timing, and authorization of material operational decisions. @S021 */ subject s : CollaborativeDecisionLog; }
    requirement def R4 { doc /* The Collaborative Decision Log and Audit Event Ledger are expected to preserve the rationale, timing, and authorization of material operational decisions. @S021 */ subject s : AuditEventLedger; }
    requirement def R5 { doc /* During Adverse Weather Mode or Capacity Reduction State, the system must support rapid development of a Tactical Regulation Proposal and consistent communication of the resulting Ground Delay Program when one is required. @S022 */ subject s : RegionalFlowPlatform; }
    requirement def R6 { doc /* During Recovery Phase, the system must help stakeholders restore scheduled flow while monitoring Target Off Block Time, Calculated Takeoff Time, and Slot Compliance State performance. @S023 */ subject s : RegionalFlowPlatform; }
    requirement def R7 { doc /* Participation in the regional system requires each stakeholder organization to assign accountable representatives, maintain current contact details, follow agreed data use rules, and support post-operational review of decisions made through the Regional Flow Platform. @S048 */ subject s : StakeholderOrganization; }
    requirement def R8 { doc /* conditional availability must be treated as uncertain @S059 */ subject s : MilitaryAirspaceLiaison; }
    requirement def R9 { doc /* changes must be entered through controlled Regional Flow Platform functions @S073 */ subject s : RegionalFlowPlatform; }
    requirement def R10 { doc /* outputs must remain visible on the Common Situation Display @S095 */ subject s : DepartureMeteringService; }
    requirement def R11 { doc /* outputs must remain visible on the Common Situation Display @S095 */ subject s : ArrivalRegulationConsole; }
    requirement def R12 { doc /* During Adverse Weather Mode or a Capacity Reduction State, airline operations centres are expected to submit conservative intents that distinguish firm operating plans from speculative recovery options. @S146 */ subject s : AirlineOperationsCentres; }
    requirement def R13 { doc /* The Airline Operations Coordinator is responsible for keeping the Flight Intent Message status, Target Off Block Time, passenger readiness indicator, and aircraft operational constraint notes current for each represented flight. @S157 */ subject s : AirlineOperationsCoordinator; }
    requirement def R14 { doc /* The Ground Handling Dispatcher is responsible for updating servicing completion, baggage readiness, staffing limitation, and equipment availability milestones as soon as the handling status changes. @S158 */ subject s : GroundHandlingDispatcher; }
    requirement def R15 { doc /* The Ramp Control Lead is responsible for maintaining stand release readiness, apron movement conflicts, tug availability, and local pushback sequencing inputs in the portal. @S159 */ subject s : RampControlLead; }
    requirement def R16 { doc /* The Tower Supervisor is responsible for reviewing runway configuration assumptions, departure sequence feasibility, and tactical tower constraints before those values are used for metering decisions. @S160 */ subject s : TowerSupervisor; }
    requirement def R17 { doc /* The Slot Coordinator is responsible for checking Calculated Takeoff Time feasibility and recording accepted slot adjustments, rejected slot adjustments, and unresolved slot conflicts in the Collaborative Decision Log. @S161 */ subject s : SlotCoordinator; }
    requirement def R18 { doc /* The Airport Duty Manager is responsible for maintaining the Airport Capacity Plan, declaring local operating impacts, and confirming transitions between Normal Operations, Adverse Weather Mode, Capacity Reduction State, and Recovery Phase. @S162 */ subject s : AirportDutyManager; }
    requirement def R19 { doc /* Cedarbell shall expose the current regional demand and constraint context to the shared workspace at each publication cycle without requiring manual re-entry. @S164 */ subject s : RegionalFlowPlatform; }
    requirement def R20 { doc /* When a milestone becomes stale, the Airport CDM Portal shall highlight the affected flight and notify the role accountable for the next update through the Alert Distribution Hub. @S166 */ subject s : AirportCDMPortal; }
    requirement def R21 { doc /* Each airport participant shall update a material change within two minutes of becoming aware of it during Normal Operations and within one minute during Adverse Weather Mode or Capacity Reduction State. @S167 */ subject s : AirportParticipant; }
    requirement def R22 { doc /* If the exact value is not yet known, the accountable participant shall enter a provisional value with an uncertainty flag rather than leaving the milestone unchanged. @S168 */ subject s : AirportParticipant; }
    requirement def R23 { doc /* During Contingency Fallback State, the Airport CDM Portal shall preserve the last synchronized milestone set and clearly mark any updates entered under degraded operating procedures. @S172 */ subject s : AirportCDMPortal; }
    requirement def R24 { doc /* Orchard shall issue time-stamped weather condition updates for use in tower and airport duty coordination. @S182 */ subject s : WeatherIngestGateway; }
    requirement def R25 { doc /* The Time Synchronization Service shall keep tower, duty desk, surveillance, and portal event times aligned so that later review can reconstruct the sequence of events. @S187 */ subject s : TimeSynchronizationService; }
    requirement def R26 { doc /* The Ramp Control Lead shall not release a pushback until the Tower Supervisor has confirmed that the movement can be integrated with the active ground route and runway plan. @S202 */ subject s : RampControlLead; }
    requirement def R27 { doc /* Airline Operations Coordinator participation is required when a resequence would materially affect passenger boarding, connection protection, or aircraft rotation plans. @S214 */ subject s : AirlineOperationsCoordinator; }
    requirement def R28 { doc /* Marlinstone shall refresh stand demand forecasts when the Ramp Movement Board records a material change in planned off-block timing. @S216 */ subject s : DemandPredictionService; }
    requirement def R29 { doc /* The engine shall not improve one operator's position by imposing an excessive delay on another operator unless the rule basis is visible and logged. @S234 */ subject s : SlotAllocationEngine; }
    requirement def R30 { doc /* Saffron shall confirm any operator-requested Target Off Block Time revision in the Airport CDM Portal before the freeze horizon expires. @S260 */ subject s : AirlineOperationsCoordinator; }
    requirement def R31 { doc /* The Aircraft Operator Representative is responsible for keeping aircraft readiness information current enough for the tower team to trust the displayed status. @S291 */ subject s : AircraftOperatorRepresentative; }
    requirement def R32 { doc /* Foxglove shall publish tower readiness changes to authenticated airline and handling users within the configured refresh interval. @S293 */ subject s : AirportCDMPortal; }
    requirement def R33 { doc /* Brindle must confirm that any revised off-block sequence remains compatible with the Departure Metering Service before the change is released to the airport community. @S313 */ subject s : TowerSupervisor; }
    requirement def R34 { doc /* The Aircraft Operator Representative is expected to declare whether the operator can accept a later off-block time without causing crew, connection, or aircraft rotation impacts. @S316 */ subject s : AircraftOperatorRepresentative; }
    requirement def R35 { doc /* Ironleaf must refresh affected departure sequence advisories when a restriction changes the usable departure routes or expected release spacing. @S334 */ subject s : TowerSequenceManager; }
    requirement def R36 { doc /* shall adjust allocated departure times when metering rules require additional stand absorption to preserve the planned runway sequence @S355 */ subject s : SlotAllocationEngine; }
    requirement def R37 { doc /* Quartzline must coordinate every pad release with the Tower Supervisor before the aircraft leaves the treated area. @S387 */ subject s : RampControlLead; }
    requirement def R38 { doc /* Skylark must refresh the apron movement layer within five seconds of each validated surface event. @S427 */ subject s : RampMovementBoard; }
    requirement def R39 { doc /* The Airline Operations Coordinator remains responsible for confirming whether the affected flight should keep its Target Off Block Time, request a new value, or accept a later Calculated Takeoff Time. @S451 */ subject s : AirlineOperationsCoordinator; }
    requirement def R40 { doc /* Lantern must distribute surface equipment and apron congestion advisories to subscribed operational roles within the latency target defined in the Business Rules Registry. @S461 */ subject s : AlertDistributionHub; }
    requirement def R41 { doc /* Nightjar shall suppress handler-exception annotations for arriving flights unless the exception changes the Airport Acceptance Rate or a regulated arrival sequence. @S535 */ subject s : ArrivalRegulationConsole; }
    requirement def R42 { doc /* customs status events and apron sensor events must align with Calculated Takeoff Time and Target Off Block Time decisions @S585 */ subject s : TimeSynchronizationService; }
    requirement def R43 { doc /* scarce capacity must be protected for the published tactical plan @S675 */ subject s : RegionalFlowManager; }
    requirement def R44 { doc /* is responsible for ensuring that declared service reductions are entered promptly and that the operational description is consistent with local aerodrome control procedures @S692 */ subject s : AirportDutyManager; }
    requirement def R45 { doc /* must not automatically overwrite issued times @S728 */ subject s : DepartureMeteringService; }
    requirement def R46 { doc /* Transition out of the Contingency Fallback State requires stable service performance, verified data consistency, successful user access, and agreement from the operational leads affected by the outage @S735 */ subject s : ContingencyFallbackState; }
    requirement def R47 { doc /* Each named operational user shall authenticate with an individually assigned identity before accessing the Airport CDM Portal, Digital Briefing Room, or any operational console. @S764 */ subject s : NamedOperationalUser; }
    requirement def R48 { doc /* Role profiles shall grant the minimum access needed to view, propose, approve, or administer operational data within the Regional Flow Platform. @S767 */ subject s : RegionalFlowPlatform; }
    requirement def R49 { doc /* Where dual control is required, the Regional Flow Platform shall record the initiating user, the approving user, the affected operational object, and the effective time of the decision. @S775 */ subject s : RegionalFlowPlatform; }
    requirement def R50 { doc /* Access to the Performance Analytics Warehouse shall be restricted to authorized analytical roles and shall not allow retrospective alteration of operational records held in the Audit Event Ledger. @S776 */ subject s : PerformanceAnalyticsWarehouse; }
    requirement def R51 { doc /* The Audit Event Ledger shall capture successful and failed authentication attempts, role changes, privilege elevations, operational approvals, configuration changes, data exports, and emergency access activations. @S777 */ subject s : AuditEventLedger; }
    requirement def R52 { doc /* All audit records shall use time derived from the Time Synchronization Service so that investigations can reconstruct event order across the Airport CDM Portal, Slot Allocation Engine, and Alert Distribution Hub. @S778 */ subject s : AuditEventLedger; }
    requirement def R53 { doc /* Audit records shall be protected against ordinary user modification and retained for a period agreed by the airport operator, regional authority, and participating aircraft operators. @S779 */ subject s : AuditEventLedger; }
    requirement def R54 { doc /* The Identity Access Service shall support rapid suspension of accounts when a user changes role, leaves an organization, or becomes subject to an operational integrity concern. @S781 */ subject s : IdentityAccessService; }
    requirement def R55 { doc /* Silverpine shall accept emergency access activations only after the Identity Access Service records the authorizing incident reference and expiry time. @S783 */ subject s : ContingencyOperationsConsole; }
    requirement def R56 { doc /* During Contingency Fallback State, access control shall continue to enforce role separation even when some integrations are unavailable and manual coordination becomes necessary. @S786 */ subject s : AccessControl; }
    requirement def R57 { doc /* When normal connectivity is restored, the Regional Flow Platform shall reconcile contingency actions with the Collaborative Decision Log so that accountability is preserved across the full incident timeline. @S787 */ subject s : RegionalFlowPlatform; }
    requirement def R58 { doc /* After connectivity is restored, audit processing shall treat reconciled contingency actions as part of the same operational record as actions taken during Normal Operations. @S788 */ subject s : AuditProcessing; }
    requirement def R59 { doc /* The Regional Flow Platform shall record slot compliance events in the Audit Event Ledger using the operating date, flight identifier, airport, runway direction, and applicable regulation reference. @S789 */ subject s : RegionalFlowPlatform; }
    requirement def R60 { doc /* The Slot Compliance State shall indicate whether a flight was compliant, early, late, exempted, substituted, cancelled, or pending review at the end of the traffic period. @S791 */ subject s : SlotComplianceState; }
    requirement def R61 { doc /* The Audit Event Ledger shall preserve the time source applied by the Time Synchronization Service so that later review can distinguish operational delay from data latency. @S792 */ subject s : AuditEventLedger; }
    requirement def R62 { doc /* User decisions entered through the Airport CDM Portal shall be linked to the authenticated role provided by the Identity Access Service. @S793 */ subject s : AirportCDMPortal; }
    requirement def R63 { doc /* The Collaborative Decision Log shall retain the stated reason, decision time, affected flight, and visible operational context for each material change to a slot or sequence. @S794 */ subject s : CollaborativeDecisionLog; }
    requirement def R64 { doc /* The Slot Coordinator shall review substitution activity after operations to confirm that priority rules were applied consistently across participating operators. @S798 */ subject s : SlotCoordinator; }
    requirement def R65 { doc /* Changes made inside the freeze horizon shall require a reason code and shall be visible to the Regional Flow Manager during post-operations review. @S800 */ subject s : ChangesMadeInsideTheFreezeHorizon; }
    requirement def R66 { doc /* The Tower Sequence Manager and Ramp Movement Board shall provide actual movement milestones that support independent verification of slot performance. @S801 */ subject s : TowerSequenceManager; }
    requirement def R67 { doc /* Surface movement evidence from the Surface Surveillance Adapter shall be retained long enough to support dispute resolution and regulatory audit requests. @S802 */ subject s : SurfaceSurveillanceAdapter; }
    requirement def R68 { doc /* Capacity changes made through the Capacity Assessment Module shall be correlated with the active Airport Capacity Plan and Airport Acceptance Rate used at the time of allocation. @S803 */ subject s : CapacityAssessmentModule; }
    requirement def R69 { doc /* The Performance Analytics Warehouse shall aggregate compliance outcomes by carrier, route group, regulation, airport operating configuration, and time band. @S804 */ subject s : PerformanceAnalyticsWarehouse; }
    requirement def R70 { doc /* Aggregated metrics shall support review of systemic lateness without exposing commercially sensitive detail beyond authorized roles. @S805 */ subject s : AggregatedMetrics; }
    requirement def R71 { doc /* The Data Governance Steward shall verify that audit fields required for slot performance reporting remain complete, immutable, and traceable to approved data definitions. @S806 */ subject s : DataGovernanceSteward; }
    requirement def R72 { doc /* The System Support Engineer shall investigate technical gaps when audit sequences show missing events, duplicate updates, or inconsistent timestamps. @S807 */ subject s : SystemSupportEngineer; }
    requirement def R73 { doc /* The Regional Flow Manager shall use the Post Operations Report to identify whether noncompliance resulted from operator choice, airport constraint, airspace constraint, weather impact, or system issue. @S808 */ subject s : RegionalFlowManager; }
    requirement def R74 { doc /* The Airport Duty Manager shall review late airport-driven changes that affected multiple flights and shall record whether the operational justification was valid. @S809 */ subject s : AirportDutyManager; }
    requirement def R75 { doc /* Findings from the review shall feed adjustments to tolerance values, reason code definitions, and training material, subject to change control. @S810 */ subject s : FindingsFromTheReview; }
    requirement def R76 { doc /* All audit outputs shall be retained according to the approved records schedule and shall remain searchable for compliance investigations, performance meetings, and lessons-learned activity. @S811 */ subject s : AuditOutputs; }
    requirement def R77 { doc /* Data governance for the Regional Flow Platform shall assign accountable owners to each operational data domain and shall make those assignments visible in the Airport CDM Portal. @S812 */ subject s : RegionalFlowPlatform; }
    requirement def R78 { doc /* The Data Governance Steward shall maintain the data ownership register and shall coordinate updates through the Business Rules Registry. @S813 */ subject s : DataGovernanceSteward; }
    requirement def R79 { doc /* The Regional Flow Manager shall own flow management policy data, including Ground Delay Program parameters and Tactical Regulation Proposal status values. @S814 */ subject s : RegionalFlowManager; }
    requirement def R80 { doc /* The Slot Coordinator shall own slot allocation reference data, including Calculated Takeoff Time tolerances and Slot Compliance State definitions. @S815 */ subject s : SlotCoordinator; }
    requirement def R81 { doc /* The Airport Duty Manager shall own airport capacity declarations, including Airport Capacity Plan records and Airport Acceptance Rate values. @S816 */ subject s : AirportDutyManager; }
    requirement def R82 { doc /* The Tower Supervisor shall own tower sequence status data maintained for the Tower Sequence Manager. @S817 */ subject s : TowerSupervisor; }
    requirement def R83 { doc /* The Ramp Control Lead shall own ramp movement status data maintained for the Ramp Movement Board. @S818 */ subject s : RampControlLead; }
    requirement def R84 { doc /* The Meteorology Briefing Officer shall own operational weather classification inputs accepted by the Weather Ingest Gateway. @S819 */ subject s : MeteorologyBriefingOfficer; }
    requirement def R85 { doc /* The Airline Operations Coordinator shall be accountable for airline-supplied schedule intent, readiness status, and Target Off Block Time updates submitted through approved interfaces. @S820 */ subject s : AirlineOperationsCoordinator; }
    requirement def R86 { doc /* Freshness indicators shall be displayed on the Common Situation Display wherever stale data could affect sequencing, metering, regulation, or resource allocation decisions. @S822 */ subject s : CommonSituationDisplay; }
    requirement def R87 { doc /* The freshness indicator shall include the time of last accepted update, the maximum permitted age, and a visual state that distinguishes current, aging, stale, and unavailable data. @S823 */ subject s : FreshnessIndicator; }
    requirement def R88 { doc /* The Time Synchronization Service shall provide the common time basis used for freshness calculations across the Regional Flow Platform. @S824 */ subject s : TimeSynchronizationService; }
    requirement def R89 { doc /* The Demand Prediction Service, Capacity Assessment Module, Slot Allocation Engine, and Departure Metering Service shall reject data that lacks a trusted timestamp. @S825 */ subject s : DemandPredictionService; }
    requirement def R90 { doc /* The Flight Data Exchange shall validate Flight Intent Message content before the data is made available for operational use. @S827 */ subject s : FlightDataExchange; }
    requirement def R91 { doc /* The Surface Surveillance Adapter shall apply position quality checks and shall mark uncertain observations before they are used by surface decision functions. @S828 */ subject s : SurfaceSurveillanceAdapter; }
    requirement def R92 { doc /* The Airline Interface Adapter shall apply carrier-specific format checks while preserving the common operational meaning required by the Regional Flow Platform. @S829 */ subject s : AirlineInterfaceAdapter; }
    requirement def R93 { doc /* The Handling Resource Planner shall validate resource quantities, task timing, and allocation identifiers against active operational reference data. @S830 */ subject s : HandlingResourcePlanner; }
    requirement def R94 { doc /* The Business Rules Registry shall hold the current validation thresholds, allowable reason codes, and exception rules approved for Normal Operations, Adverse Weather Mode, Capacity Reduction State, Recovery Phase, and Contingency Fallback State. @S831 */ subject s : BusinessRulesRegistry; }
    requirement def R95 { doc /* The Data Governance Steward shall coordinate discrepancy resolution with the responsible operational owner and shall record the disposition in the Audit Event Ledger. @S833 */ subject s : DataGovernanceSteward; }
    requirement def R96 { doc /* Urgent discrepancies that could change a metering, arrival regulation, or slot allocation decision shall be raised through the Alert Distribution Hub and reviewed in the Digital Briefing Room. @S834 */ subject s : AlertDistributionHub; }
    requirement def R97 { doc /* The System Support Engineer shall investigate technical causes of missing, delayed, duplicated, or transformed records and shall provide evidence needed for stewardship decisions. @S835 */ subject s : SystemSupportEngineer; }
    requirement def R98 { doc /* The Performance Analytics Warehouse shall retain data quality measures, including validation failure rates, freshness breaches, manual corrections, and recurring ownership conflicts. @S836 */ subject s : PerformanceAnalyticsWarehouse; }
    requirement def R99 { doc /* Performance measurement for the Meridian Regional Air Traffic Flow Management and Airport Collaborative Decision-Making System shall convert operational events into repeatable indicators that can be reviewed after each operating day. @S838 */ subject s : MeridianRegionalAirTrafficFlowManagementAndAirportCollaborativeDecisionMakingSystem; }
    requirement def R100 { doc /* The Performance Analytics Warehouse shall calculate delay absorption as the portion of expected airborne or terminal-area delay that is converted into controlled ground delay before departure. @S839 */ subject s : PerformanceAnalyticsWarehouse; }
    requirement def R101 { doc /* Delay absorption shall be measured by comparing the unconstrained demand predicted by the Demand Prediction Service with the regulated demand produced by the Slot Allocation Engine and the realized movement times captured through the Flight Data Exchange. @S840 */ subject s : PerformanceAnalyticsWarehouse; }
    requirement def R102 { doc /* The principal delay absorption indicator shall report minutes absorbed at origin, minutes remaining in the arrival stream, and minutes transferred to surface queues within the region. @S841 */ subject s : DelayAbsorptionIndicator; }
    requirement def R103 { doc /* The Regional Flow Manager shall use this indicator to verify that a Ground Delay Program reduced airborne holding without creating excessive departure congestion at constrained airports. @S842 */ subject s : RegionalFlowManager; }
    requirement def R104 { doc /* The Tower Sequence Manager shall provide runway sequence counts @S844 */ subject s : TowerSequenceManager; }
    requirement def R105 { doc /* the Ramp Movement Board shall provide surface queue counts based on movement status and surveillance confirmation. @S844 */ subject s : RampMovementBoard; }
    requirement def R106 { doc /* The North Runway Meter, South Runway Meter, East Apron Sensor, and West Apron Sensor shall support independent checks of queue length where surveillance coverage is available. @S845 */ subject s : NorthRunwayMeter; }
    requirement def R107 { doc /* The North Runway Meter, South Runway Meter, East Apron Sensor, and West Apron Sensor shall support independent checks of queue length where surveillance coverage is available. @S845 */ subject s : SouthRunwayMeter; }
    requirement def R108 { doc /* The North Runway Meter, South Runway Meter, East Apron Sensor, and West Apron Sensor shall support independent checks of queue length where surveillance coverage is available. @S845 */ subject s : EastApronSensor; }
    requirement def R109 { doc /* The North Runway Meter, South Runway Meter, East Apron Sensor, and West Apron Sensor shall support independent checks of queue length where surveillance coverage is available. @S845 */ subject s : WestApronSensor; }
    requirement def R110 { doc /* The Slot Coordinator shall review slot adherence by operator, airport, time band, and regulation identifier to detect recurring causes of noncompliance. @S848 */ subject s : SlotCoordinator; }
    requirement def R111 { doc /* The Slot Compliance State shall be used to identify periods when adherence monitoring has operational priority over advisory optimization. @S850 */ subject s : SlotComplianceState; }
    requirement def R112 { doc /* The Capacity Assessment Module shall record the available Airport Acceptance Rate used in each baseline so that avoided cancellation estimates remain traceable. @S853 */ subject s : CapacityAssessmentModule; }
    requirement def R113 { doc /* The Airline Operations Coordinator and Aircraft Operator Representative shall be able to challenge cancellation avoidance results through the Collaborative Decision Log when local business decisions affected the outcome. @S854 */ subject s : AirlineOperationsCoordinator; }
    requirement def R114 { doc /* The Airline Operations Coordinator and Aircraft Operator Representative shall be able to challenge cancellation avoidance results through the Collaborative Decision Log when local business decisions affected the outcome. @S854 */ subject s : AircraftOperatorRepresentative; }
    requirement def R115 { doc /* The Performance Analytics Warehouse shall apply approved fuel burn and emissions factors by aircraft category, operating phase, and delay location. @S856 */ subject s : PerformanceAnalyticsWarehouse; }
    requirement def R116 { doc /* The Meteorology Briefing Officer shall support interpretation of emissions results by identifying periods when weather routing or convective avoidance dominated fuel performance. @S858 */ subject s : MeteorologyBriefingOfficer; }
    requirement def R117 { doc /* The Airport Duty Manager shall receive benefit summaries that show changes in stand occupancy, surface congestion, recovery duration, and passenger-facing disruption indicators. @S860 */ subject s : AirportDutyManager; }
    requirement def R118 { doc /* The Data Governance Steward shall ensure that published performance measures identify data sources, calculation versions, confidence limits, and known exclusions. @S861 */ subject s : DataGovernanceSteward; }
    requirement def R119 { doc /* The Post Operations Report shall present regional benefits alongside operational trade-offs so that decision makers can see whether delay, queue, slot, cancellation, and emissions objectives were balanced in practice. @S862 */ subject s : PostOperationsReport; }
    requirement def R120 { doc /* Training for the Meridian Regional Air Traffic Flow Management and Airport Collaborative Decision-Making System shall be role based and shall cover normal coordination, constrained operations, recovery actions, and degraded system use. @S863 */ subject s : MeridianRegionalAirTrafficFlowManagementAndAirportCollaborativeDecisionMakingSystem; }
    requirement def R121 { doc /* The Regional Flow Manager shall receive advanced instruction on interpreting demand and capacity information, leading collaborative decisions, and authorizing operational measures in the Regional Flow Platform. @S864 */ subject s : RegionalFlowManager; }
    requirement def R122 { doc /* Air traffic controllers shall be trained to understand how flow measures, sequencing changes, and calculated times affect sector workload, runway demand, and controller tactical flexibility. @S865 */ subject s : AirTrafficControllers; }
    requirement def R123 { doc /* The Tower Supervisor shall receive practical training on the Tower Sequence Manager, Departure Metering Service, Arrival Regulation Console, North Runway Meter, and South Runway Meter. @S866 */ subject s : TowerSupervisor; }
    requirement def R124 { doc /* Ramp personnel shall be trained under the direction of the Ramp Control Lead to use the Ramp Movement Board without substituting system indications for required visual checks, radio coordination, and local safety procedures. @S867 */ subject s : RampPersonnel; }
    requirement def R125 { doc /* The Airline Operations Coordinator and Aircraft Operator Representative shall be trained to submit, review, and update Flight Intent Message data through approved interfaces and to assess the operational effect of Calculated Takeoff Time and Target Off Block Time changes. @S868 */ subject s : AirlineOperationsCoordinator; }
    requirement def R126 { doc /* The Airline Operations Coordinator and Aircraft Operator Representative shall be trained to submit, review, and update Flight Intent Message data through approved interfaces and to assess the operational effect of Calculated Takeoff Time and Target Off Block Time changes. @S868 */ subject s : AircraftOperatorRepresentative; }
    requirement def R127 { doc /* Ground handling personnel shall be trained by the Ground Handling Dispatcher on the Handling Resource Planner and on procedures for confirming that resource constraints are represented accurately before they influence collaborative decisions. @S869 */ subject s : GroundHandlingPersonnel; }
    requirement def R128 { doc /* The Slot Coordinator shall receive training on the Slot Allocation Engine, Airport CDM Portal, and applicable Business Rules Registry entries so that slot actions are applied consistently and transparently. @S870 */ subject s : SlotCoordinator; }
    requirement def R129 { doc /* The Network Operations Liaison and Airspace Sector Planner shall be trained to coordinate regional constraints, sector load conditions, and network measures using the Sector Load Monitor and Common Situation Display. @S871 */ subject s : NetworkOperationsLiaison; }
    requirement def R130 { doc /* The Network Operations Liaison and Airspace Sector Planner shall be trained to coordinate regional constraints, sector load conditions, and network measures using the Sector Load Monitor and Common Situation Display. @S871 */ subject s : AirspaceSectorPlanner; }
    requirement def R131 { doc /* The Airport Duty Manager shall be trained to recognize when an Airport Capacity Plan requires revision and when the operational state should move from Normal Operations to Adverse Weather Mode or Capacity Reduction State. @S872 */ subject s : AirportDutyManager; }
    requirement def R132 { doc /* The Meteorology Briefing Officer shall be trained to explain weather uncertainty in operational terms and to verify that the Weather Ingest Gateway supports the assumptions used during briefings. @S873 */ subject s : MeteorologyBriefingOfficer; }
    requirement def R133 { doc /* The Emergency Response Coordinator shall participate in recurrent training so that emergency priorities are integrated into flow management decisions without obscuring command authority or safety responsibilities. @S874 */ subject s : EmergencyResponseCoordinator; }
    requirement def R134 { doc /* The Deicing Coordinator shall receive seasonal refresher training on how deicing capacity assumptions are represented in demand and departure metering tools. @S875 */ subject s : DeicingCoordinator; }
    requirement def R135 { doc /* The Data Governance Steward shall train operational users on data quality responsibilities, privacy expectations, and the correct interpretation of audit records in the Audit Event Ledger. @S876 */ subject s : DataGovernanceSteward; }
    requirement def R136 { doc /* The System Support Engineer shall train superusers on service status checks, access fault escalation, and safe use of the Contingency Operations Console during partial outages. @S877 */ subject s : SystemSupportEngineer; }
    requirement def R137 { doc /* Initial training shall include classroom instruction, supervised workstation practice, scenario walkthroughs in the Digital Briefing Room, and observed operational shadowing before independent system use is authorized. @S878 */ subject s : InitialTraining; }
    requirement def R138 { doc /* Recurrent training shall be required at least annually and after major changes to the Regional Flow Platform, Demand Prediction Service, Capacity Assessment Module, or Flight Data Exchange. @S879 */ subject s : RecurrentTraining; }
    requirement def R139 { doc /* Simulation exercises shall use realistic traffic samples, weather constraints, surface congestion, airline schedule pressure, handling resource shortages, and recovery objectives to test coordinated decision making. @S880 */ subject s : SimulationExercises; }
    requirement def R140 { doc /* Each exercise shall include participants from tower, ramp, airline operations, handling, airport operations, network coordination, meteorology, data governance, and system support functions when those functions are relevant to the scenario. @S881 */ subject s : Exercise; }
    requirement def R141 { doc /* Exercises shall cover transitions among Normal Operations, Adverse Weather Mode, Capacity Reduction State, Recovery Phase, Contingency Fallback State, and Slot Compliance State. @S882 */ subject s : Exercise; }
    requirement def R142 { doc /* Simulation events shall require users to compare automated recommendations with local knowledge, document significant decisions in the Collaborative Decision Log, and explain departures from system proposals. @S883 */ subject s : SimulationEvents; }
    requirement def R143 { doc /* Human factors safeguards shall include workload monitoring, clear alert prioritization, consistent terminology, confirmation steps for high impact actions, and protection against silent mode changes. @S884 */ subject s : HumanFactorsSafeguards; }
    requirement def R144 { doc /* Workstation layouts shall support rapid comparison between the Common Situation Display, Airport CDM Portal, Tower Sequence Manager, Ramp Movement Board, and relevant advisory messages without forcing users to copy critical values manually. @S885 */ subject s : WorkstationLayouts; }
    requirement def R145 { doc /* Training assessments shall verify that users can identify stale data, time synchronization problems, duplicate flights, conflicting constraints, and inappropriate automation reliance before such issues affect live operations. @S886 */ subject s : TrainingAssessments; }
    requirement def R146 { doc /* Post-exercise reviews shall use evidence from the Performance Analytics Warehouse and Audit Event Ledger to improve procedures, refine training materials, and confirm that human performance concerns are assigned to accountable owners. @S887 */ subject s : PostExerciseReviews; }
    requirement def R147 { doc /* Deployment of the Regional Flow Platform shall proceed through phased increments that limit operational exposure while progressively adding airports, interfaces, and decision support functions. @S888 */ subject s : RegionalFlowPlatform; }
    requirement def R148 { doc /* The first increment shall establish the core operational baseline for the Regional Flow Manager, Network Operations Liaison, Data Governance Steward, and System Support Engineer in a controlled production environment. @S889 */ subject s : FirstIncrement; }
    requirement def R149 { doc /* This baseline shall include the Identity Access Service, Time Synchronization Service, Audit Event Ledger, Performance Analytics Warehouse, and Business Rules Registry before any airport is permitted to exchange operational data. @S890 */ subject s : CoreOperationalBaseline; }
    requirement def R150 { doc /* Pilot airport selection shall favor locations with stable operational leadership, representative traffic complexity, available surface surveillance data, and demonstrated willingness to participate in joint procedure development. @S891 */ subject s : PilotAirportSelection; }
    requirement def R151 { doc /* The initial pilot shall include one constrained primary airport and one less constrained regional airport so that both high-demand and routine operating patterns are exercised. @S892 */ subject s : InitialPilot; }
    requirement def R152 { doc /* Each candidate airport shall provide evidence that the Airport Duty Manager, Tower Supervisor, Ramp Control Lead, Airline Operations Coordinator, Ground Handling Dispatcher, and Aircraft Operator Representative have named accountable implementation contacts. @S893 */ subject s : CandidateAirport; }
    requirement def R153 { doc /* Readiness Gate 1 shall confirm that governance, security approvals, user role definitions, operating hours, and support escalation paths are documented and accepted by local stakeholders. @S894 */ subject s : ReadinessGate1; }
    requirement def R154 { doc /* Readiness Gate 2 shall confirm that the Flight Data Exchange, Airline Interface Adapter, Surface Surveillance Adapter, and Weather Ingest Gateway can be connected without disrupting existing airport operations. @S895 */ subject s : ReadinessGate2; }
    requirement def R155 { doc /* Readiness Gate 3 shall confirm that local procedures have been mapped to the Airport CDM Portal, Tower Sequence Manager, Ramp Movement Board, Departure Metering Service, and Arrival Regulation Console. @S896 */ subject s : ReadinessGate3; }
    requirement def R156 { doc /* Readiness Gate 4 shall confirm that training, shadow operations, contingency procedures, and operational acceptance criteria have been completed before live collaborative decisions are made through the Regional Flow Platform. @S897 */ subject s : ReadinessGate4; }
    requirement def R157 { doc /* Interface certification shall be performed separately from operational acceptance so that technical conformance defects do not become unresolved procedural issues. @S898 */ subject s : Interface; }
    requirement def R158 { doc /* Each interface shall be tested for message structure, time stamping, identity attribution, replay handling, duplicate detection, outage recovery, and rejection behavior under degraded network conditions. @S899 */ subject s : Interface; }
    requirement def R159 { doc /* The Demand Prediction Service, Capacity Assessment Module, Slot Allocation Engine, Gate Conflict Detector, Sector Load Monitor, North Runway Meter, and South Runway Meter shall be certified against agreed reference scenarios before they are used for operational recommendations. @S900 */ subject s : DemandPredictionService; }
    requirement def R160 { doc /* Certification results shall be recorded in the Collaborative Decision Log when they affect operational procedures and in the Audit Event Ledger when they affect access, configuration, or transaction traceability. @S901 */ subject s : CollaborativeDecisionLog; }
    requirement def R161 { doc /* Airport onboarding shall start with data discovery workshops that identify local tools, manual workarounds, unofficial spreadsheets, and locally maintained constraint registers. @S902 */ subject s : AirportOnboarding; }
    requirement def R162 { doc /* The migration plan shall classify each local tool as retired, retained for read-only reference, integrated through an approved interface, or replaced by a Regional Flow Platform function. @S903 */ subject s : MigrationPlan; }
    requirement def R163 { doc /* No local tool shall be retired until the responsible operational owner verifies that its essential decisions, timing assumptions, and audit needs are supported in the target process. @S904 */ subject s : LocalTool; }
    requirement def R164 { doc /* During shadow operations, local tools shall remain the authoritative source while the Regional Flow Platform produces parallel outputs for comparison by operational users. @S905 */ subject s : LocalTool; }
    requirement def R165 { doc /* The cutover decision shall be based on measured agreement between local practice and Regional Flow Platform outputs, user confidence, defect closure, and demonstrated recovery from simulated failures. @S906 */ subject s : RegionalFlowPlatform; }
    requirement def R166 { doc /* After cutover, local users shall enter operational decisions through the Airport CDM Portal and shall avoid reintroducing uncontrolled parallel records that undermine common situational awareness. @S907 */ subject s : LocalUsers; }
    requirement def R167 { doc /* The Contingency Operations Console shall be available at each onboarded airport before reliance on the Regional Flow Platform is declared for Normal Operations, Adverse Weather Mode, Capacity Reduction State, Recovery Phase, or Contingency Fallback State. @S908 */ subject s : ContingencyOperationsConsole; }
    requirement def R168 { doc /* Expansion beyond the pilot airports shall occur in waves that group airports by interface maturity, traffic dependency, stakeholder readiness, and available support capacity. @S909 */ subject s : MeridianRegionalATFMACDMSystem; }
    requirement def R169 { doc /* Each onboarding wave shall include a stabilization period in which the System Support Engineer and Data Governance Steward monitor defect trends, data quality, access changes, and user adoption. @S910 */ subject s : MeridianRegionalATFMACDMSystem; }
    requirement def R170 { doc /* Full regional deployment shall be declared only after the Regional Flow Manager confirms that operational benefits, safety constraints, cyber controls, and stakeholder obligations remain stable across multiple airports and traffic conditions. @S911 */ subject s : MeridianRegionalATFMACDMSystem; }
    requirement def R171 { doc /* Operational service management for the Regional Flow Platform shall begin when a deployed airport is accepted into steady state support after the regional stabilization period. @S912 */ subject s : RegionalFlowPlatform; }
    requirement def R172 { doc /* The service model shall distinguish continuous operational support from planned engineering support so that safety related traffic flow functions remain protected at all times. @S913 */ subject s : MeridianRegionalATFMACDMSystem; }
    requirement def R173 { doc /* The System Support Engineer shall provide round the clock on call coverage for production incidents affecting the Regional Flow Platform, Airport CDM Portal, Slot Allocation Engine, Departure Metering Service, Arrival Regulation Console, and Alert Distribution Hub. @S914 */ subject s : SystemSupportEngineer; }
    requirement def R174 { doc /* Standard service desk coverage for access requests, reporting questions, configuration inquiries, and minor usability issues shall be available during normal regional administrative hours on business days. @S915 */ subject s : MeridianRegionalATFMACDMSystem; }
    requirement def R175 { doc /* During published peak traffic periods, Adverse Weather Mode, Capacity Reduction State, and Recovery Phase, the on call support posture shall be raised so that the System Support Engineer can join the Digital Briefing Room without delay. @S916 */ subject s : SystemSupportEngineer; }
    requirement def R176 { doc /* The Regional Flow Manager, Tower Supervisor, Ramp Control Lead, Airport Duty Manager, and Network Operations Liaison shall retain operational command authority during support activity. @S917 */ subject s : RegionalFlowManager; }
    requirement def R177 { doc /* The System Support Engineer shall advise operational supervisors on technical status, known workarounds, data integrity concerns, and recovery options, but shall not issue traffic management instructions. @S918 */ subject s : SystemSupportEngineer; }
    requirement def R178 { doc /* Incidents shall be classified by operational effect, with the highest priority assigned to loss of common situational awareness, loss of slot computation, corruption of operational timing data, or failure of alert distribution during active traffic management. @S919 */ subject s : MeridianRegionalATFMACDMSystem; }
    requirement def R179 { doc /* A critical incident shall be acknowledged within fifteen minutes and shall have continuous technical ownership until service is restored or an agreed operational workaround is in place. @S920 */ subject s : SystemSupportEngineer; }
    requirement def R180 { doc /* A high priority incident that degrades a major function without stopping tactical coordination shall be acknowledged within thirty minutes and shall be reviewed with the affected operational supervisor at least hourly. @S921 */ subject s : SystemSupportEngineer; }
    requirement def R181 { doc /* Medium and low priority incidents shall be handled through the service queue, with target updates provided at intervals appropriate to their operational impact and planned resolution path. @S922 */ subject s : MeridianRegionalATFMACDMSystem; }
    requirement def R182 { doc /* The System Support Engineer shall maintain an incident record that captures the initial symptom, affected components, operational state, timeline, mitigation actions, data corrections, and supervisor decisions. @S923 */ subject s : SystemSupportEngineer; }
    requirement def R183 { doc /* Incident records shall reference the Audit Event Ledger where user actions, configuration changes, interface events, or automated decisions are relevant to the investigation. @S924 */ subject s : IncidentRecord; }
    requirement def R184 { doc /* The Collaborative Decision Log shall be used to preserve the operational context of major incidents when traffic management decisions are made while a technical degradation is present. @S925 */ subject s : CollaborativeDecisionLog; }
    requirement def R185 { doc /* The System Support Engineer shall verify that fallback tools, exported operational data, and restoration checkpoints are available before advising that normal technical service can resume. @S927 */ subject s : SystemSupportEngineer; }
    requirement def R186 { doc /* Future enhancement of the Regional Flow Platform should be treated as an incremental extension of the operational service rather than as a replacement of the current concept. @S936 */ subject s : RegionalFlowPlatform; }
    requirement def R187 { doc /* Cross-border exchange should use standardized message structures where practical @S939 */ subject s : MeridianRegionalATFMACDMSystem; }
    requirement def R188 { doc /* the Business Rules Registry should retain the local parameters needed for Meridian operations @S939 */ subject s : BusinessRulesRegistry; }
    requirement def R189 { doc /* The Flight Data Exchange should be enhanced to accept richer intent data, including improved route options, expected cruise profiles, and updated departure readiness information @S940 */ subject s : FlightDataExchange; }
    requirement def R190 { doc /* The Demand Prediction Service should use this data to create more stable demand pictures across longer planning horizons while still preserving tactical responsiveness @S941 */ subject s : DemandPredictionService; }
    requirement def R191 { doc /* Trajectory prediction should also make greater use of weather features, sector configuration, runway direction, and surface movement status when estimating flight progress @S942 */ subject s : DemandPredictionService; }
    requirement def R192 { doc /* The Weather Ingest Gateway and Sector Load Monitor should provide the common inputs needed to connect airspace capacity and airport capacity in the same prediction cycle @S943 */ subject s : WeatherIngestGateway; }
    requirement def R193 { doc /* The Capacity Assessment Module should evolve from a mainly rules-based assessment into a service that can compare planned capacity, observed throughput, and predicted constraint persistence @S944 */ subject s : CapacityAssessmentModule; }
    requirement def R194 { doc /* Any use of learning models should be introduced with explainability requirements @S945 */ subject s : MeridianRegionalATFMACDMSystem; }
    requirement def R195 { doc /* Advanced turnaround prediction should combine aircraft state, handling milestones, stand occupancy, crew readiness, passenger processing, and ramp congestion signals @S946 */ subject s : MeridianRegionalATFMACDMSystem; }
    requirement def R196 { doc /* The Airport CDM Portal, Airline Interface Adapter, Handling Resource Planner, and Ramp Movement Board should provide the main operational inputs for this capability @S947 */ subject s : AirportCDMPortal; }
    requirement def R197 { doc /* Predicted changes to Target Off Block Time should be presented with confidence levels rather than as unconditional system corrections @S948 */ subject s : MeridianRegionalATFMACDMSystem; }
    requirement def R198 { doc /* The Slot Allocation Engine should use improved turnaround predictions to protect feasible Calculated Takeoff Time assignments and to reduce avoidable re-sequencing @S949 */ subject s : SlotAllocationEngine; }
    requirement def R199 { doc /* The Tower Sequence Manager and Departure Metering Service should receive only the information needed for tactical sequencing, with detailed airline operational data controlled by policy @S950 */ subject s : TowerSequenceManager; }
    requirement def R200 { doc /* Machine-assisted recovery options should support the Recovery Phase by proposing coordinated actions that balance runway throughput, sector loading, stand availability, and airline priorities @S951 */ subject s : MeridianRegionalATFMACDMSystem; }
    requirement def R201 { doc /* These options should be generated by the Contingency Operations Console and reviewed through the Common Situation Display before any operational decision is applied @S952 */ subject s : ContingencyOperationsConsole; }
    requirement def R202 { doc /* The system should not automatically impose a Ground Delay Program, change an Airport Acceptance Rate, or alter a tactical measure without authorized human confirmation @S953 */ subject s : MeridianRegionalATFMACDMSystem; }
    requirement def R203 { doc /* Recovery recommendations should include the operational rationale, expected benefit, key assumptions, and possible secondary effects on connected flights and surface movements. @S954 */ subject s : RecoveryRecommendations; }
    requirement def R204 { doc /* The Collaborative Decision Log and Audit Event Ledger should record each proposed option, the user response, and the final decision so that performance can be reviewed after operations. @S955 */ subject s : CollaborativeDecisionLog; }
    requirement def R205 { doc /* The Collaborative Decision Log and Audit Event Ledger should record each proposed option, the user response, and the final decision so that performance can be reviewed after operations. @S955 */ subject s : AuditEventLedger; }
    requirement def R206 { doc /* Regional expansion should include a repeatable onboarding pattern for new airports, airspace sectors, airlines, and handling organizations. @S956 */ subject s : RegionalExpansion; }
    requirement def R207 { doc /* The Identity Access Service, Time Synchronization Service, and Performance Analytics Warehouse should be scaled early because they form shared foundations for a wider regional deployment. @S957 */ subject s : IdentityAccessService; }
    requirement def R208 { doc /* The Identity Access Service, Time Synchronization Service, and Performance Analytics Warehouse should be scaled early because they form shared foundations for a wider regional deployment. @S957 */ subject s : TimeSynchronizationService; }
    requirement def R209 { doc /* The Identity Access Service, Time Synchronization Service, and Performance Analytics Warehouse should be scaled early because they form shared foundations for a wider regional deployment. @S957 */ subject s : PerformanceAnalyticsWarehouse; }
    requirement def R210 { doc /* Data governance should remain under the Data Governance Steward, with clear rules for retention, consent, quality thresholds, and permitted operational use. @S958 */ subject s : DataGovernanceSteward; }
    requirement def R211 { doc /* Future releases should be validated in shadow mode before operational activation so that the Regional Flow Manager, Airline Operations Coordinator, Tower Supervisor, and Airport Duty Manager can compare recommendations with actual outcomes. @S959 */ subject s : FutureReleases; }
    requirement def R212 { doc /* Sustained regional ATFM and A-CDM operation requires each participating organization to treat the operating picture as a shared operational asset rather than a local advisory product. @S960 */ subject s : ParticipatingOrganization; }
    requirement def R213 { doc /* should be kept consistent with the Regional Flow Platform and Airport CDM Portal @S974 */ subject s : CommonSituationDisplay; }
    requirement def R214 { doc /* Calculated Takeoff Time and Target Off Block Time commitments should be treated as executable operating constraints unless they are revised through the agreed coordination process @S976 */ subject s : CalculatedTakeoffTime; }
    requirement def R215 { doc /* Ground Delay Program decisions, Tactical Regulation Proposal review, and Airport Acceptance Rate changes should be visible to affected participants before they are applied whenever operational time permits @S977 */ subject s : GroundDelayProgram; }
    requirement def R216 { doc /* must be operated with monitored data quality thresholds and clear fallback procedures @S979 */ subject s : FlightDataExchange; }
    requirement def R217 { doc /* must be operated with monitored data quality thresholds and clear fallback procedures @S979 */ subject s : AirlineInterfaceAdapter; }
    requirement def R218 { doc /* must be operated with monitored data quality thresholds and clear fallback procedures @S979 */ subject s : SurfaceSurveillanceAdapter; }
    requirement def R219 { doc /* must be operated with monitored data quality thresholds and clear fallback procedures @S979 */ subject s : WeatherIngestGateway; }
    requirement def R220 { doc /* must use the approved rules recorded in the Business Rules Registry @S980 */ subject s : SlotAllocationEngine; }
    requirement def R221 { doc /* must use the approved rules recorded in the Business Rules Registry @S980 */ subject s : DepartureMeteringService; }
    requirement def R222 { doc /* must use the approved rules recorded in the Business Rules Registry @S980 */ subject s : ArrivalRegulationConsole; }
    requirement def R223 { doc /* must use the approved rules recorded in the Business Rules Registry @S980 */ subject s : TowerSequenceManager; }
    requirement def R224 { doc /* must use the approved rules recorded in the Business Rules Registry @S980 */ subject s : RampMovementBoard; }
    requirement def R225 { doc /* must support traceability, least-privilege access, and after-action accountability for all operationally significant changes @S981 */ subject s : IdentityAccessService; }
    requirement def R226 { doc /* must support traceability, least-privilege access, and after-action accountability for all operationally significant changes @S981 */ subject s : AuditEventLedger; }
    requirement def R227 { doc /* should be used to measure compliance, delay outcomes, capacity use, and the effectiveness of collaborative decisions @S982 */ subject s : PerformanceAnalyticsWarehouse; }
    requirement def R228 { doc /* should be used to measure compliance, delay outcomes, capacity use, and the effectiveness of collaborative decisions @S982 */ subject s : PostOperationsReport; }
}
