package L2Model {
    item def AcceptedIntentDataItem { doc /* @S128 */ }
    item def AcceptedOrRejectedExemptionItem { doc /* @S239 */ }
    item def AcceptedSlotAdjustmentsRejectedSlotAdjustmentsAndUnresolvedSlotConflictsItem { doc /* @S161 */ }
    item def AcknowledgementsItem { doc /* @S405 */ }
    item def ActiveRestrictionStatusExpectedOperationalEffectAndRelatedCoordinationNotesItem { doc /* @S337 */ }
    item def ActiveSpacingRulesItem { doc /* @S297,S404 */ }
    item def ActiveSurfaceAdvisoriesItem { doc /* @S462 */ }
    item def AffectedRunwayQueueItem { doc /* @S366 */ }
    item def AgreedTargetOffBlockTimeValuesAndStakeholderRemarksItem { doc /* @S429 */ }
    item def AirlineIntegrationTransactionsItem { doc /* @S149 */ }
    item def AirportCapacityPlanItem { doc /* @S078,S107,S132,S252,S349,S374,S493,S697,S721 */ }
    item def AirspaceAlertAcknowledgementAndDownstreamDecisionItem { doc /* @S333 */ }
    item def AlertItem { doc /* @S093,S210 */ }
    item def ApronSweepCompletionNoteItem { doc /* @S678 */ }
    item def ArrivalPlanItem { doc /* @S405 */ }
    item def AuthenticatedRoleItem { doc /* @S793 */ }
    item def BaseMapTimelineFlightListAndMeasureStatusPanelsItem { doc /* @S421 */ }
    item def BoardingLoadingDoorClosureAndTowReadinessMilestonesItem { doc /* @S292 */ }
    item def BusinessRulesRegistryParametersItem { doc /* @S080 */ }
    item def CalculatedTakeoffTimeAndTargetOffBlockTimeItem { doc /* @S161,S259,S369,S625,S886 */ }
    item def CandidatePushbackSpacingItem { doc /* @S456 */ }
    item def CapacityChangeNotificationItem { doc /* @S121 */ }
    item def CombinedTacticalViewItem { doc /* @S420 */ }
    item def CommonTimeBasisItem { doc /* @S824 */ }
    item def ConcurrenceItem { doc /* @S673 */ }
    item def ConditionItem { doc /* @S218 */ }
    item def ConditionsItem { doc /* @S175 */ }
    item def ConstraintItem { doc /* @S318,S508,S705 */ }
    item def ConstraintsItem { doc /* @S135,S145,S213,S225,S625 */ }
    item def CrewBusDelaySlipItem { doc /* @S237 */ }
    item def CrewDutyExtensionLogItem { doc /* @S726 */ }
    item def CrewLegalityImpactsItem { doc /* @S627 */ }
    item def CrewLegalityInputsItem { doc /* @S622 */ }
    item def CurrentAgreedTargetSetItem { doc /* @S265 */ }
    item def CurrentAirlineIntentsItem { doc /* @S131 */ }
    item def CurrentMovementAreaOccupancyAndEquipmentStatusIndicatorsItem { doc /* @S445 */ }
    item def CurrentOperatingBasisItem { doc /* @S734 */ }
    item def CurrentOperatingScheduleItem { doc /* @S103 */ }
    item def CurrentRampIntentItem { doc /* @S217 */ }
    item def CustomsHoldReleaseNoteItem { doc /* @S679 */ }
    item def DataItem { doc /* @S086 */ }
    item def DataQualityMeasuresItem { doc /* @S837 */ }
    item def DecisionsAndUnresolvedIssuesItem { doc /* @S099 */ }
    item def DeicingPadQueueCardItem { doc /* @S378 */ }
    item def DemandItem { doc /* @S132,S225,S329,S351 */ }
    item def DemandForecastItem { doc /* @S101 */ }
    item def DemandProjectionsItem { doc /* @S107 */ }
    item def DepartureFixLoadSheetItem { doc /* @S598 */ }
    item def DispositionItem { doc /* @S833 */ }
    item def DiversionRationalePriorityClassificationResourceCommitmentAndAgreedRecoveryTargetItem { doc /* @S506 */ }
    item def DutyDeskConfirmationsItem { doc /* @S185 */ }
    item def EvidenceItem { doc /* @S887 */ }
    item def ExceptionItem { doc /* @S671 */ }
    item def ExpectedServiceCompletionTimesItem { doc /* @S302 */ }
    item def ExternalCoordinationOutcomesItem { doc /* @S084 */ }
    item def FeasibilityResultAndTimingBoundaryItem { doc /* @S626 */ }
    item def FiledFlightInformationItem { doc /* @S103 */ }
    item def FlightIntentMessageItem { doc /* @S126 */ }
    item def ForecastConfidenceTimingRiskAndExpectedOperationalImpactItem { doc /* @S086 */ }
    item def ForecastDemandAssessedCapacityAndActiveGroundDelayProgramEffectsItem { doc /* @S117 */ }
    item def FreezeHorizonItem { doc /* @S800 */ }
    item def FuelTruckHoldAdviceItem { doc /* @S450 */ }
    item def GateReopeningMemoItem { doc /* @S472 */ }
    item def GroundDelayProgramItem { doc /* @S078,S398,S745 */ }
    item def HandlingResourcePlannerViewItem { doc /* @S438 */ }
    item def IndicationsItem { doc /* @S205 */ }
    item def InformationItem { doc /* @S063 */ }
    item def InfrastructureEventsItem { doc /* @S712 */ }
    item def InputsItem { doc /* @S204 */ }
    item def LateBaggageTagListItem { doc /* @S519 */ }
    item def LoggedRationaleItem { doc /* @S760 */ }
    item def MachineAssistedRecoveryOptionsItem { doc /* @S952 */ }
    item def MandatoryFieldsPermissibleStatusValuesRetentionRulesAndDataQualityThresholdsItem { doc /* @S170 */ }
    item def MaterialDeviationsItem { doc /* @S091 */ }
    item def MedicalDiversionNoticeItem { doc /* @S576 */ }
    item def MorningPlanAvailabilityNotificationItem { doc /* @S073 */ }
    item def MorningWeatherOutlookItem { doc /* @S057,S066 */ }
    item def MovementIndicationsItem { doc /* @S179 */ }
    item def MovementUpdatesItem { doc /* @S222 */ }
    item def NormalizedScheduleItem { doc /* @S053 */ }
    item def NotificationsItem { doc /* @S614 */ }
    item def ObservationsItem { doc /* @S828 */ }
    item def OperationalBasisForEachValueItem { doc /* @S400 */ }
    item def OperationalDecisionsItem { doc /* @S907 */ }
    item def OperationalReadinessInformationItem { doc /* @S016 */ }
    item def OperationalSignificanceOfTheConditionItem { doc /* @S447 */ }
    item def OperationalWeatherClassificationInputsItem { doc /* @S819 */ }
    item def OutputsItem { doc /* @S095 */ }
    item def ParallelOutputsItem { doc /* @S905 */ }
    item def PassengerMisconnectCountItem { doc /* @S851 */ }
    item def PersonnelEquipmentOrCleaningVehiclesReassignmentItem { doc /* @S653 */ }
    item def PlannedRemoteStandOperatingPostureItem { doc /* @S544 */ }
    item def PositionUpdatesItem { doc /* @S179 */ }
    item def PredictedReadinessItem { doc /* @S593 */ }
    item def PrincipalDelayAbsorptionIndicatorItem { doc /* @S842 */ }
    item def ProposedDepartureOpportunitiesAndAssociatedCalculatedTakeoffTimeValuesItem { doc /* @S242,S258 */ }
    item def ProposedSubstitutionItem { doc /* @S667 */ }
    item def PushbackWindowTokenItem { doc /* @S503 */ }
    item def RealizedMovementTimesItem { doc /* @S840 */ }
    item def ReconsiderationRequestItem { doc /* @S363 */ }
    item def RecordedRegulationHistoryItem { doc /* @S418 */ }
    item def RegionalDemandAndConstraintContextItem { doc /* @S164 */ }
    item def RegulatedDemandItem { doc /* @S840 */ }
    item def RemoteStandShuttleCountItem { doc /* @S648 */ }
    item def ResourceDrivenFeasibilityStatusItem { doc /* @S312 */ }
    item def RevisedInputsItem { doc /* @S699 */ }
    item def RicherIntentDataItem { doc /* @S941 */ }
    item def RunwayAssignmentPressureAirborneSequenceSpacingAndExpectedCrossingPointsItem { doc /* @S425 */ }
    item def RunwayInspectionNoteItem { doc /* @S181 */ }
    item def RunwayLightingOutageCardItem { doc /* @S693 */ }
    item def RunwaySpecificCapacityValuesItem { doc /* @S114 */ }
    item def ScheduledMovementsItem { doc /* @S593 */ }
    item def SectorDemandItem { doc /* @S432,S593 */ }
    item def SharedViewOfDemandCapacityConstraintsAndActiveTrafficManagementMeasuresItem { doc /* @S020 */ }
    item def SignificantDecisionsItem { doc /* @S883,S975 */ }
    item def SlotComplianceEventsItem { doc /* @S789 */ }
    item def SlotSwapPermissionEmailItem { doc /* @S795 */ }
    item def StaleMilestoneNotificationItem { doc /* @S166 */ }
    item def StandOccupancyPushbackSpacingAndTugAvailabilityItem { doc /* @S677 */ }
    item def StandReadinessStatusItem { doc /* @S657 */ }
    item def StandTowRequestFormItem { doc /* @S304 */ }
    item def SubscriptionRulesItem { doc /* @S332 */ }
    item def SurfaceConstraintsItem { doc /* @S448 */ }
    item def SurfaceEquipmentAndApronCongestionAdvisoriesItem { doc /* @S463 */ }
    item def SurfaceSurveillanceInputsItem { doc /* @S454 */ }
    item def SynchronizedTimestampsItem { doc /* @S098,S122 */ }
    item def TacticalRegulationProposalItem { doc /* @S501 */ }
    item def TechnicalStatusKnownWorkaroundsDataIntegrityConcernsAndRecoveryOptionsItem { doc /* @S918 */ }
    item def TemporaryRestrictionNoticeItem { doc /* @S399 */ }
    item def TimeItem { doc /* @S778 */ }
    item def TimeSourceItem { doc /* @S792 */ }
    item def ToleranceItem { doc /* @S659 */ }
    item def TowbarShortageReportItem { doc /* @S556 */ }
    item def TowerReadinessChangesItem { doc /* @S293 */ }
    item def TraceItem { doc /* @S123 */ }
    item def TransactionItem { doc /* @S194 */ }
    item def UnconstrainedDemandItem { doc /* @S840 */ }
    item def UnresolvedAssumptionsItem { doc /* @S071 */ }
    item def UrgentDiscrepanciesItem { doc /* @S834 */ }
    item def WeatherFeedItem { doc /* @S109 */ }
    item def WeatherImpactsItem { doc /* @S434 */ }
    item def WeatherInterpretationForecastConfidenceAndExpectedTimingOfOperationalImpactsItem { doc /* @S163 */ }
    part def AccessibleBoardingSupport { doc /* @S548 */ }
    part def AccountableRoles { doc /* @S099 */ }
    part def AirNavigationServiceParticipation { doc /* @S045 */ }
    part def AirTrafficControllers { doc /* @S865 */ }
    part def AircraftOperatorRepresentative { doc /* @S039,S055,S082,S215,S291,S312,S316,S363,S405,S437,S476,S620,S622,S630,S666,S673,S725,S726,S771,S797,S854,S868,S965 */ }
    part def AircraftRegistration { doc /* @S127 */ }
    part def AirlineInterfaceAdapter { doc /* @S018,S033,S103,S126,S128,S135,S145,S235,S452,S478,S519,S618,S622,S625,S741,S829,S947,S979 */ }
    part def AirlineOperationsCentre { doc /* @S126,S131,S135,S139,S146 */ }
    part def AirlineOperationsCoordinator { doc /* @S011,S039,S054,S081,S121,S129,S138,S157,S214,S237,S259,S260,S284,S312,S317,S338,S362,S385,S403,S437,S451,S472,S507,S521,S546,S554,S574,S604,S623,S630,S658,S667,S679,S725,S740,S766,S771,S795,S820,S851,S854,S868,S959,S965 */ }
    part def Airlines { doc /* @S043 */ }
    part def Airport { doc /* @S890 */ }
    part def AirportAcceptanceRate { doc /* @S046,S226 */ }
    part def AirportCDMPortal { doc /* @S016,S031,S150,S153,S162,S163,S164,S166,S170,S172,S179,S185,S195,S264,S270,S293,S312,S337,S363,S381,S405,S429,S447,S470,S485,S503,S527,S531,S544,S559,S572,S602,S622,S626,S648,S649,S667,S668,S673,S681,S695,S712,S793,S812,S907,S947 */ }
    part def AirportCapacityPlan { doc /* @S046,S226 */ }
    part def AirportDutyDesk { doc /* @S177,S178,S185 */ }
    part def AirportDutyManager { doc /* @S040,S062,S088,S091,S116,S144,S162,S175,S177,S181,S183,S190,S196,S198,S218,S368,S435,S447,S471,S496,S544,S563,S568,S576,S660,S678,S679,S692,S713,S716,S734,S750,S809,S816,S860,S872,S917,S959,S962 */ }
    part def AirportNetwork { doc /* @S003,S026 */ }
    part def AirportParticipant { doc /* @S167,S168 */ }
    part def AirportResourceStatus { doc /* @S100 */ }
    part def AirportStakeholders { doc /* @S016 */ }
    part def AirspaceConstraints { doc /* @S100 */ }
    part def AirspacePlanningPersonnel { doc /* @S045 */ }
    part def AirspaceSectorLoadingConditions { doc /* @S226 */ }
    part def AirspaceSectorPlanner { doc /* @S041,S058,S079,S326,S402,S432,S501,S608,S871,S967 */ }
    part def AlertDistributionHub { doc /* @S033,S073,S121,S166,S193,S331,S332,S366,S440,S461,S463,S501,S505,S529,S588,S614,S705,S731,S834 */ }
    part def ArrivalRegulationConsole { doc /* @S017,S032,S070,S095,S241,S336,S407,S495,S535,S576,S596,S698,S729,S757,S980 */ }
    part def ArrivalWorkspace { doc /* @S153,S155 */ }
    part def AuditEventLedger { doc /* @S021,S034,S098,S123,S149,S194,S222,S245,S271,S289,S333,S369,S417,S418,S442,S466,S488,S515,S537,S636,S664,S683,S710,S777,S778,S779,S789,S792,S833,S887,S890,S901,S955,S981 */ }
    part def AuthenticatedAirlineAndHandlingUsers { doc /* @S293 */ }
    part def AuthorizedUsers { doc /* @S020,S462,S627 */ }
    part def AverageQueueLength { doc /* @S846 */ }
    part def BasedCarriers { doc /* @S043 */ }
    part def BusinessRulesRegistry { doc /* @S034,S080,S297,S332,S404,S436,S486,S534,S539,S586,S631,S659,S670,S706,S746,S790,S799,S800,S831,S849,S890,S939 */ }
    part def CalculatedTakeoffTime { doc /* @S046 */ }
    part def CalculatedTakeoffTimeAndTargetOffBlockTime { doc /* @S976 */ }
    part def CandidateAirport { doc /* @S893 */ }
    part def CapacityAssessmentModule { doc /* @S014,S031,S057,S066,S094,S107,S114,S120,S132,S133,S192,S225,S252,S328,S341,S351,S373,S400,S431,S448,S494,S557,S584,S594,S600,S694,S697,S803,S825,S853,S944,S973 */ }
    part def CapacityPicture { doc /* @S100 */ }
    part def CapacityValues { doc /* @S120 */ }
    part def CargoAndGeneralAviationAerodromes { doc /* @S001 */ }
    part def CargoOperators { doc /* @S043 */ }
    part def CharterOperators { doc /* @S043 */ }
    part def CivilTrafficManagers { doc /* @S324 */ }
    part def CodeSetChecks { doc /* @S826 */ }
    part def CollaborativeDecisionLog { doc /* @S021,S046,S071,S084,S122,S145,S161,S169,S186,S239,S267,S288,S321,S369,S392,S405,S442,S466,S487,S506,S531,S589,S615,S637,S682,S709,S720,S759,S760,S794,S883,S901,S925,S955,S975 */ }
    part def CommonServices { doc /* @S030 */ }
    part def CommonSituationDisplay { doc /* @S020,S046,S072,S095,S117,S130,S161,S165,S259,S265,S337,S366,S369,S391,S400,S421,S425,S462,S527,S560,S613,S625,S627,S685,S704,S758,S822,S886,S952,S974 */ }
    part def ConfidenceRecord { doc /* @S119 */ }
    part def ConstrainedPrimaryAirport { doc /* @S892 */ }
    part def ContingencyFallbackState { doc /* @S735 */ }
    part def ContingencyOperationsConsole { doc /* @S032,S195,S247,S540,S719,S722,S783,S908,S952 */ }
    part def ContractedHandlers { doc /* @S044 */ }
    part def CoreOperationalBaseline { doc /* @S890 */ }
    part def CrewReadiness { doc /* @S127 */ }
    part def CriticalIncident { doc /* @S920 */ }
    part def DataGovernanceSteward { doc /* @S042,S098,S170,S240,S273,S490,S515,S541,S587,S711,S733,S742,S773,S780,S785,S806,S813,S833,S861,S876,S910,S958 */ }
    part def DeicingCoordinator { doc /* @S040,S092,S294,S375,S378,S390,S875,S969 */ }
    part def DeicingInterfacePoint { doc /* @S295 */ }
    part def DeicingProviders { doc /* @S044 */ }
    part def DemandForecasts { doc /* @S100 */ }
    part def DemandPredictionService { doc /* @S013,S031,S053,S101,S103,S105,S107,S131,S132,S216,S225,S251,S329,S350,S351,S395,S430,S493,S571,S593,S701,S743,S754,S825,S840,S941,S973 */ }
    part def DepartureMeteringService { doc /* @S017,S032,S069,S095,S242,S258,S278,S315,S335,S347,S348,S352,S379,S426,S456,S483,S534,S553,S601,S626,S656,S686,S699,S728,S747,S825,S851,S950,S980 */ }
    part def DepartureWorkspace { doc /* @S153 */ }
    part def DesignatedMilitaryCoordinationFunction { doc /* @S045 */ }
    part def DigitalBriefingRoom { doc /* @S031,S071,S078,S086,S107,S132,S252,S345,S349,S374,S493,S506,S599,S697,S721,S734,S834 */ }
    part def DomesticAirports { doc /* @S001 */ }
    part def DoorCycleTime { doc /* @S549 */ }
    part def Drivers { doc /* @S548 */ }
    part def EastApronSensor { doc /* @S019,S063,S115,S179,S205,S282,S448,S474,S578,S645,S845 */ }
    part def EmergencyResponseCoordinator { doc /* @S041,S096,S414,S499,S874,S968 */ }
    part def Exercise { doc /* @S881 */ }
    part def Exercises { doc /* @S882 */ }
    part def ExpansionBeyondThePilotAirports { doc /* @S909 */ }
    part def FirstIncrement { doc /* @S889 */ }
    part def Flight { doc /* @S265,S570,S849 */ }
    part def FlightDataExchange { doc /* @S018,S033,S052,S053,S103,S128,S278,S593,S638,S684,S827,S840,S940,S941,S979 */ }
    part def FlightIntentMessage { doc /* @S046,S127,S226 */ }
    part def FreshnessIndicator { doc /* @S823 */ }
    part def FuelingProviders { doc /* @S044 */ }
    part def FutureReleases { doc /* @S959 */ }
    part def GateConflictDetector { doc /* @S019,S210,S364,S386,S439,S459,S468,S472,S509,S558,S582,S657 */ }
    part def Governance { doc /* @S983 */ }
    part def GroundDelayProgram { doc /* @S136,S227,S977 */ }
    part def GroundHandlingDispatcher { doc /* @S040,S064,S091,S140,S158,S237,S261,S292,S302,S383,S438,S508,S519,S523,S550,S556,S643,S653,S869,S966 */ }
    part def GroundHandlingPersonnel { doc /* @S869 */ }
    part def GroundServiceProviders { doc /* @S044 */ }
    part def HandlingResourcePlanner { doc /* @S065,S141,S212,S213,S302,S303,S304,S318,S384,S438,S460,S477,S508,S522,S547,S648,S653,S705,S830,S947 */ }
    part def HarborEastAirport { doc /* @S026 */ }
    part def HighPriorityIncident { doc /* @S921 */ }
    part def HumanFactorsSafeguards { doc /* @S884 */ }
    part def IdentityAccessService { doc /* @S034,S126,S152,S194,S272,S515,S635,S650,S781,S783,S793,S890,S957,S981 */ }
    part def IncidentRecord { doc /* @S923,S924 */ }
    part def Incidents { doc /* @S919 */ }
    part def InitialPilot { doc /* @S892 */ }
    part def InitialTraining { doc /* @S878 */ }
    part def IntegratedTacticalManagementPosition { doc /* @S420,S421,S429,S434 */ }
    part def LakesideRegionalAirport { doc /* @S026 */ }
    part def LessConstrainedRegionalAirport { doc /* @S892 */ }
    part def LoadingPositions { doc /* @S548 */ }
    part def LocalTool { doc /* @S904,S905 */ }
    part def LocalUsers { doc /* @S907 */ }
    part def MandatoryFieldChecks { doc /* @S826 */ }
    part def MaximumLoad { doc /* @S549 */ }
    part def MaximumQueueLength { doc /* @S846 */ }
    part def MediumAndLowPriorityIncidents { doc /* @S922 */ }
    part def MeridianInternationalAirport { doc /* @S026 */ }
    part def MeridianRegion { doc /* @S001 */ }
    part def MeridianRegionalAirTrafficFlowManagementAndAirportCollaborativeDecisionMakingSystem { doc /* @S838,S850,S863 */ }
    part def MeteorologyBriefingOfficer { doc /* @S041,S056,S057,S066,S085,S086,S087,S112,S163,S372,S434,S512,S819,S858,S873,S967 */ }
    part def MigrationPlan { doc /* @S903 */ }
    part def MilestoneView { doc /* @S153,S156 */ }
    part def MilitaryAirspaceLiaison { doc /* @S006,S041,S059,S093,S325,S399,S433,S511,S609,S967 */ }
    part def MobilityAssistanceRequirements { doc /* @S549 */ }
    part def NetworkOperationsLiaison { doc /* @S039,S083,S084,S339,S413,S480,S510,S614,S674,S871,S917,S938 */ }
    part def NorthRunwayMeter { doc /* @S019,S114,S280,S359,S454,S845 */ }
    part def NorthValleyAirport { doc /* @S026 */ }
    part def ObservedTraffic { doc /* @S100 */ }
    part def OnCallSupportPosture { doc /* @S916 */ }
    part def OnboardingWave { doc /* @S910 */ }
    part def OperationalInterface { doc /* @S292 */ }
    part def OperationalOwner { doc /* @S904 */ }
    part def OperationalParticipants { doc /* @S265 */ }
    part def OperationalPlausibilityChecks { doc /* @S826 */ }
    part def OperationalSupervisors { doc /* @S918,S934 */ }
    part def OperationalUser { doc /* @S764 */ }
    part def OperationalUsers { doc /* @S905 */ }
    part def OwnedDataElement { doc /* @S821 */ }
    part def PadQueueControls { doc /* @S376 */ }
    part def ParticipatingAirport { doc /* @S027 */ }
    part def ParticipatingOrganization { doc /* @S960 */ }
    part def ParticipatingRoles { doc /* @S073 */ }
    part def PassengerBusConstraints { doc /* @S549 */ }
    part def PassengerConnectionSensitivity { doc /* @S127 */ }
    part def PassengerTransportProviders { doc /* @S044 */ }
    part def PerformanceAnalyticsWarehouse { doc /* @S034,S074,S099,S123,S148,S173,S197,S248,S274,S322,S346,S370,S394,S418,S489,S514,S538,S565,S590,S616,S639,S665,S712,S737,S760,S776,S804,S836,S837,S839,S840,S856,S887,S890,S957,S982 */ }
    part def PilotAirportSelection { doc /* @S891 */ }
    part def PostExerciseReviews { doc /* @S887 */ }
    part def PostOperationsReport { doc /* @S046,S074,S099,S862,S982 */ }
    part def PreferredRoute { doc /* @S127 */ }
    part def PrimaryInputs { doc /* @S226 */ }
    part def PrimaryInternationalHub { doc /* @S001 */ }
    part def PrimaryWorkspace { doc /* @S153 */ }
    part def PrincipalDelayAbsorptionIndicator { doc /* @S841,S842 */ }
    part def QueueLengthPerformance { doc /* @S843 */ }
    part def QueueMetrics { doc /* @S846 */ }
    part def RampControlLead { doc /* @S040,S063,S090,S142,S159,S184,S200,S202,S204,S205,S206,S208,S210,S211,S213,S218,S219,S244,S262,S283,S304,S357,S378,S387,S446,S473,S508,S545,S556,S614,S642,S647,S654,S677,S678,S749,S766,S770,S818,S867,S917,S966 */ }
    part def RampMovementBoard { doc /* @S017,S032,S063,S090,S203,S216,S222,S255,S311,S361,S377,S427,S445,S450,S458,S469,S525,S551,S581,S646,S657,S677,S703,S801,S844,S947,S980 */ }
    part def RampPersonnel { doc /* @S867 */ }
    part def RampServiceOrganizations { doc /* @S044 */ }
    part def ReadinessGate1 { doc /* @S894 */ }
    part def ReadinessGate2 { doc /* @S895 */ }
    part def ReadinessGate3 { doc /* @S896 */ }
    part def ReadinessGate4 { doc /* @S897 */ }
    part def RecoveryRecommendations { doc /* @S954 */ }
    part def RecoveryTime { doc /* @S846 */ }
    part def RecurrentTraining { doc /* @S879 */ }
    part def RegionalExpansion { doc /* @S956 */ }
    part def RegionalFlowManagementPersonnel { doc /* @S045 */ }
    part def RegionalFlowManager { doc /* @S010,S038,S050,S077,S078,S093,S094,S117,S121,S137,S228,S246,S286,S327,S343,S367,S393,S396,S399,S410,S411,S416,S420,S463,S479,S492,S513,S532,S555,S573,S598,S614,S634,S675,S687,S696,S698,S721,S729,S753,S766,S768,S800,S808,S814,S842,S864,S911,S917,S926,S938,S959,S961 */ }
    part def RegionalFlowPlatform { doc /* @S012,S030,S051,S072,S073,S075,S097,S101,S109,S130,S146,S147,S164,S191,S228,S247,S250,S268,S302,S314,S333,S344,S349,S367,S368,S371,S422,S444,S517,S540,S593,S621,S691,S706,S707,S708,S713,S716,S755,S756,S767,S775,S787,S789,S812,S824,S831,S888,S905,S908,S912,S926,S936 */ }
    part def RegionalSystem { doc /* @S028 */ }
    part def RemoteStand { doc /* @S564 */ }
    part def RequestedDepartureTiming { doc /* @S127 */ }
    part def RunwayMeteringLimits { doc /* @S226 */ }
    part def ScheduledPassengerOperators { doc /* @S043 */ }
    part def SchemaChecks { doc /* @S826 */ }
    part def SectorLoadMonitor { doc /* @S019,S106,S329,S408,S432,S484,S592,S593,S598,S611,S943,S973 */ }
    part def SecuritySegregation { doc /* @S549 */ }
    part def ServiceModel { doc /* @S913 */ }
    part def SharedOperationalPicture { doc /* @S046 */ }
    part def ShuttleAvailability { doc /* @S548 */ }
    part def SimulationEvents { doc /* @S883 */ }
    part def SimulationExercises { doc /* @S880 */ }
    part def SlotAdherence { doc /* @S847 */ }
    part def SlotAllocationEngine { doc /* @S015,S031,S080,S134,S137,S225,S227,S234,S244,S253,S269,S342,S355,S374,S398,S404,S428,S456,S503,S533,S575,S603,S625,S659,S669,S671,S699,S700,S745,S825,S840,S949,S980 */ }
    part def SlotComplianceState { doc /* @S791,S850 */ }
    part def SlotCoordinator { doc /* @S039,S068,S080,S136,S161,S229,S239,S258,S285,S356,S404,S457,S481,S502,S614,S633,S671,S672,S722,S724,S726,S736,S766,S768,S795,S798,S815,S848,S870,S964 */ }
    part def SouthRunwayMeter { doc /* @S019,S114,S280,S359,S455,S845 */ }
    part def SouthportAirport { doc /* @S026 */ }
    part def StakeholderOrganization { doc /* @S048 */ }
    part def Stand { doc /* @S663 */ }
    part def StandAccessRouting { doc /* @S549 */ }
    part def StandardServiceDeskCoverage { doc /* @S915 */ }
    part def StewardshipReviews { doc /* @S837 */ }
    part def SurfaceDecisionFunctions { doc /* @S828 */ }
    part def SurfaceSurveillanceAdapter { doc /* @S018,S033,S179,S204,S281,S360,S389,S445,S454,S474,S580,S606,S693,S802,S828,S979 */ }
    part def System { doc /* @S022,S023,S047,S078,S104,S217,S219,S220,S318,S319,S320,S397,S398,S459,S464,S465,S738,S745,S746,S752,S772,S774,S780,S782,S786,S788,S791,S951,S953 */ }
    part def SystemSupportEngineer { doc /* @S042,S171,S688,S727,S732,S772,S780,S807,S835,S877,S910,S914,S916,S918,S923,S927 */ }
    part def TacticalRegulationProposal { doc /* @S046 */ }
    part def TargetOffBlockTime { doc /* @S046,S948 */ }
    part def TemporalSequenceChecks { doc /* @S826 */ }
    part def TerminalCurbSpace { doc /* @S548 */ }
    part def TimeAboveThreshold { doc /* @S846 */ }
    part def TimeNeededToClearPassengersFromTheAircraftVicinity { doc /* @S549 */ }
    part def TimeOrderedControlSheet { doc /* @S722 */ }
    part def TimeSynchronizationService { doc /* @S034,S098,S110,S122,S149,S187,S245,S256,S382,S585,S651,S778,S792,S824,S890,S957 */ }
    part def TowerSequenceManager { doc /* @S017,S032,S089,S180,S217,S242,S254,S275,S279,S297,S334,S380,S411,S445,S450,S536,S552,S583,S601,S702,S801,S844,S950,S980 */ }
    part def TowerSequenceWorkflow { doc /* @S298 */ }
    part def TowerSupervisor { doc /* @S040,S060,S061,S089,S121,S143,S160,S175,S181,S183,S189,S202,S218,S243,S263,S277,S280,S287,S296,S313,S358,S368,S388,S401,S425,S500,S605,S614,S655,S676,S693,S748,S766,S769,S817,S866,S917,S959 */ }
    part def TowerSupervisoryPersonnel { doc /* @S045 */ }
    part def TowingProviders { doc /* @S044 */ }
    part def TrainingAssessments { doc /* @S886 */ }
    part def TurnaroundStatus { doc /* @S127 */ }
    part def Users { doc /* @S883,S886,S975 */ }
    part def ValidationRules { doc /* @S826 */ }
    part def Vehicles { doc /* @S548 */ }
    part def WeatherFeed { doc /* @S111 */ }
    part def WeatherIngestGateway { doc /* @S018,S033,S057,S086,S102,S108,S109,S111,S182,S409,S434,S610,S819,S943,S979 */ }
    part def WeatherProducts { doc /* @S100 */ }
    part def WestApronSensor { doc /* @S019,S063,S115,S179,S205,S282,S474,S579,S645,S845 */ }
    part def WorkstationLayouts { doc /* @S885 */ }
    part system {
        part accessibleBoardingSupport : AccessibleBoardingSupport;
        part accountableRoles : AccountableRoles {
            perform action a0 { doc /* confirm that decisions and unresolved issues are available to the Performance Analytics Warehouse @S099 */ }
        }
        part airNavigationServiceParticipation : AirNavigationServiceParticipation;
        part airTrafficControllers : AirTrafficControllers;
        part aircraftOperatorRepresentative : AircraftOperatorRepresentative {
            perform action a0 { doc /* align airline intentions, schedule constraints, and slot management decisions with the shared plan @S039 */ }
            perform action a1 { doc /* validates that operator priorities are visible where they are allowed by the Business Rules Registry and local coordination agreements @S055 */ }
            perform action a2 { doc /* provides aircraft-specific constraints when requested @S082 */ }
            perform action a3 { doc /* ensuring that operator commitments entered in the Airport CDM Portal are operationally achievable @S082 */ }
            perform action a4 { doc /* remains accountable for operator acceptance of any revised off-block expectation @S215 */ }
            perform action a5 { doc /* keeping aircraft readiness information current @S291 */ }
            perform action a6 { doc /* declare whether the operator can accept a later off-block time @S316 */ }
            perform action a7 { doc /* requests reconsideration through the Airport CDM Portal @S363 */ }
            perform action a8 { doc /* review proposed timing changes @S437 */ }
            perform action a9 { doc /* confirms whether the aircraft can accept a revised stand assignment @S476 */ }
            perform action a10 { doc /* sends the Crew Duty Extension Log @S620 */ }
            perform action a11 { doc /* remains responsible for the correctness of crew legality inputs @S622 */ }
            perform action a12 { doc /* provides the ranking @S630 */ }
            perform action a13 { doc /* identifies a flight that can exchange its assigned demand position @S666 */ }
            perform action a14 { doc /* records concurrence in the Airport CDM Portal @S673 */ }
            perform action a15 { doc /* acknowledge manual slot assignments @S725 */ }
            perform action a16 { doc /* view airline-relevant planning data @S771 */ }
            perform action a17 { doc /* submit coordination inputs @S771 */ }
            perform action a18 { doc /* proposes a substitution @S797 */ }
            perform action a19 { doc /* challenge cancellation avoidance results through the Collaborative Decision Log @S854 */ }
            perform action a20 { doc /* submit, review, and update Flight Intent Message data @S868 */ }
            perform action a21 { doc /* providing operationally realistic airline intentions @S965 */ }
            perform action a22 { doc /* honoring agreed times @S965 */ }
        }
        part aircraftRegistration : AircraftRegistration;
        part airlineInterfaceAdapter : AirlineInterfaceAdapter {
            perform action a0 { doc /* provide the data feeds needed to maintain a current and consistent operational picture @S018 */ }
            perform action a1 { doc /* provide managed integration points with external systems @S033 */ }
            perform action a2 { doc /* validates message structure @S128 */ }
            perform action a3 { doc /* maps carrier codes to the Business Rules Registry @S128 */ }
            perform action a4 { doc /* forwards accepted intent data to the Flight Data Exchange @S128 */ }
            perform action a5 { doc /* supplies operator preferences @S235 */ }
            perform action a6 { doc /* produces the Late Baggage Tag List @S452 */ }
            perform action a7 { doc /* maintains airline-provided connection exposure @S478 */ }
            perform action a8 { doc /* accepts legality indicators @S618 */ }
            perform action a9 { doc /* validates the timeliness, flight association, and airline ownership of connection-risk data @S741 */ }
            perform action a10 { doc /* apply carrier-specific format checks @S829 */ }
            perform action a11 { doc /* preserving the common operational meaning @S829 */ }
        }
        part airlineOperationsCentre : AirlineOperationsCentre {
            perform action a0 { doc /* submits a Flight Intent Message through the Airline Interface Adapter @S126 */ }
            perform action a1 { doc /* receive those constraints through the Airline Interface Adapter @S135 */ }
            perform action a2 { doc /* view them in the Airport CDM Portal @S135 */ }
            perform action a3 { doc /* submits an updated Flight Intent Message @S139 */ }
            perform action a4 { doc /* submit conservative intents @S146 */ }
        }
        part airlineOperationsCoordinator : AirlineOperationsCoordinator {
            perform action a0 { doc /* align airline intentions, schedule constraints, and slot management decisions with the shared plan @S039 */ }
            perform action a1 { doc /* reviews material deviations from filed intent, including aircraft swaps, early cancellations, recovery flights, and known connection protection actions @S054 */ }
            perform action a2 { doc /* represents carrier operating priorities @S081 */ }
            perform action a3 { doc /* confirms that Flight Intent Message updates are complete, timely, and traceable @S081 */ }
            perform action a4 { doc /* correct them @S129 */ }
            perform action a5 { doc /* evaluates each constraint against crew legality, aircraft rotation continuity, maintenance positioning, and passenger recovery commitments @S138 */ }
            perform action a6 { doc /* keeping the Flight Intent Message status, Target Off Block Time, passenger readiness indicator, and aircraft operational constraint notes current @S157 */ }
            perform action a7 { doc /* uses the delay slip @S237 */ }
            perform action a8 { doc /* requesting an exemption review for a crew connectivity constraint @S237 */ }
            perform action a9 { doc /* reviews the proposed Target Off Block Time @S259 */ }
            perform action a10 { doc /* confirm any operator-requested Target Off Block Time revision in the Airport CDM Portal @S260 */ }
            perform action a11 { doc /* request a sequence review @S284 */ }
            perform action a12 { doc /* decide whether a swap between company flights is operationally meaningful @S317 */ }
            perform action a13 { doc /* uses the shared display to identify flights that may need rerouting, delayed pushback planning, or revised operator intent @S338 */ }
            perform action a14 { doc /* confirms whether each affected aircraft can absorb the assigned delay at stand @S362 */ }
            perform action a15 { doc /* reviews aircraft readiness @S385 */ }
            perform action a16 { doc /* request a later pad entry @S385 */ }
            perform action a17 { doc /* reviews the proposed treatment for network impact @S403 */ }
            perform action a18 { doc /* identifies flights where upstream delay would create a disproportionate connection or aircraft rotation penalty @S403 */ }
            perform action a19 { doc /* review proposed timing changes @S437 */ }
            perform action a20 { doc /* confirming whether the affected flight should keep its Target Off Block Time, request a new value, or accept a later Calculated Takeoff Time @S451 */ }
            perform action a21 { doc /* uses the Gate Reopening Memo to confirm when a previously unavailable gate can be planned again @S472 */ }
            perform action a22 { doc /* supplies passenger, crew, maintenance, and aircraft rotation impacts @S507 */ }
            perform action a23 { doc /* confirms whether the aircraft can remain on plan, accept a short readiness deferral, or require a revised departure intent @S521 */ }
            perform action a24 { doc /* uses remote stands to protect connection banks @S546 */ }
            perform action a25 { doc /* request revision of the Target Off Block Time @S554 */ }
            perform action a26 { doc /* uses customs hold visibility to adjust connection protection, passenger messaging assumptions, and expected aircraft turnaround timing @S574 */ }
            perform action a27 { doc /* reviews the airport-level result @S604 */ }
            perform action a28 { doc /* determine whether flight swaps, cancellations, or recovery plans are needed @S604 */ }
            perform action a29 { doc /* mark a flight as non-recoverable by delay after a specified time @S623 */ }
            perform action a30 { doc /* prevents automated suggestions that would create an infeasible rotation @S623 */ }
            perform action a31 { doc /* provides the ranking @S630 */ }
            perform action a32 { doc /* propose a revised Target Off Block Time @S658 */ }
            perform action a33 { doc /* enters the proposed substitution in the Airport CDM Portal @S667 */ }
            perform action a34 { doc /* confirm that a candidate substitution is eligible for customs release @S679 */ }
            perform action a35 { doc /* requesting a slot swap @S679 */ }
            perform action a36 { doc /* acknowledge manual slot assignments @S725 */ }
            perform action a37 { doc /* sends the Passenger Misconnect Count @S740 */ }
            perform action a38 { doc /* receive role profiles @S766 */ }
            perform action a39 { doc /* view airline-relevant planning data @S771 */ }
            perform action a40 { doc /* submit coordination inputs @S771 */ }
            perform action a41 { doc /* uses the permission email to justify an approved slot substitution @S795 */ }
            perform action a42 { doc /* be accountable for airline-supplied schedule intent, readiness status, and Target Off Block Time updates @S820 */ }
            perform action a43 { doc /* challenge cancellation avoidance results through the Collaborative Decision Log @S854 */ }
            perform action a44 { doc /* submit, review, and update Flight Intent Message data @S868 */ }
            perform action a45 { doc /* assess the operational effect of Calculated Takeoff Time and Target Off Block Time changes @S868 */ }
            perform action a46 { doc /* compare recommendations with actual outcomes @S959 */ }
            perform action a47 { doc /* providing operationally realistic airline intentions @S965 */ }
            perform action a48 { doc /* honoring agreed times @S965 */ }
        }
        part airlines : Airlines;
        part airport : Airport {
            perform action a0 { doc /* exchange operational data @S890 */ }
        }
        part airportAcceptanceRate : AirportAcceptanceRate;
        part airportCDMPortal : AirportCDMPortal {
            perform action a0 { doc /* provides airport stakeholders with a controlled interface for sharing operational readiness information and confirming decisions that affect the surface and terminal sequence @S016 */ }
            perform action a1 { doc /* support planning and collaborative assessment @S031 */ }
            perform action a2 { doc /* provides the shared operational workspace @S150 */ }
            perform action a3 { doc /* highlight the affected flight @S166 */ }
            perform action a4 { doc /* notify the role accountable for the next update through the Alert Distribution Hub @S166 */ }
            perform action a5 { doc /* preserve the last synchronized milestone set @S172 */ }
            perform action a6 { doc /* clearly mark any updates entered under degraded operating procedures @S172 */ }
            perform action a7 { doc /* records duty desk confirmations as operational annotations @S185 */ }
            perform action a8 { doc /* presents each proposed value with its confidence status, last update time, and the reason code @S264 */ }
            perform action a9 { doc /* requires a revised reason code @S270 */ }
            perform action a10 { doc /* marks the earlier value as superseded rather than deleted @S270 */ }
            perform action a11 { doc /* publish tower readiness changes @S293 */ }
            perform action a12 { doc /* presents the resource-driven feasibility status @S312 */ }
            perform action a13 { doc /* displays the active restriction status, expected operational effect, and any related coordination notes on the Common Situation Display @S337 */ }
            perform action a14 { doc /* records the selected fluid type, mixture ratio, treatment start time, treatment completion time, and expected holdover reference @S381 */ }
            perform action a15 { doc /* presents the resulting arrival plan @S405 */ }
            perform action a16 { doc /* records acknowledgements in the Collaborative Decision Log @S405 */ }
            perform action a17 { doc /* exposes agreed Target Off Block Time values and stakeholder remarks @S429 */ }
            perform action a18 { doc /* presents each gate conflict @S470 */ }
            perform action a19 { doc /* shows downstream departure-fix pressure @S485 */ }
            perform action a20 { doc /* uses the window token to preserve the agreed pushback opportunity @S503 */ }
            perform action a21 { doc /* keeps detailed handler notes available to authorized users @S527 */ }
            perform action a22 { doc /* prompts the accountable role to record the proposed mitigation in the Collaborative Decision Log @S531 */ }
            perform action a23 { doc /* records the operational reason, affected flights, expected passenger transfer duration, and responsible control position @S559 */ }
            perform action a24 { doc /* displays border and customs status in a controlled view @S572 */ }
            perform action a25 { doc /* confirm that remote-stand passenger transfer demand is consistent with stand readiness timing @S648 */ }
            perform action a26 { doc /* records each stand readiness confirmation @S649 */ }
            perform action a27 { doc /* validates the submitting user through the Identity Access Service @S668 */ }
            perform action a28 { doc /* blocks any proposal from a party without delegated operator authority @S668 */ }
            perform action a29 { doc /* keeps the proposal pending @S681 */ }
            perform action a30 { doc /* prevents the Slot Allocation Engine from publishing the revised slot assignment @S681 */ }
            perform action a31 { doc /* presents infrastructure events to authorized airport, airline, and flow management users @S695 */ }
            exhibit state modes {
                state s0 { doc /* Adverse Weather Mode @S162 */ }
                state s1 { doc /* Capacity Reduction State @S162 */ }
                state s2 { doc /* Contingency Fallback State @S172 */ }
                state s3 { doc /* Normal Operations @S162 */ }
                state s4 { doc /* Recovery Phase @S162 */ }
                state s5 { doc /* read-only mode @S429 */ }
                state s6 { doc /* unavailable @S195 */ }
            }
        }
        part airportCapacityPlan : AirportCapacityPlan;
        part airportDutyDesk : AirportDutyDesk {
            perform action a0 { doc /* reviews tower inputs, airport operations reports, and surveillance indications @S178 */ }
            perform action a1 { doc /* confirming whether a local condition should be reflected in the Airport Capacity Plan @S178 */ }
            exhibit state modes {
                state s0 { doc /* Adverse Weather Mode @S177 */ }
                state s1 { doc /* Capacity Reduction State @S177 */ }
                state s2 { doc /* Normal Operations @S177 */ }
                state s3 { doc /* Recovery Phase @S177 */ }
            }
        }
        part airportDutyManager : AirportDutyManager {
            perform action a0 { doc /* represent local airport, tower, ramp, handling, and winter operations considerations @S040 */ }
            perform action a1 { doc /* confirms terminal opening status, essential facility readiness, and airport service constraints @S062 */ }
            perform action a2 { doc /* confirms that airport-side constraints are reflected consistently across the Airport CDM Portal and the Common Situation Display @S088 */ }
            perform action a3 { doc /* request a manual capacity review @S116 */ }
            perform action a4 { doc /* monitors the Common Situation Display @S144 */ }
            perform action a5 { doc /* maintaining the Airport Capacity Plan @S162 */ }
            perform action a6 { doc /* declaring local operating impacts @S162 */ }
            perform action a7 { doc /* confirming transitions between Normal Operations, Adverse Weather Mode, Capacity Reduction State, and Recovery Phase @S162 */ }
            perform action a8 { doc /* maintains the airport duty desk @S177 */ }
            perform action a9 { doc /* confirm that the duty desk has a current record of pavement status @S181 */ }
            perform action a10 { doc /* endorsing any declared capacity change @S181 */ }
            perform action a11 { doc /* agree on the operational interpretation @S183 */ }
            perform action a12 { doc /* verifies that airfield operations checks have been completed @S190 */ }
            perform action a13 { doc /* requesting changes to Airport Acceptance Rate values or departure metering assumptions @S190 */ }
            perform action a14 { doc /* briefs open safety checks, unresolved surveillance discrepancies, and any tower coordination points that remain active @S196 */ }
            perform action a15 { doc /* handover has identified active surface constraints @S198 */ }
            perform action a16 { doc /* agree whether the metering horizon should be extended @S368 */ }
            perform action a17 { doc /* declare Normal Operations, Adverse Weather Mode, Capacity Reduction State, Recovery Phase, or Contingency Fallback State @S435 */ }
            perform action a18 { doc /* records the operational significance of the condition in the Airport CDM Portal @S447 */ }
            perform action a19 { doc /* sets the recovery priority for stands that can be reopened quickly @S471 */ }
            perform action a20 { doc /* sends the Medical Diversion Notice @S496 */ }
            perform action a21 { doc /* publishes the planned remote stand operating posture in the Airport CDM Portal @S544 */ }
            perform action a22 { doc /* reduce planned remote stand use @S563 */ }
            perform action a23 { doc /* produces the Customs Hold Release Note @S568 */ }
            perform action a24 { doc /* declare a localized Capacity Reduction State @S660 */ }
            perform action a25 { doc /* uses the Apron Sweep Completion Note to confirm that apron availability constraints do not invalidate an approved substitution @S678 */ }
            perform action a26 { doc /* ensuring that declared service reductions are entered promptly @S692 */ }
            perform action a27 { doc /* confirms closure in the Airport CDM Portal @S713 */ }
            perform action a28 { doc /* declaring the Contingency Fallback State @S716 */ }
            perform action a29 { doc /* conducts fallback briefings @S734 */ }
            perform action a30 { doc /* publishes the current operating basis through the Digital Briefing Room @S734 */ }
            perform action a31 { doc /* uses the Airport CDM Portal @S750 */ }
            perform action a32 { doc /* see whether airline recovery actions are concentrated in one bank or distributed across the operating day @S750 */ }
            perform action a33 { doc /* review late airport-driven changes @S809 */ }
            perform action a34 { doc /* record whether the operational justification was valid @S809 */ }
            perform action a35 { doc /* own airport capacity declarations @S816 */ }
            perform action a36 { doc /* receive benefit summaries @S860 */ }
            perform action a37 { doc /* recognize when an Airport Capacity Plan requires revision @S872 */ }
            perform action a38 { doc /* retain operational command authority @S917 */ }
            perform action a39 { doc /* compare recommendations with actual outcomes @S959 */ }
            perform action a40 { doc /* confirm capacity assumptions used for airport-level coordination @S962 */ }
            exhibit state modes {
                state s0 { doc /* Adverse Weather Mode @S435,S563 */ }
                state s1 { doc /* Capacity Reduction State @S435 */ }
                state s2 { doc /* Contingency Fallback State @S435 */ }
                state s3 { doc /* Normal Operations @S435 */ }
                state s4 { doc /* Recovery Phase @S435 */ }
            }
        }
        part airportNetwork : AirportNetwork {
            perform action a0 { doc /* operates near declared capacity @S003 */ }
            exhibit state modes {
                state s0 { doc /* Normal Operations @S003 */ }
            }
        }
        part airportParticipant : AirportParticipant {
            perform action a0 { doc /* update a material change @S167 */ }
            perform action a1 { doc /* enter a provisional value with an uncertainty flag @S168 */ }
        }
        part airportResourceStatus : AirportResourceStatus;
        part airportStakeholders : AirportStakeholders {
            perform action a0 { doc /* sharing operational readiness information @S016 */ }
            perform action a1 { doc /* confirming decisions that affect the surface and terminal sequence @S016 */ }
        }
        part airspaceConstraints : AirspaceConstraints;
        part airspacePlanningPersonnel : AirspacePlanningPersonnel;
        part airspaceSectorLoadingConditions : AirspaceSectorLoadingConditions;
        part airspaceSectorPlanner : AirspaceSectorPlanner {
            perform action a0 { doc /* participate when weather, airspace structure, special-use airspace, or emergency response conditions affect available capacity @S041 */ }
            perform action a1 { doc /* declares expected sector constraints, route availability assumptions, and any planned staffing limitations @S058 */ }
            perform action a2 { doc /* supports the Regional Flow Manager @S079 */ }
            perform action a3 { doc /* validating sector constraints in the Sector Load Monitor @S079 */ }
            perform action a4 { doc /* advising whether demand smoothing is required before tactical execution @S079 */ }
            perform action a5 { doc /* converts confirmed restricted area information into sector availability assumptions @S326 */ }
            perform action a6 { doc /* checks whether existing flight plans require rerouting, metering, or ground delay action @S326 */ }
            perform action a7 { doc /* confirms whether terminal and en-route sector loads can absorb the regulated stream @S402 */ }
            perform action a8 { doc /* monitors sector demand @S432 */ }
            perform action a9 { doc /* confirms whether proposed measures are compatible with en route capacity @S432 */ }
            perform action a10 { doc /* protects sector margins @S501 */ }
            perform action a11 { doc /* request a Tactical Regulation Proposal @S501 */ }
            perform action a12 { doc /* validates the operational meaning of each constraint @S608 */ }
            perform action a13 { doc /* coordinate regional constraints, sector load conditions, and network measures @S871 */ }
            perform action a14 { doc /* timely disclosure of weather, sector, and airspace constraints @S967 */ }
        }
        part alertDistributionHub : AlertDistributionHub {
            perform action a0 { doc /* provide managed integration points with external systems @S033 */ }
            perform action a1 { doc /* notifies participating roles that the morning plan is available @S073 */ }
            perform action a2 { doc /* notifies the Regional Flow Manager, Tower Supervisor, and Airline Operations Coordinator that the capacity picture may change @S121 */ }
            perform action a3 { doc /* distributes approved duty coordination alerts to affected operational roles @S193 */ }
            perform action a4 { doc /* applies subscription rules from the Business Rules Registry @S332 */ }
            perform action a5 { doc /* highlights the affected runway queue on the Common Situation Display @S366 */ }
            perform action a6 { doc /* routed through the Alert Distribution Hub for stakeholder acknowledgement @S440 */ }
            perform action a7 { doc /* distribute surface equipment and apron congestion advisories @S461 */ }
            perform action a8 { doc /* provides role-specific alert summaries @S505 */ }
            perform action a9 { doc /* routes notifications according to severity, time to milestone, and subscribed operational role @S529 */ }
            perform action a10 { doc /* issues targeted alerts @S588 */ }
            perform action a11 { doc /* sends notifications @S614 */ }
            perform action a12 { doc /* sends notifications @S705 */ }
            perform action a13 { doc /* deliver mandatory operational advisories @S731 */ }
            perform action a14 { doc /* raised Urgent discrepancies @S834 */ }
        }
        part arrivalRegulationConsole : ArrivalRegulationConsole {
            perform action a0 { doc /* support the transition from regional planning decisions to executable airport and tower actions @S017 */ }
            perform action a1 { doc /* support tactical airport and regional coordination @S032 */ }
            perform action a2 { doc /* highlights inbound demand periods @S070 */ }
            perform action a3 { doc /* presents proposed arrival opportunities @S241 */ }
            perform action a4 { doc /* applies airspace capacity reductions to inbound flows @S336 */ }
            perform action a5 { doc /* issues alerts before predicted holding stacks form @S407 */ }
            perform action a6 { doc /* presents diversion options with estimated holding exposure, likely gate or stand impact, and any expected effect on regulated arrivals already in the plan @S495 */ }
            perform action a7 { doc /* suppress handler-exception annotations for arriving flights @S535 */ }
            perform action a8 { doc /* uses the Medical Diversion Notice to protect arrival priority, stand assignment timing, and downstream border coordination @S576 */ }
            perform action a9 { doc /* applies the revised Airport Acceptance Rate @S698 */ }
            perform action a10 { doc /* display arrival demand @S729 */ }
            perform action a11 { doc /* show inbound connection pressure @S757 */ }
        }
        part arrivalWorkspace : ArrivalWorkspace {
            perform action a0 { doc /* shows expected landing demand, stand allocation risk, inbound regulation effects, and handling readiness indicators @S155 */ }
        }
        part auditEventLedger : AuditEventLedger {
            perform action a0 { doc /* preserve the rationale, timing, and authorization of material operational decisions @S021 */ }
            perform action a1 { doc /* provide governance, security, traceability, and performance measurement capabilities @S034 */ }
            perform action a2 { doc /* retains the trace from incoming forecast product to capacity value @S123 */ }
            perform action a3 { doc /* retains movement updates from the Ramp Movement Board @S222 */ }
            perform action a4 { doc /* stores the previous value, new value, responsible user or automated function, timestamp, authority basis, and applicable operating state for every target time change @S271 */ }
            perform action a5 { doc /* preserves the sequence history @S289 */ }
            perform action a6 { doc /* preserves the same decision history @S488 */ }
            perform action a7 { doc /* retain traceability of who viewed, changed, or approved diversion decisions @S515 */ }
            perform action a8 { doc /* records who raised, changed, acknowledged, or closed each escalated exception @S537 */ }
            perform action a9 { doc /* records who entered or changed a recovery choice, the effective time, the affected flight reference, and the reason category @S636 */ }
            perform action a10 { doc /* stores readiness changes, user acknowledgements, hazard closures, and release decisions @S664 */ }
            perform action a11 { doc /* records each approval, rejection, cancellation, and override @S683 */ }
            perform action a12 { doc /* preserves the technical record of submission, validation, publication, acknowledgement, and withdrawal @S710 */ }
            perform action a13 { doc /* capture successful and failed authentication attempts, role changes, privilege elevations, operational approvals, configuration changes, data exports, and emergency access activations @S777 */ }
            perform action a14 { doc /* preserve the time source @S792 */ }
            perform action a15 { doc /* record each proposed option, the user response, and the final decision @S955 */ }
        }
        part authenticatedAirlineAndHandlingUsers : AuthenticatedAirlineAndHandlingUsers;
        part authorizedUsers : AuthorizedUsers;
        part averageQueueLength : AverageQueueLength;
        part basedCarriers : BasedCarriers;
        part businessRulesRegistry : BusinessRulesRegistry {
            perform action a0 { doc /* provide governance, security, traceability, and performance measurement capabilities @S034 */ }
            perform action a1 { doc /* supplies the applicable thresholds for alerting, approval routing, and measure publication @S436 */ }
            perform action a2 { doc /* holds the local rules for connection protection, gate compatibility, towing priority, stand reopening approval, and minimum turnaround recovery margins @S486 */ }
            perform action a3 { doc /* confirms that the condition is operationally material @S534 */ }
            perform action a4 { doc /* tighten escalation thresholds for flights close to departure @S539 */ }
            perform action a5 { doc /* suppress low-impact local issues @S539 */ }
            perform action a6 { doc /* defines which border and customs states block sequencing @S586 */ }
            perform action a7 { doc /* defines which preference fields are mandatory, optional, or hidden from other participants @S631 */ }
            perform action a8 { doc /* provides the governing parameters for precedence, equity, customs eligibility, minimum notification time, and prohibited trades @S670 */ }
            perform action a9 { doc /* defines which infrastructure events require approval @S706 */ }
            perform action a10 { doc /* permits that use for the active operating state @S746 */ }
            perform action a11 { doc /* hold the current validation thresholds, allowable reason codes, and exception rules @S831 */ }
            perform action a12 { doc /* retain the local parameters needed for Meridian operations @S939 */ }
            exhibit state modes {
                state s0 { doc /* Adverse Weather Mode @S539 */ }
                state s1 { doc /* Capacity Reduction State @S539 */ }
            }
        }
        part calculatedTakeoffTime : CalculatedTakeoffTime;
        part calculatedTakeoffTimeAndTargetOffBlockTime : CalculatedTakeoffTimeAndTargetOffBlockTime;
        part candidateAirport : CandidateAirport {
            perform action a0 { doc /* provide evidence @S893 */ }
        }
        part capacityAssessmentModule : CapacityAssessmentModule {
            perform action a0 { doc /* supports the assessment of declared and tactical capacity @S014 */ }
            perform action a1 { doc /* support planning and collaborative assessment @S031 */ }
            perform action a2 { doc /* combines the runway declaration, weather outlook, airspace constraints, stand readiness, and ground resource assumptions into a proposed Airport Acceptance Rate by period @S066 */ }
            perform action a3 { doc /* indicates that declared capacity no longer matches observed conditions @S094 */ }
            perform action a4 { doc /* combines demand projections with the Airport Capacity Plan @S107 */ }
            perform action a5 { doc /* determine whether a published Airport Acceptance Rate remains feasible @S107 */ }
            perform action a6 { doc /* applies the current wind, visibility, and precipitation assumptions @S114 */ }
            perform action a7 { doc /* flags the associated capacity values as provisional @S120 */ }
            perform action a8 { doc /* compares that demand with the Airport Capacity Plan and the current Airport Acceptance Rate @S132 */ }
            perform action a9 { doc /* recommending operating limits @S132 */ }
            perform action a10 { doc /* qualify capacity confidence during convective weather impacts @S133 */ }
            perform action a11 { doc /* use the confirmed airport position to recalculate available capacity @S192 */ }
            perform action a12 { doc /* applies the active Airport Capacity Plan and Airport Acceptance Rate @S252 */ }
            perform action a13 { doc /* determine whether the proposed demand pattern remains operationally feasible @S252 */ }
            perform action a14 { doc /* treats a restriction as a time-bounded reduction in route, sector, or airport throughput @S328 */ }
            perform action a15 { doc /* recalculates the effective Airport Acceptance Rate @S341 */ }
            perform action a16 { doc /* passes the revised assumption into the operational planning cycle @S341 */ }
            perform action a17 { doc /* compares that demand with the active Airport Acceptance Rate, runway configuration, taxiway constraints, and sector limits @S351 */ }
            perform action a18 { doc /* reduces practical departure capacity @S373 */ }
            perform action a19 { doc /* calculates candidate Airport Acceptance Rate values @S400 */ }
            perform action a20 { doc /* exposes the operational basis for each value on the Common Situation Display @S400 */ }
            perform action a21 { doc /* recalculates available capacity @S431 */ }
            perform action a22 { doc /* converts persistent surface constraints into reduced stand throughput, extended turn buffers, or modified taxi-out assumptions @S448 */ }
            perform action a23 { doc /* evaluates runway availability, stand availability, sector load, handling capacity, and service constraints @S494 */ }
            perform action a24 { doc /* reflects persistent remote stand service limits as a reduction in practical gate throughput @S557 */ }
            perform action a25 { doc /* applies persistent apron congestion as a local capacity factor @S584 */ }
            perform action a26 { doc /* evaluates whether the affected traffic is dominated by departures, arrivals, or mixed flows @S594 */ }
            perform action a27 { doc /* applies Business Rules Registry thresholds to distinguish a short tactical peak from sustained saturation @S600 */ }
            perform action a28 { doc /* converts the limit into a runway configuration constraint @S694 */ }
            perform action a29 { doc /* calculates the operational effect @S697 */ }
            perform action a30 { doc /* reject data that lacks a trusted timestamp @S825 */ }
            perform action a31 { doc /* record the available Airport Acceptance Rate used in each baseline @S853 */ }
            perform action a32 { doc /* compare planned capacity, observed throughput, and predicted constraint persistence @S944 */ }
            perform action a33 { doc /* provide planning evidence @S973 */ }
            exhibit state modes {
                state s0 { doc /* Adverse Weather Mode @S584 */ }
                state s1 { doc /* Normal Operations @S584 */ }
            }
        }
        part capacityPicture : CapacityPicture;
        part capacityValues : CapacityValues {
            exhibit state modes {
                state s0 { doc /* provisional @S120 */ }
            }
        }
        part cargoAndGeneralAviationAerodromes : CargoAndGeneralAviationAerodromes;
        part cargoOperators : CargoOperators;
        part charterOperators : CharterOperators;
        part civilTrafficManagers : CivilTrafficManagers {
            perform action a0 { doc /* receive usable timing, altitude, and boundary information @S324 */ }
        }
        part codeSetChecks : CodeSetChecks;
        part collaborativeDecisionLog : CollaborativeDecisionLog {
            perform action a0 { doc /* preserve the rationale, timing, and authorization of material operational decisions @S021 */ }
            perform action a1 { doc /* records who changed a value, when the change was made, whether the change was provisional or confirmed, and what operational decision relied on it @S169 */ }
            perform action a2 { doc /* captures the time, origin, and rationale for each local coordination decision @S186 */ }
            perform action a3 { doc /* records each challenge, counterproposal, acceptance, rejection, and reason code @S267 */ }
            perform action a4 { doc /* captures winter-mode decisions @S392 */ }
            perform action a5 { doc /* records each accepted conflict resolution @S487 */ }
            perform action a6 { doc /* records the operational reason @S589 */ }
            perform action a7 { doc /* records the constraint, chosen conversion rule, responsible actor, and time of approval @S615 */ }
            perform action a8 { doc /* records any agreed operational outcome @S637 */ }
            perform action a9 { doc /* captures the proposed flights, the reason code, the user confirmations, the governance outcome, and the final decision time @S682 */ }
            perform action a10 { doc /* records the time of publication, approving role, capacity effect, affected services, and any later amendment @S709 */ }
            perform action a11 { doc /* retain the stated reason, decision time, affected flight, and visible operational context @S794 */ }
            perform action a12 { doc /* preserve the operational context of major incidents @S925 */ }
            perform action a13 { doc /* record each proposed option, the user response, and the final decision @S955 */ }
        }
        part commonServices : CommonServices {
            perform action a0 { doc /* support regional flow management and Airport Collaborative Decision-Making participation @S030 */ }
        }
        part commonSituationDisplay : CommonSituationDisplay {
            perform action a0 { doc /* give authorized users a shared view of demand, capacity, constraints, and active traffic management measures @S020 */ }
            perform action a1 { doc /* presents the approved pre-tactical baseline @S072 */ }
            perform action a2 { doc /* reflected on the Common Situation Display as proposed airline actions @S130 */ }
            perform action a3 { doc /* distinguishes values supplied by connected services, values confirmed by users, and values that have exceeded the configured freshness threshold @S165 */ }
            perform action a4 { doc /* shows the current agreed target set @S265 */ }
            perform action a5 { doc /* highlights expired treatments, pad closures, fluid shortages, and ramp blockages @S391 */ }
            perform action a6 { doc /* provides the base map, timeline, flight list, and measure status panels @S421 */ }
            perform action a7 { doc /* highlights active surface advisories @S462 */ }
            perform action a8 { doc /* shows only the flight impact, severity, and expected recovery window @S527 */ }
            perform action a9 { doc /* presents remote stand status in time order @S560 */ }
            perform action a10 { doc /* shows crew legality impacts as coded operational states @S627 */ }
            perform action a11 { doc /* presents the updated Calculated Takeoff Time and Target Off Block Time @S685 */ }
            perform action a12 { doc /* shows the affected resource, start time, review time, and current decision status @S704 */ }
            perform action a13 { doc /* presents passenger disruption cues @S758 */ }
            perform action a14 { doc /* displayed Freshness indicators @S822 */ }
            perform action a15 { doc /* reviewed machine-assisted recovery options @S952 */ }
            exhibit state modes {
                state s0 { doc /* feasible @S627 */ }
                state s1 { doc /* infeasible @S627 */ }
                state s2 { doc /* operator review required @S627 */ }
                state s3 { doc /* time critical @S627 */ }
            }
        }
        part confidenceRecord : ConfidenceRecord {
            perform action a0 { doc /* stores the originating feed, the processing time, the transformation version, and any manual override @S119 */ }
        }
        part constrainedPrimaryAirport : ConstrainedPrimaryAirport;
        part contingencyFallbackState : ContingencyFallbackState;
        part contingencyOperationsConsole : ContingencyOperationsConsole {
            perform action a0 { doc /* support tactical airport and regional coordination @S032 */ }
            perform action a1 { doc /* provides a degraded channel for recording tower and duty desk decisions @S195 */ }
            perform action a2 { doc /* preserves the last valid allocation @S247 */ }
            perform action a3 { doc /* supports manual amendments @S247 */ }
            perform action a4 { doc /* marks the resulting Slot Compliance State as provisional @S247 */ }
            perform action a5 { doc /* exception summaries remain available @S540 */ }
            perform action a6 { doc /* provides a protected operating position with independent access to the Flight Data Exchange, Alert Distribution Hub, Audit Event Ledger, and Digital Briefing Room @S719 */ }
            perform action a7 { doc /* accept emergency access activations @S783 */ }
            perform action a8 { doc /* generated machine-assisted recovery options @S952 */ }
        }
        part contractedHandlers : ContractedHandlers;
        part coreOperationalBaseline : CoreOperationalBaseline;
        part crewReadiness : CrewReadiness;
        part criticalIncident : CriticalIncident;
        part dataGovernanceSteward : DataGovernanceSteward {
            perform action a0 { doc /* maintain data quality, access control, operational continuity, and controlled configuration of the Regional Flow Platform @S042 */ }
            perform action a1 { doc /* verifies that operational decisions, role acknowledgements, and exception handling are captured in the Audit Event Ledger @S098 */ }
            perform action a2 { doc /* defines the mandatory fields, permissible status values, retention rules, and data quality thresholds @S170 */ }
            perform action a3 { doc /* ensures that exemption categories, priority codes, and fairness metrics are versioned in the Business Rules Registry @S240 */ }
            perform action a4 { doc /* reviews audit samples @S273 */ }
            perform action a5 { doc /* ensures that passenger connection information used for prioritization is aggregated or role-restricted @S490 */ }
            perform action a6 { doc /* ensures that sensitive operational and passenger information remains role-restricted @S515 */ }
            perform action a7 { doc /* ensures that baggage and handler data exposed outside the local operation is limited to operational necessity @S541 */ }
            perform action a8 { doc /* maintains the access rules and retention rules for border and customs data @S587 */ }
            perform action a9 { doc /* monitors data quality for infrastructure events @S711 */ }
            perform action a10 { doc /* confirms which data sets may be trusted @S733 */ }
            perform action a11 { doc /* marks any later synchronization from fallback records for reconciliation review @S733 */ }
            perform action a12 { doc /* defines the acceptable aggregation level @S742 */ }
            perform action a13 { doc /* manage data retention rules, reference data ownership, and audit review processes @S773 */ }
            perform action a14 { doc /* post-event review @S785 */ }
            perform action a15 { doc /* verify that audit fields remain complete, immutable, and traceable @S806 */ }
            perform action a16 { doc /* maintain the data ownership register @S813 */ }
            perform action a17 { doc /* coordinate updates through the Business Rules Registry @S813 */ }
            perform action a18 { doc /* coordinate discrepancy resolution with the responsible operational owner @S833 */ }
            perform action a19 { doc /* record the disposition in the Audit Event Ledger @S833 */ }
            perform action a20 { doc /* ensure that published performance measures identify data sources, calculation versions, confidence limits, and known exclusions @S861 */ }
            perform action a21 { doc /* train operational users on data quality responsibilities, privacy expectations, and the correct interpretation of audit records @S876 */ }
            perform action a22 { doc /* monitor defect trends, data quality, access changes, and user adoption @S910 */ }
        }
        part deicingCoordinator : DeicingCoordinator {
            perform action a0 { doc /* represent local airport, tower, ramp, handling, and winter operations considerations @S040 */ }
            perform action a1 { doc /* provides pre-tactical and tactical advice @S092 */ }
            perform action a2 { doc /* sends the Deicing Pad Queue Card @S294 */ }
            perform action a3 { doc /* maintains the active pad configuration @S375 */ }
            perform action a4 { doc /* marks the treatment as expired @S390 */ }
            perform action a5 { doc /* returns the aircraft to the appropriate queue state @S390 */ }
            perform action a6 { doc /* receive seasonal refresher training @S875 */ }
            perform action a7 { doc /* confirm deicing constraints @S969 */ }
            exhibit state modes {
                state s0 { doc /* winter operations @S092 */ }
            }
        }
        part deicingInterfacePoint : DeicingInterfacePoint {
            perform action a0 { doc /* exposes whether a flight still requires treatment, is waiting for pad access, is under treatment, or has been released for taxi @S295 */ }
        }
        part deicingProviders : DeicingProviders;
        part demandForecasts : DemandForecasts;
        part demandPredictionService : DemandPredictionService {
            perform action a0 { doc /* estimates expected demand @S013 */ }
            perform action a1 { doc /* support planning and collaborative assessment @S031 */ }
            perform action a2 { doc /* converts the normalized schedule into expected arrival and departure demand by time band, runway direction, terminal area, and major traffic flow @S053 */ }
            perform action a3 { doc /* generates the demand forecast @S101 */ }
            perform action a4 { doc /* receives filed flight information @S103 */ }
            perform action a5 { doc /* compares it with the current operating schedule @S103 */ }
            perform action a6 { doc /* estimate arrival and departure loads by planning interval @S105 */ }
            perform action a7 { doc /* uses recent conformance history, aircraft rotation timing, and known bank structures @S105 */ }
            perform action a8 { doc /* refine departure demand, arrival demand, and recovery demand by time band @S131 */ }
            perform action a9 { doc /* refresh stand demand forecasts @S216 */ }
            perform action a10 { doc /* estimates demand pressure over the next planning horizon @S251 */ }
            perform action a11 { doc /* marks flights whose proposed Target Off Block Time values are likely to cause runway or sector imbalance @S251 */ }
            perform action a12 { doc /* estimates the departure demand profile by stand, apron area, runway, and departure fix @S350 */ }
            perform action a13 { doc /* shows that inbound demand will exceed the Airport Acceptance Rate @S395 */ }
            perform action a14 { doc /* continuously updates short-term traffic forecasts @S430 */ }
            perform action a15 { doc /* compares amended Flight Intent Message data with the Airport Capacity Plan and the current Airport Acceptance Rate @S493 */ }
            perform action a16 { doc /* show whether a diversion can be absorbed without creating unsafe demand peaks @S493 */ }
            perform action a17 { doc /* treats the turnaround milestone as uncertain @S571 */ }
            perform action a18 { doc /* recalculates short-term demand against the constrained capacity @S701 */ }
            perform action a19 { doc /* combines connection-risk indicators with aircraft readiness, scheduled bank structure, and forecast arrival variability @S743 */ }
            perform action a20 { doc /* estimate the sensitivity of selected departures @S743 */ }
            perform action a21 { doc /* discounts the associated connection benefit @S754 */ }
            perform action a22 { doc /* reject data that lacks a trusted timestamp @S825 */ }
            perform action a23 { doc /* predicted unconstrained demand @S840 */ }
            perform action a24 { doc /* create more stable demand pictures across longer planning horizons @S941 */ }
            perform action a25 { doc /* provide planning evidence @S973 */ }
        }
        part departureMeteringService : DepartureMeteringService {
            perform action a0 { doc /* support the transition from regional planning decisions to executable airport and tower actions @S017 */ }
            perform action a1 { doc /* support tactical airport and regional coordination @S032 */ }
            perform action a2 { doc /* estimates provisional Target Off Block Time sensitivity @S069 */ }
            perform action a3 { doc /* presents proposed departure opportunities and associated Calculated Takeoff Time values @S242 */ }
            perform action a4 { doc /* aligns each Target Off Block Time with the applicable Calculated Takeoff Time @S278 */ }
            perform action a5 { doc /* absorb a small ground handling variation @S315 */ }
            perform action a6 { doc /* uses the current capacity assumptions to adjust departure release guidance @S335 */ }
            perform action a7 { doc /* preserving previously coordinated Calculated Takeoff Time values @S335 */ }
            perform action a8 { doc /* deciding where delay is best absorbed before aircraft begin taxi @S347 */ }
            perform action a9 { doc /* converts runway demand into controlled stand delay @S348 */ }
            perform action a10 { doc /* derives a feasible Target Off Block Time @S352 */ }
            perform action a11 { doc /* withholds further push clearances @S379 */ }
            perform action a12 { doc /* sends revised departure metering advisories @S426 */ }
            perform action a13 { doc /* translates runway metering limits into candidate pushback spacing @S456 */ }
            perform action a14 { doc /* sequences recovered departures @S483 */ }
            perform action a15 { doc /* applies exception status @S534 */ }
            perform action a16 { doc /* incorporates remote stand constraints when estimating whether a Target Off Block Time remains achievable @S553 */ }
            perform action a17 { doc /* limited departure metering adjustment @S601 */ }
            perform action a18 { doc /* receives only the feasibility result and timing boundary needed for sequencing decisions @S626 */ }
            perform action a19 { doc /* suppresses release recommendations for flights whose assigned stand is not marked ready or whose access route is blocked by an unresolved apron condition @S656 */ }
            perform action a20 { doc /* recalculates metering advisories @S686 */ }
            perform action a21 { doc /* prevents the swap from creating a new demand peak at a departure fix @S686 */ }
            perform action a22 { doc /* updates metering rates @S699 */ }
            perform action a23 { doc /* provides revised inputs to the Slot Allocation Engine @S699 */ }
            perform action a24 { doc /* recommend a minor hold, release, or resequencing action @S747 */ }
            perform action a25 { doc /* reject data that lacks a trusted timestamp @S825 */ }
            perform action a26 { doc /* weight departure sequencing decisions @S851 */ }
            exhibit state modes {
                state s0 { doc /* monitoring mode @S728 */ }
            }
        }
        part departureWorkspace : DepartureWorkspace;
        part designatedMilitaryCoordinationFunction : DesignatedMilitaryCoordinationFunction;
        part digitalBriefingRoom : DigitalBriefingRoom {
            perform action a0 { doc /* support planning and collaborative assessment @S031 */ }
            perform action a1 { doc /* displays the emerging Airport Capacity Plan @S071 */ }
            perform action a2 { doc /* records unresolved assumptions in the Collaborative Decision Log @S071 */ }
            perform action a3 { doc /* provides a common venue to confirm the active interpretation of the restriction @S345 */ }
            perform action a4 { doc /* records the diversion rationale, priority classification, resource commitment, and agreed recovery target in the Collaborative Decision Log @S506 */ }
            perform action a5 { doc /* reviewed Urgent discrepancies @S834 */ }
        }
        part domesticAirports : DomesticAirports;
        part doorCycleTime : DoorCycleTime;
        part drivers : Drivers;
        part eastApronSensor : EastApronSensor {
            perform action a0 { doc /* provide additional indicators of emerging capacity loss and operational imbalance @S019 */ }
            perform action a1 { doc /* detecting aircraft movement @S282 */ }
            perform action a2 { doc /* provide supporting movement evidence for the reopened area @S474 */ }
            perform action a3 { doc /* reports stand occupancy transitions, pushback lane blockage durations, and sensor confidence values @S578 */ }
            perform action a4 { doc /* provide supporting surveillance cues @S645 */ }
            perform action a5 { doc /* support independent checks of queue length @S845 */ }
        }
        part emergencyResponseCoordinator : EmergencyResponseCoordinator {
            perform action a0 { doc /* participate when weather, airspace structure, special-use airspace, or emergency response conditions affect available capacity @S041 */ }
            perform action a1 { doc /* confirms rescue, medical, and airport safety readiness with the Airport Duty Manager @S499 */ }
            perform action a2 { doc /* participate in recurrent training @S874 */ }
            perform action a3 { doc /* require protective operating measures @S968 */ }
        }
        part exercise : Exercise;
        part exercises : Exercises;
        part expansionBeyondThePilotAirports : ExpansionBeyondThePilotAirports;
        part firstIncrement : FirstIncrement {
            perform action a0 { doc /* establish the core operational baseline @S889 */ }
        }
        part flight : Flight {
            exhibit state modes {
                state s0 { doc /* customs hold @S570 */ }
                state s1 { doc /* exempted from compliance monitoring @S265 */ }
                state s2 { doc /* frozen @S265 */ }
                state s3 { doc /* proposed @S265 */ }
                state s4 { doc /* under negotiation @S265 */ }
            }
        }
        part flightDataExchange : FlightDataExchange {
            perform action a0 { doc /* provide the data feeds needed to maintain a current and consistent operational picture @S018 */ }
            perform action a1 { doc /* provide managed integration points with external systems @S033 */ }
            perform action a2 { doc /* normalizes flight identifiers, aircraft types, routing fields, and planned operating times @S052 */ }
            perform action a3 { doc /* provides current flight intent data @S278 */ }
            perform action a4 { doc /* distributes only the approved operational result to downstream services @S638 */ }
            perform action a5 { doc /* publishes revised Flight Intent Message content @S684 */ }
            perform action a6 { doc /* validate Flight Intent Message content @S827 */ }
            perform action a7 { doc /* captured realized movement times @S840 */ }
            perform action a8 { doc /* accept richer intent data @S940 */ }
        }
        part flightIntentMessage : FlightIntentMessage;
        part freshnessIndicator : FreshnessIndicator {
            perform action a0 { doc /* distinguishes current, aging, stale, and unavailable data @S823 */ }
        }
        part fuelingProviders : FuelingProviders;
        part futureReleases : FutureReleases {
            exhibit state modes {
                state s0 { doc /* shadow mode @S959 */ }
            }
        }
        part gateConflictDetector : GateConflictDetector {
            perform action a0 { doc /* provide additional indicators of emerging capacity loss and operational imbalance @S019 */ }
            perform action a1 { doc /* alerts the Ramp Control Lead @S210 */ }
            perform action a2 { doc /* warns when continued stand holding would block an inbound allocation or create a conflict with a planned equipment move @S364 */ }
            perform action a3 { doc /* produces the Gate Reopening Memo @S386 */ }
            perform action a4 { doc /* highlights stand conflicts @S439 */ }
            perform action a5 { doc /* checks whether the congestion can be relieved by resequencing adjacent stands @S459 */ }
            perform action a6 { doc /* compares planned arrivals, planned departures, assigned gates, towing availability, and published stand status @S468 */ }
            perform action a7 { doc /* identify conflicts @S468 */ }
            perform action a8 { doc /* flags conflicts between diversion parking requirements and planned turnarounds @S509 */ }
            perform action a9 { doc /* identifies cases where an aircraft assigned to a contact gate would cause less overall delay @S558 */ }
            perform action a10 { doc /* uses border status and apron occupancy evidence to distinguish a true gate conflict from a temporary clearance delay @S582 */ }
            perform action a11 { doc /* checks readiness status against aircraft allocation, towing activity, and adjacent stand occupancy @S657 */ }
            perform action a12 { doc /* identify conflicts before ground movement begins @S657 */ }
        }
        part governance : Governance;
        part groundDelayProgram : GroundDelayProgram {
            exhibit state modes {
                state s0 { doc /* active @S136,S227 */ }
            }
        }
        part groundHandlingDispatcher : GroundHandlingDispatcher {
            perform action a0 { doc /* represent local airport, tower, ramp, handling, and winter operations considerations @S040 */ }
            perform action a1 { doc /* confirms whether planned handling teams and equipment coverage are sufficient @S064 */ }
            perform action a2 { doc /* confirms that handling resource assumptions are current in the Handling Resource Planner @S091 */ }
            perform action a3 { doc /* escalates material deviations through the Airport Duty Manager @S091 */ }
            perform action a4 { doc /* sends the Crew Bus Delay Slip @S140 */ }
            perform action a5 { doc /* updating servicing completion, baggage readiness, staffing limitation, and equipment availability milestones @S158 */ }
            perform action a6 { doc /* updates handling milestones @S261 */ }
            perform action a7 { doc /* updates boarding, loading, door closure, and tow readiness milestones @S292 */ }
            perform action a8 { doc /* updates the Handling Resource Planner with expected service completion times @S302 */ }
            perform action a9 { doc /* updates remaining fluid inventory and truck serviceability @S383 */ }
            perform action a10 { doc /* compare planned off-block demand with available servicing capacity at affected stands @S438 */ }
            perform action a11 { doc /* confirm stand access, towing resources, refueling constraints, and unloading capacity @S508 */ }
            perform action a12 { doc /* confirm which flights require baggage reconciliation @S519 */ }
            perform action a13 { doc /* sends the Towbar Shortage Report @S523 */ }
            perform action a14 { doc /* verifies that bus assignments do not conflict with baggage, catering, fueling, or crew transport movements @S550 */ }
            perform action a15 { doc /* assigns qualified personnel to perform apron sweeps @S643 */ }
            perform action a16 { doc /* updates the Handling Resource Planner @S653 */ }
            perform action a17 { doc /* train Ground handling personnel on the Handling Resource Planner @S869 */ }
            perform action a18 { doc /* maintaining accurate surface and handling status @S966 */ }
        }
        part groundHandlingPersonnel : GroundHandlingPersonnel {
            perform action a0 { doc /* confirming that resource constraints are represented accurately @S869 */ }
        }
        part groundServiceProviders : GroundServiceProviders;
        part handlingResourcePlanner : HandlingResourcePlanner {
            perform action a0 { doc /* compares the demand curve with available ground resources @S065 */ }
            perform action a1 { doc /* flags time bands where aircraft turn performance is likely to reduce stand availability @S065 */ }
            perform action a2 { doc /* correlated ground handling impacts with stand occupancy, baggage readiness, catering status, and boarding progress @S141 */ }
            perform action a3 { doc /* provides the shared planning basis for baggage, catering, cleaning, boarding support, and towing resources @S212 */ }
            perform action a4 { doc /* maintains the operational view of dispatch teams, tow teams, ramp buses, belt loaders, high loaders, stairs, ground power units, air start units, and potable water equipment @S303 */ }
            perform action a5 { doc /* reserve towing capacity @S304 */ }
            perform action a6 { doc /* test whether the requested movement can be completed before the proposed Target Off Block Time @S304 */ }
            perform action a7 { doc /* reports a constraint @S318 */ }
            perform action a8 { doc /* compares fluid inventory with scheduled deicing demand @S384 */ }
            perform action a9 { doc /* warns when a planned bank cannot be supported without resequencing @S384 */ }
            perform action a10 { doc /* evaluates whether additional ground handling resources can remove the constraint @S460 */ }
            perform action a11 { doc /* estimates whether the proposed turnaround can be recovered @S477 */ }
            perform action a12 { doc /* assigns a severity level to the handler exception @S522 */ }
            perform action a13 { doc /* suppresses duplicate updates @S522 */ }
            perform action a14 { doc /* produces the Remote Stand Shuttle Count @S547 */ }
            perform action a15 { doc /* validate resource quantities, task timing, and allocation identifiers against active operational reference data @S830 */ }
        }
        part harborEastAirport : HarborEastAirport;
        part highPriorityIncident : HighPriorityIncident;
        part humanFactorsSafeguards : HumanFactorsSafeguards;
        part identityAccessService : IdentityAccessService {
            perform action a0 { doc /* provide governance, security, traceability, and performance measurement capabilities @S034 */ }
            perform action a1 { doc /* managed by the Identity Access Service @S126 */ }
            perform action a2 { doc /* controls access to the Airport CDM Portal @S152 */ }
            perform action a3 { doc /* restricts entry of duty desk confirmations to authorized airport operations staff @S194 */ }
            perform action a4 { doc /* records each transaction in the Audit Event Ledger @S194 */ }
            perform action a5 { doc /* ensures that only users with the assigned operational role can approve frozen-time changes, manual exemptions, or retrospective corrections @S272 */ }
            perform action a6 { doc /* retain traceability of who viewed, changed, or approved diversion decisions @S515 */ }
            perform action a7 { doc /* enforces these visibility rules for Airport CDM Portal, Digital Briefing Room, and application programming interfaces @S635 */ }
            perform action a8 { doc /* restricts readiness confirmation privileges @S650 */ }
            perform action a9 { doc /* support rapid suspension of accounts @S781 */ }
            perform action a10 { doc /* records the authorizing incident reference and expiry time @S783 */ }
        }
        part incidentRecord : IncidentRecord {
            perform action a0 { doc /* captures the initial symptom, affected components, operational state, timeline, mitigation actions, data corrections, and supervisor decisions @S923 */ }
            perform action a1 { doc /* reference the Audit Event Ledger @S924 */ }
        }
        part incidents : Incidents;
        part initialPilot : InitialPilot;
        part initialTraining : InitialTraining;
        part integratedTacticalManagementPosition : IntegratedTacticalManagementPosition {
            perform action a0 { doc /* presents a combined tactical view @S420 */ }
            perform action a1 { doc /* applies weather-driven capacity values @S434 */ }
        }
        part lakesideRegionalAirport : LakesideRegionalAirport;
        part lessConstrainedRegionalAirport : LessConstrainedRegionalAirport;
        part loadingPositions : LoadingPositions;
        part localTool : LocalTool;
        part localUsers : LocalUsers {
            perform action a0 { doc /* enter operational decisions through the Airport CDM Portal @S907 */ }
            perform action a1 { doc /* avoid reintroducing uncontrolled parallel records @S907 */ }
        }
        part mandatoryFieldChecks : MandatoryFieldChecks;
        part maximumLoad : MaximumLoad;
        part maximumQueueLength : MaximumQueueLength;
        part mediumAndLowPriorityIncidents : MediumAndLowPriorityIncidents;
        part meridianInternationalAirport : MeridianInternationalAirport;
        part meridianRegion : MeridianRegion;
        part meridianRegionalAirTrafficFlowManagementAndAirportCollaborativeDecisionMakingSystem : MeridianRegionalAirTrafficFlowManagementAndAirportCollaborativeDecisionMakingSystem {
            perform action a0 { doc /* convert operational events into repeatable indicators @S838 */ }
            exhibit state modes {
                state s0 { doc /* Slot Compliance State @S850 */ }
            }
        }
        part meteorologyBriefingOfficer : MeteorologyBriefingOfficer {
            perform action a0 { doc /* participate when weather, airspace structure, special-use airspace, or emergency response conditions affect available capacity @S041 */ }
            perform action a1 { doc /* provides the morning weather outlook @S056 */ }
            perform action a2 { doc /* produces the Storm Cell Snapshot @S085 */ }
            perform action a3 { doc /* briefs forecast confidence, timing risk, and expected operational impact in the Digital Briefing Room @S086 */ }
            perform action a4 { doc /* states the trigger conditions that would justify moving from Normal Operations to Adverse Weather Mode @S087 */ }
            perform action a5 { doc /* reviews degraded weather inputs @S112 */ }
            perform action a6 { doc /* attach weather interpretation, forecast confidence, and expected timing of operational impacts @S163 */ }
            perform action a7 { doc /* confirms the trigger conditions in the Digital Briefing Room @S372 */ }
            perform action a8 { doc /* verifies weather impacts @S434 */ }
            perform action a9 { doc /* maintains rapidly updated forecast information @S512 */ }
            perform action a10 { doc /* own operational weather classification inputs @S819 */ }
            perform action a11 { doc /* support interpretation of emissions results @S858 */ }
            perform action a12 { doc /* identifying periods when weather routing or convective avoidance dominated fuel performance @S858 */ }
            perform action a13 { doc /* explain weather uncertainty in operational terms @S873 */ }
            perform action a14 { doc /* verify that the Weather Ingest Gateway supports the assumptions used during briefings @S873 */ }
            perform action a15 { doc /* timely disclosure of weather, sector, and airspace constraints @S967 */ }
        }
        part migrationPlan : MigrationPlan {
            perform action a0 { doc /* classify each local tool @S903 */ }
        }
        part milestoneView : MilestoneView {
            perform action a0 { doc /* records the planned, target, estimated, actual, and manually confirmed times @S156 */ }
        }
        part militaryAirspaceLiaison : MilitaryAirspaceLiaison {
            perform action a0 { doc /* close coordination @S006 */ }
            perform action a1 { doc /* participate when weather, airspace structure, special-use airspace, or emergency response conditions affect available capacity @S041 */ }
            perform action a2 { doc /* confirms whether shared airspace assumptions remain valid for the morning @S059 */ }
            perform action a3 { doc /* identifies any conditional availability that must be treated as uncertain @S059 */ }
            perform action a4 { doc /* confirms military airspace availability assumptions @S093 */ }
            perform action a5 { doc /* alerts the Regional Flow Manager @S093 */ }
            perform action a6 { doc /* sends the Temporary Restriction Notice @S325 */ }
            perform action a7 { doc /* confirming the activation window, affected volume, controlling authority, and any published contingency conditions @S325 */ }
            perform action a8 { doc /* mark an airspace release or closure assumption for review @S433 */ }
            perform action a9 { doc /* states whether flexible use airspace can be adjusted @S511 */ }
            perform action a10 { doc /* confirms whether conditional route availability changes the effective capacity @S609 */ }
            perform action a11 { doc /* timely disclosure of weather, sector, and airspace constraints @S967 */ }
        }
        part mobilityAssistanceRequirements : MobilityAssistanceRequirements;
        part networkOperationsLiaison : NetworkOperationsLiaison {
            perform action a0 { doc /* align airline intentions, schedule constraints, and slot management decisions with the shared plan @S039 */ }
            perform action a1 { doc /* coordinates with adjacent network units @S083 */ }
            perform action a2 { doc /* confirms that regional measures remain compatible with upstream and downstream flow constraints @S083 */ }
            perform action a3 { doc /* records external coordination outcomes in the Collaborative Decision Log @S084 */ }
            perform action a4 { doc /* coordinates with external network positions @S339 */ }
            perform action a5 { doc /* coordinates with affected airline control centers @S413 */ }
            perform action a6 { doc /* reviews whether protecting a connecting passenger group supports wider network recovery @S480 */ }
            perform action a7 { doc /* coordinates downstream network effects @S510 */ }
            perform action a8 { doc /* monitors aggregate displacement from approved substitutions @S674 */ }
            perform action a9 { doc /* coordinate regional constraints, sector load conditions, and network measures @S871 */ }
            perform action a10 { doc /* retain operational command authority @S917 */ }
            perform action a11 { doc /* negotiate measures before local capacity is saturated @S938 */ }
        }
        part northRunwayMeter : NorthRunwayMeter {
            perform action a0 { doc /* provide additional indicators of emerging capacity loss and operational imbalance @S019 */ }
            perform action a1 { doc /* receive runway-specific capacity values @S114 */ }
            perform action a2 { doc /* maintain separate queues @S280 */ }
            perform action a3 { doc /* maintain independent queue counts @S359 */ }
            perform action a4 { doc /* reduces the departure release rate @S454 */ }
            perform action a5 { doc /* support independent checks of queue length @S845 */ }
        }
        part northValleyAirport : NorthValleyAirport;
        part observedTraffic : ObservedTraffic;
        part onCallSupportPosture : OnCallSupportPosture;
        part onboardingWave : OnboardingWave;
        part operationalInterface : OperationalInterface;
        part operationalOwner : OperationalOwner {
            perform action a0 { doc /* verifies that its essential decisions, timing assumptions, and audit needs are supported @S904 */ }
        }
        part operationalParticipants : OperationalParticipants;
        part operationalPlausibilityChecks : OperationalPlausibilityChecks;
        part operationalSupervisors : OperationalSupervisors {
            perform action a0 { doc /* directed use of contingency procedures @S934 */ }
        }
        part operationalUser : OperationalUser {
            perform action a0 { doc /* authenticate with an individually assigned identity @S764 */ }
            perform action a1 { doc /* accessing the Airport CDM Portal, Digital Briefing Room, or any operational console @S764 */ }
        }
        part operationalUsers : OperationalUsers;
        part ownedDataElement : OwnedDataElement;
        part padQueueControls : PadQueueControls {
            perform action a0 { doc /* assign aircraft to a deicing lane @S376 */ }
        }
        part participatingAirport : ParticipatingAirport {
            perform action a0 { doc /* remains responsible for its local safety management, aerodrome certification obligations, and operational command authority @S027 */ }
        }
        part participatingOrganization : ParticipatingOrganization {
            perform action a0 { doc /* treat the operating picture as a shared operational asset @S960 */ }
        }
        part participatingRoles : ParticipatingRoles;
        part passengerBusConstraints : PassengerBusConstraints;
        part passengerConnectionSensitivity : PassengerConnectionSensitivity;
        part passengerTransportProviders : PassengerTransportProviders;
        part performanceAnalyticsWarehouse : PerformanceAnalyticsWarehouse {
            perform action a0 { doc /* provide governance, security, traceability, and performance measurement capabilities @S034 */ }
            perform action a1 { doc /* retains the baseline inputs, capacity declarations, and approval timestamps @S074 */ }
            perform action a2 { doc /* reconstruct the decision basis after operations @S123 */ }
            perform action a3 { doc /* compares submitted intents, issued constraints, actual off-block times, and achieved arrival outcomes @S148 */ }
            perform action a4 { doc /* compare planned outcomes with actual off-block, takeoff, landing, and stand events @S173 */ }
            perform action a5 { doc /* uses the recorded milestones and decision history @S173 */ }
            perform action a6 { doc /* compares recorded duty coordination events with actual movement data @S197 */ }
            perform action a7 { doc /* identify delays, missed checks, and opportunities to improve local decision quality @S197 */ }
            perform action a8 { doc /* compares proposed opportunities, actual movement times, exemption usage, and operator-level delay equity @S248 */ }
            perform action a9 { doc /* uses frozen targets, actual milestone timestamps, and audit records to measure compliance, delay attribution, negotiation effectiveness, and rule quality @S274 */ }
            perform action a10 { doc /* compares predicted and actual handling constraints @S322 */ }
            perform action a11 { doc /* identify chronic equipment shortages by stand group @S322 */ }
            perform action a12 { doc /* compares planned capacity, issued alerts, operator acknowledgements, and realized delay @S346 */ }
            perform action a13 { doc /* compares planned stand absorption, actual off block performance, and runway queue length @S370 */ }
            perform action a14 { doc /* verify that the agreed thresholds were not exceeded @S370 */ }
            perform action a15 { doc /* compares planned treatment throughput, actual pad occupancy, and departure compliance @S394 */ }
            perform action a16 { doc /* compare predicted holding, actual airborne delay, diversion outcomes, and achieved landing rates @S418 */ }
            perform action a17 { doc /* measures whether recovered gate assignments reduced missed connections @S489 */ }
            perform action a18 { doc /* compares actual handling times, sector load, connection outcomes, and regulation changes against the recorded diversion plan @S514 */ }
            perform action a19 { doc /* compares escalated exceptions with actual off-block performance @S538 */ }
            perform action a20 { doc /* tune severity thresholds @S538 */ }
            perform action a21 { doc /* reduce nuisance alerts over time @S538 */ }
            perform action a22 { doc /* retains remote stand timing measures @S565 */ }
            perform action a23 { doc /* compares planned clearance assumptions with actual border release timing and apron availability @S590 */ }
            perform action a24 { doc /* compares predicted sector pressure, actual airborne delay, and airport departure compliance @S616 */ }
            perform action a25 { doc /* tune Demand Prediction Service and Capacity Assessment Module @S616 */ }
            perform action a26 { doc /* analyze anonymized patterns of legality constraints and recovery selections @S639 */ }
            perform action a27 { doc /* uses aggregated readiness and contamination timing data @S665 */ }
            perform action a28 { doc /* identify recurring debris locations, inefficient sweep patterns, and opportunities for preventive maintenance @S665 */ }
            perform action a29 { doc /* uses completed infrastructure events to measure delay attribution, capacity recovery time, and the accuracy of initial duration estimates @S712 */ }
            perform action a30 { doc /* receives the outage timeline, manual intervention record, and recovery milestones @S737 */ }
            perform action a31 { doc /* compares later delay outcomes with the logged rationale @S760 */ }
            perform action a32 { doc /* aggregate compliance outcomes @S804 */ }
            perform action a33 { doc /* retain data quality measures @S836 */ }
            perform action a34 { doc /* calculate delay absorption @S839 */ }
            perform action a35 { doc /* apply approved fuel burn and emissions factors @S856 */ }
            exhibit state modes {
                state s0 { doc /* Recovery Phase @S489 */ }
            }
        }
        part pilotAirportSelection : PilotAirportSelection;
        part postExerciseReviews : PostExerciseReviews {
            perform action a0 { doc /* improve procedures @S887 */ }
            perform action a1 { doc /* refine training materials @S887 */ }
            perform action a2 { doc /* confirm that human performance concerns are assigned to accountable owners @S887 */ }
        }
        part postOperationsReport : PostOperationsReport {
            perform action a0 { doc /* compare planned performance with actual outcomes @S074 */ }
            perform action a1 { doc /* present regional benefits alongside operational trade-offs @S862 */ }
        }
        part preferredRoute : PreferredRoute;
        part primaryInputs : PrimaryInputs;
        part primaryInternationalHub : PrimaryInternationalHub;
        part primaryWorkspace : PrimaryWorkspace {
            perform action a0 { doc /* presents the Common Situation Display @S153 */ }
        }
        part principalDelayAbsorptionIndicator : PrincipalDelayAbsorptionIndicator {
            perform action a0 { doc /* report minutes absorbed at origin, minutes remaining in the arrival stream, and minutes transferred to surface queues @S841 */ }
        }
        part queueLengthPerformance : QueueLengthPerformance;
        part queueMetrics : QueueMetrics;
        part rampControlLead : RampControlLead {
            perform action a0 { doc /* represent local airport, tower, ramp, handling, and winter operations considerations @S040 */ }
            perform action a1 { doc /* reviews early stand readiness @S063 */ }
            perform action a2 { doc /* maintains the Ramp Movement Board in a state that supports reliable departure metering @S090 */ }
            perform action a3 { doc /* uses the Ramp Movement Board to identify whether the proposed recovery action can be supported @S142 */ }
            perform action a4 { doc /* maintaining stand release readiness, apron movement conflicts, tug availability, and local pushback sequencing inputs in the portal @S159 */ }
            perform action a5 { doc /* reviews apron movement constraints with the duty desk @S184 */ }
            perform action a6 { doc /* maintains the operational sequence for pushbacks, stand exits, stand entries, and towing movements @S200 */ }
            perform action a7 { doc /* release a pushback @S202 */ }
            perform action a8 { doc /* reconciling sensor data with visual and operational reports @S205 */ }
            perform action a9 { doc /* assigns priority to towing movements @S206 */ }
            perform action a10 { doc /* sends the Stand Tow Request Form @S208 */ }
            perform action a11 { doc /* coordinates with the Ground Handling Dispatcher @S211 */ }
            perform action a12 { doc /* reviews Handling Resource Planner constraints @S213 */ }
            perform action a13 { doc /* committing to a pushback sequence @S213 */ }
            perform action a14 { doc /* escalates the condition to the Tower Supervisor and Airport Duty Manager @S218 */ }
            perform action a15 { doc /* increases spacing between pushbacks and towing movements @S219 */ }
            perform action a16 { doc /* identify apron constraints through the Ramp Movement Board @S244 */ }
            perform action a17 { doc /* assesses whether the proposed off-block pattern is compatible with apron access, stand conflicts, and local movement restrictions @S262 */ }
            perform action a18 { doc /* coordinates pushback release priorities against stand conflicts, taxi lane constraints, and the runway demand @S283 */ }
            perform action a19 { doc /* reviews the proposed windows against apron congestion, towing activity, and aircraft readiness @S357 */ }
            perform action a20 { doc /* accepting them for local execution @S357 */ }
            perform action a21 { doc /* verify pad entry order @S378 */ }
            perform action a22 { doc /* authorizing a movement from the staging area @S378 */ }
            perform action a23 { doc /* coordinate every pad release with the Tower Supervisor @S387 */ }
            perform action a24 { doc /* verifies whether the condition blocks a single movement, a stand group, or a wider apron route @S446 */ }
            perform action a25 { doc /* coordinates stand reopening with the Ground Handling Dispatcher @S473 */ }
            perform action a26 { doc /* confirm stand access, towing resources, refueling constraints, and unloading capacity @S508 */ }
            perform action a27 { doc /* confirms that each planned remote stand has an assigned aircraft route, safe passenger transfer path, and defined contingency for blocked apron movement @S545 */ }
            perform action a28 { doc /* uses the Towbar Shortage Report to determine whether remote stand aircraft can be repositioned @S556 */ }
            perform action a29 { doc /* defines the sweep areas @S642 */ }
            perform action a30 { doc /* sends the Apron Sweep Completion Note @S647 */ }
            perform action a31 { doc /* reviews unresolved hazards against active turnaround demand @S654 */ }
            perform action a32 { doc /* allowing pushback planning to continue for the affected stand @S654 */ }
            perform action a33 { doc /* confirms that the revised sequence remains compatible with stand occupancy, pushback spacing, and tug availability @S677 */ }
            perform action a34 { doc /* uses the Ramp Movement Board @S749 */ }
            perform action a35 { doc /* determine whether a proposed metering adjustment can be supported by stand availability, pushback feasibility, and taxi route status @S749 */ }
            perform action a36 { doc /* receive role profiles @S766 */ }
            perform action a37 { doc /* update ramp movement status through the Ramp Movement Board @S770 */ }
            perform action a38 { doc /* own ramp movement status data @S818 */ }
            perform action a39 { doc /* train Ramp personnel @S867 */ }
            perform action a40 { doc /* retain operational command authority @S917 */ }
            perform action a41 { doc /* maintaining accurate surface and handling status @S966 */ }
        }
        part rampMovementBoard : RampMovementBoard {
            perform action a0 { doc /* support the transition from regional planning decisions to executable airport and tower actions @S017 */ }
            perform action a1 { doc /* support tactical airport and regional coordination @S032 */ }
            perform action a2 { doc /* supports reliable departure metering @S090 */ }
            perform action a3 { doc /* is the primary working view for planned apron movements, active conflicts, towing tasks, and occupied stand intervals @S203 */ }
            perform action a4 { doc /* records a material change in planned off-block timing @S216 */ }
            perform action a5 { doc /* maintains milestone timestamps @S255 */ }
            perform action a6 { doc /* shows occupied stands, blocked service roads, and pending pushback areas @S311 */ }
            perform action a7 { doc /* produces the Fuel Truck Hold Advice @S361 */ }
            perform action a8 { doc /* displays each aircraft as pending push, taxi to pad, in treatment, awaiting release, or returning to stand @S377 */ }
            perform action a9 { doc /* refresh the apron movement layer @S427 */ }
            perform action a10 { doc /* shows conflicting pushbacks, blocked lead-in lines, saturated holding points, or insufficient room for safe wingtip clearance @S458 */ }
            perform action a11 { doc /* maintains the operational view of occupied, blocked, cleaning, boarding, and tow-ready positions @S469 */ }
            perform action a12 { doc /* displays the resulting constraint as a stand-level exception with a time band @S525 */ }
            perform action a13 { doc /* displays remote stand occupancy, expected towing actions, and bus service readiness @S551 */ }
            perform action a14 { doc /* presents apron sensor events as operational evidence @S581 */ }
            perform action a15 { doc /* displays stand readiness status @S646 */ }
            perform action a16 { doc /* shows stand occupancy, pushback spacing, and tug availability @S677 */ }
            perform action a17 { doc /* receives the same operational status @S703 */ }
            perform action a18 { doc /* provide actual movement milestones @S801 */ }
            perform action a19 { doc /* provide surface queue counts @S844 */ }
        }
        part rampPersonnel : RampPersonnel {
            perform action a0 { doc /* use the Ramp Movement Board @S867 */ }
        }
        part rampServiceOrganizations : RampServiceOrganizations;
        part readinessGate1 : ReadinessGate1 {
            perform action a0 { doc /* confirm that governance, security approvals, user role definitions, operating hours, and support escalation paths are documented and accepted by local stakeholders @S894 */ }
        }
        part readinessGate2 : ReadinessGate2 {
            perform action a0 { doc /* confirm that the Flight Data Exchange, Airline Interface Adapter, Surface Surveillance Adapter, and Weather Ingest Gateway can be connected @S895 */ }
        }
        part readinessGate3 : ReadinessGate3 {
            perform action a0 { doc /* confirm that local procedures have been mapped @S896 */ }
        }
        part readinessGate4 : ReadinessGate4 {
            perform action a0 { doc /* confirm that training, shadow operations, contingency procedures, and operational acceptance criteria have been completed @S897 */ }
        }
        part recoveryRecommendations : RecoveryRecommendations;
        part recoveryTime : RecoveryTime;
        part recurrentTraining : RecurrentTraining;
        part regionalExpansion : RegionalExpansion;
        part regionalFlowManagementPersonnel : RegionalFlowManagementPersonnel;
        part regionalFlowManager : RegionalFlowManager {
            perform action a0 { doc /* balancing demand against capacity across the Meridian region @S010 */ }
            perform action a1 { doc /* coordinating regional traffic management actions @S010 */ }
            perform action a2 { doc /* balancing demand and capacity at the regional level @S038 */ }
            perform action a3 { doc /* owns the baseline process @S050 */ }
            perform action a4 { doc /* confirms that the planning horizon, cutover time, and review checkpoints are understood by the participating operational roles @S050 */ }
            perform action a5 { doc /* owns the regional operating intent @S077 */ }
            perform action a6 { doc /* confirms that planned demand, declared capacity, and coordination milestones are aligned @S077 */ }
            perform action a7 { doc /* reviews the Airport Capacity Plan, the Ground Delay Program status, and any Tactical Regulation Proposal @S078 */ }
            perform action a8 { doc /* chairs decision checkpoints @S094 */ }
            perform action a9 { doc /* authorizes changes to flow measures @S094 */ }
            perform action a10 { doc /* uses the Common Situation Display to compare forecast demand, assessed capacity, and any active Ground Delay Program effects @S117 */ }
            perform action a11 { doc /* confirms airline recovery priorities @S137 */ }
            perform action a12 { doc /* owns the final operating policy for priority classes @S228 */ }
            perform action a13 { doc /* authorize temporary rule changes @S228 */ }
            perform action a14 { doc /* approved shorter recalculation cycles @S246 */ }
            perform action a15 { doc /* is notified when local resequencing threatens to erode the planned departure rate @S286 */ }
            perform action a16 { doc /* assesses whether the effect is localized to one stream or requires a broader Ground Delay Program @S327 */ }
            perform action a17 { doc /* decides whether to absorb the impact through metering, targeted delay, reroute coordination, or a wider regulation @S343 */ }
            perform action a18 { doc /* increase stand absorption @S367 */ }
            perform action a19 { doc /* authorizes a controlled transition from Capacity Reduction State toward Recovery Phase @S393 */ }
            perform action a20 { doc /* evaluates regulation options in the Arrival Regulation Console @S396 */ }
            perform action a21 { doc /* uses the restriction notice to bound the arrival regulation timeline @S399 */ }
            perform action a22 { doc /* committing new landing-rate values in the Arrival Regulation Console @S399 */ }
            perform action a23 { doc /* apply a tactical landing-rate reduction for a defined review interval @S410 */ }
            perform action a24 { doc /* approve a staged landing-rate increase @S411 */ }
            perform action a25 { doc /* combine arrival regulation with departure metering @S416 */ }
            perform action a26 { doc /* compare planned demand, measured throughput, and active control measures @S420 */ }
            perform action a27 { doc /* uses these advisories to decide whether the tactical plan should retain normal sequencing, shift to local metering, or support a Tactical Regulation Proposal @S463 */ }
            perform action a28 { doc /* balances passenger connection pressure against network fairness @S479 */ }
            perform action a29 { doc /* uses the Regional Flow Platform @S492 */ }
            perform action a30 { doc /* maintain a ranked view of candidate diversions, expected arrival times, required services, and the operational consequence of accepting each aircraft @S492 */ }
            perform action a31 { doc /* shifts from acceptance decisions to recovery coordination @S513 */ }
            perform action a32 { doc /* balancing restored arrival capacity, departure release opportunities, and stand clearance timing @S513 */ }
            perform action a33 { doc /* sees aggregated impact by departure bank, runway stream, and airline group @S532 */ }
            perform action a34 { doc /* considers repeated remote stand transfer delays as an input to tactical capacity assessment @S555 */ }
            perform action a35 { doc /* uses aggregated border delay exposure to decide whether an arrival regulation should be adjusted @S573 */ }
            perform action a36 { doc /* uses the load sheet to confirm whether a departure fix constraint should be represented as an airport departure measure @S598 */ }
            perform action a37 { doc /* see aggregate recovery pressure across operators @S634 */ }
            perform action a38 { doc /* suspend collaborative substitution during a Capacity Reduction State @S675 */ }
            perform action a39 { doc /* reviews the published constraint @S696 */ }
            perform action a40 { doc /* confirmation @S698 */ }
            perform action a41 { doc /* applies the last verified Airport Capacity Plan @S721 */ }
            perform action a42 { doc /* adjusts it by direct coordination with the Airspace Sector Planner and Meteorology Briefing Officer @S721 */ }
            perform action a43 { doc /* approves any arrival regulation changes through direct coordination @S729 */ }
            perform action a44 { doc /* consider a recovery action credible @S753 */ }
            perform action a45 { doc /* receive role profiles @S766 */ }
            perform action a46 { doc /* authorize regional traffic management measures @S768 */ }
            perform action a47 { doc /* use the Post Operations Report to identify whether noncompliance resulted @S808 */ }
            perform action a48 { doc /* own flow management policy data @S814 */ }
            perform action a49 { doc /* verify that a Ground Delay Program reduced airborne holding @S842 */ }
            perform action a50 { doc /* receive advanced instruction on interpreting demand and capacity information, leading collaborative decisions, and authorizing operational measures @S864 */ }
            perform action a51 { doc /* confirms that operational benefits, safety constraints, cyber controls, and stakeholder obligations remain stable @S911 */ }
            perform action a52 { doc /* retain operational command authority @S917 */ }
            perform action a53 { doc /* direct transition to Contingency Fallback State @S926 */ }
            perform action a54 { doc /* see upstream demand pressure earlier @S938 */ }
            perform action a55 { doc /* compare recommendations with actual outcomes @S959 */ }
            perform action a56 { doc /* activate, amend, or terminate regional flow measures @S961 */ }
            exhibit state modes {
                state s0 { doc /* Recovery Phase @S513 */ }
                state s1 { doc /* tactical operations @S094 */ }
            }
        }
        part regionalFlowPlatform : RegionalFlowPlatform {
            perform action a0 { doc /* integrate planning, tactical regulation, airport readiness, and post-event analysis @S012 */ }
            perform action a1 { doc /* creates the initial demand picture from published schedules, approved seasonal allocations, overnight schedule changes, and received Flight Intent Message data @S051 */ }
            perform action a2 { doc /* reconciles them with airport and airspace constraints @S130 */ }
            perform action a3 { doc /* permits more frequent intent updates @S147 */ }
            perform action a4 { doc /* retaining the previous values needed for audit and performance review @S147 */ }
            perform action a5 { doc /* expose the current regional demand and constraint context to the shared workspace @S164 */ }
            perform action a6 { doc /* receives confirmed capacity impacts through normal system interfaces @S191 */ }
            perform action a7 { doc /* creates the initial Target Off Block Time proposal @S250 */ }
            perform action a8 { doc /* locks the Target Off Block Time @S268 */ }
            perform action a9 { doc /* distinguish an air traffic delay from a local handling delay @S302 */ }
            perform action a10 { doc /* marks a proposed Target Off Block Time as conditional @S314 */ }
            perform action a11 { doc /* records each airspace alert, acknowledgement, and downstream decision in the Audit Event Ledger @S333 */ }
            perform action a12 { doc /* normalizes each Flight Intent Message against the current Airport Capacity Plan @S349 */ }
            perform action a13 { doc /* synchronizes the tactical display with the Time Synchronization Service @S422 */ }
            perform action a14 { doc /* correlates surface equipment conditions with flight intent, stand assignment, and runway plan data @S444 */ }
            perform action a15 { doc /* recommending any change to the active tactical plan @S444 */ }
            perform action a16 { doc /* treats these conditions as operational exceptions @S517 */ }
            perform action a17 { doc /* filtered, grouped, and escalated @S517 */ }
            perform action a18 { doc /* aligns these sector values with scheduled movements and predicted readiness @S593 */ }
            perform action a19 { doc /* treats the received legality status as an operator assertion @S621 */ }
            perform action a20 { doc /* does not independently calculate labor agreement compliance @S621 */ }
            perform action a21 { doc /* records each event as an operational constraint @S691 */ }
            perform action a22 { doc /* maintains the infrastructure event as a controlling assumption @S708 */ }
            perform action a23 { doc /* returns the affected resource to Normal Operations or Recovery Phase handling @S713 */ }
            perform action a24 { doc /* record the initiating user, the approving user, the affected operational object, and the effective time of the decision @S775 */ }
            perform action a25 { doc /* reconcile contingency actions with the Collaborative Decision Log @S787 */ }
            perform action a26 { doc /* record slot compliance events in the Audit Event Ledger @S789 */ }
            perform action a27 { doc /* produces parallel outputs @S905 */ }
            exhibit state modes {
                state s0 { doc /* Adverse Weather Mode @S072,S146,S344,S367,S707,S755,S831,S908 */ }
                state s1 { doc /* Capacity Reduction State @S072,S146,S228,S344,S368,S706,S831,S908 */ }
                state s2 { doc /* Contingency Fallback State @S247,S540,S716,S831,S908,S926 */ }
                state s3 { doc /* Normal Operations @S072,S713,S831,S908 */ }
                state s4 { doc /* Recovery Phase @S072,S147,S713,S756,S831,S908 */ }
                state s5 { doc /* degraded @S097 */ }
                state s6 { doc /* shadow operations @S905 */ }
                state s7 { doc /* winter operating mode @S371 */ }
            }
        }
        part regionalSystem : RegionalSystem {
            perform action a0 { doc /* provides a shared coordination layer @S028 */ }
        }
        part remoteStand : RemoteStand {
            exhibit state modes {
                state s0 { doc /* Recovery Phase @S564 */ }
            }
        }
        part requestedDepartureTiming : RequestedDepartureTiming;
        part runwayMeteringLimits : RunwayMeteringLimits;
        part scheduledPassengerOperators : ScheduledPassengerOperators;
        part schemaChecks : SchemaChecks;
        part sectorLoadMonitor : SectorLoadMonitor {
            perform action a0 { doc /* provide additional indicators of emerging capacity loss and operational imbalance @S019 */ }
            perform action a1 { doc /* contributes airspace demand indicators @S106 */ }
            perform action a2 { doc /* provides the operational view of expected demand against the reduced sector capacity @S329 */ }
            perform action a3 { doc /* highlights intervals where overload is likely @S329 */ }
            perform action a4 { doc /* contributes early warnings @S408 */ }
            perform action a5 { doc /* produces the Departure Fix Load Sheet @S484 */ }
            perform action a6 { doc /* supplies time-bucketed counts, predicted occupancy, and overload flags @S592 */ }
            perform action a7 { doc /* provide planning evidence @S973 */ }
        }
        part securitySegregation : SecuritySegregation;
        part serviceModel : ServiceModel {
            perform action a0 { doc /* distinguish continuous operational support from planned engineering support @S913 */ }
        }
        part sharedOperationalPicture : SharedOperationalPicture;
        part shuttleAvailability : ShuttleAvailability;
        part simulationEvents : SimulationEvents;
        part simulationExercises : SimulationExercises;
        part slotAdherence : SlotAdherence;
        part slotAllocationEngine : SlotAllocationEngine {
            perform action a0 { doc /* supports fair and traceable allocation of constrained departure and arrival opportunities @S015 */ }
            perform action a1 { doc /* support planning and collaborative assessment @S031 */ }
            perform action a2 { doc /* applies the current Business Rules Registry parameters @S080 */ }
            perform action a3 { doc /* converts accepted constraints into Calculated Takeoff Time values and Target Off Block Time guidance @S134 */ }
            perform action a4 { doc /* publishes a revised constraint set @S137 */ }
            perform action a5 { doc /* proposes regulated departure and arrival opportunities @S225 */ }
            perform action a6 { doc /* derives a Calculated Takeoff Time or arrival opportunity @S227 */ }
            perform action a7 { doc /* recalculating the regulated opportunity @S244 */ }
            perform action a8 { doc /* derives the Calculated Takeoff Time @S253 */ }
            perform action a9 { doc /* receives a capacity update @S269 */ }
            perform action a10 { doc /* revise slot outcomes @S342 */ }
            perform action a11 { doc /* adjust allocated departure times @S355 */ }
            perform action a12 { doc /* recalculates affected Calculated Takeoff Time values @S374 */ }
            perform action a13 { doc /* support a Ground Delay Program @S398 */ }
            perform action a14 { doc /* produces the Pushback Window Token @S428 */ }
            perform action a15 { doc /* uses the sanitized readiness state @S533 */ }
            perform action a16 { doc /* evaluating whether a regulated flight can keep its allocated departure opportunity @S533 */ }
            perform action a17 { doc /* treats an unresolved customs hold as a reason to avoid assigning an aggressive departure sequence position @S575 */ }
            perform action a18 { doc /* preserves equity by distributing delay across operators @S603 */ }
            perform action a19 { doc /* evaluating whether a Calculated Takeoff Time should be offered, retained, exchanged, or released @S625 */ }
            perform action a20 { doc /* retains the Calculated Takeoff Time @S659 */ }
            perform action a21 { doc /* evaluates the candidate swap against active Ground Delay Program constraints, Calculated Takeoff Time integrity, Target Off Block Time dependencies, and Airport Acceptance Rate commitments @S669 */ }
            perform action a22 { doc /* raised exception @S671 */ }
            perform action a23 { doc /* protect fairness @S700 */ }
            perform action a24 { doc /* apply the approved sequencing policy, runway capacity, airspace constraints, and published Ground Delay Program parameters @S745 */ }
            perform action a25 { doc /* reject data that lacks a trusted timestamp @S825 */ }
            perform action a26 { doc /* produced regulated demand @S840 */ }
            perform action a27 { doc /* protect feasible Calculated Takeoff Time assignments @S949 */ }
            perform action a28 { doc /* reduce avoidable re-sequencing @S949 */ }
        }
        part slotComplianceState : SlotComplianceState {
            perform action a0 { doc /* indicate whether a flight was compliant, early, late, exempted, substituted, cancelled, or pending review @S791 */ }
        }
        part slotCoordinator : SlotCoordinator {
            perform action a0 { doc /* align airline intentions, schedule constraints, and slot management decisions with the shared plan @S039 */ }
            perform action a1 { doc /* uses the Slot Allocation Engine to prepare an initial slot feasibility view @S068 */ }
            perform action a2 { doc /* does not publish binding Calculated Takeoff Time values during baseline construction @S068 */ }
            perform action a3 { doc /* maintains accountability for Calculated Takeoff Time allocation policy @S080 */ }
            perform action a4 { doc /* confirms that the Slot Allocation Engine applies the current Business Rules Registry parameters @S080 */ }
            perform action a5 { doc /* reviews airline requests for priority handling against published equity and operational feasibility rules @S136 */ }
            perform action a6 { doc /* checking Calculated Takeoff Time feasibility @S161 */ }
            perform action a7 { doc /* recording accepted slot adjustments, rejected slot adjustments, and unresolved slot conflicts in the Collaborative Decision Log @S161 */ }
            perform action a8 { doc /* administers the allocation run @S229 */ }
            perform action a9 { doc /* reviews exceptions @S229 */ }
            perform action a10 { doc /* confirms that proposed results are ready for publication through the Airport CDM Portal @S229 */ }
            perform action a11 { doc /* records each accepted or rejected exemption in the Collaborative Decision Log @S239 */ }
            perform action a12 { doc /* reviews proposed Calculated Takeoff Time values against network constraints @S258 */ }
            perform action a13 { doc /* requests adjustment @S258 */ }
            perform action a14 { doc /* verifies that any proposed resequencing remains compatible with the Calculated Takeoff Time tolerance and the current Slot Compliance State @S285 */ }
            perform action a15 { doc /* records the agreed pushback window rationale in the coordination notes @S356 */ }
            perform action a16 { doc /* uses the Slot Allocation Engine to distribute arrival times @S404 */ }
            perform action a17 { doc /* reviews the relationship between the Calculated Takeoff Time and the proposed surface release time @S457 */ }
            perform action a18 { doc /* accepting the change @S457 */ }
            perform action a19 { doc /* protects constrained rotations @S481 */ }
            perform action a20 { doc /* checking that a recovered gate plan remains compatible with the applicable Calculated Takeoff Time @S481 */ }
            perform action a21 { doc /* reviews the effect of diversion acceptance on Calculated Takeoff Time and Target Off Block Time commitments @S502 */ }
            perform action a22 { doc /* evaluate the operational acceptability of a requested change @S633 */ }
            perform action a23 { doc /* reviews any exception raised by the Slot Allocation Engine @S671 */ }
            perform action a24 { doc /* confirms whether the swap remains consistent with regional flow objectives @S671 */ }
            perform action a25 { doc /* sends the Slot Swap Permission Email @S672 */ }
            perform action a26 { doc /* initiates manual slot procedures using a time-ordered control sheet @S722 */ }
            perform action a27 { doc /* assigns any revised Calculated Takeoff Time @S724 */ }
            perform action a28 { doc /* confirming runway capacity with the Tower Supervisor @S724 */ }
            perform action a29 { doc /* confirming surface feasibility with the Ramp Control Lead @S724 */ }
            perform action a30 { doc /* uses the Crew Duty Extension Log to check whether manually issued slot times remain operationally achievable @S726 */ }
            perform action a31 { doc /* reconciles the manual slot record with the Slot Allocation Engine @S736 */ }
            perform action a32 { doc /* resolves any conflict in the Collaborative Decision Log @S736 */ }
            perform action a33 { doc /* returning automation to control @S736 */ }
            perform action a34 { doc /* receive role profiles @S766 */ }
            perform action a35 { doc /* administer slot allocation functions @S768 */ }
            perform action a36 { doc /* review substitution activity @S798 */ }
            perform action a37 { doc /* own slot allocation reference data @S815 */ }
            perform action a38 { doc /* review slot adherence @S848 */ }
            perform action a39 { doc /* detect recurring causes of noncompliance @S848 */ }
            perform action a40 { doc /* receive training on the Slot Allocation Engine, Airport CDM Portal, and applicable Business Rules Registry entries @S870 */ }
            perform action a41 { doc /* owns slot fairness, slot compliance monitoring, and exception handling @S964 */ }
            exhibit state modes {
                state s0 { doc /* Slot Compliance State @S285 */ }
            }
        }
        part southRunwayMeter : SouthRunwayMeter {
            perform action a0 { doc /* provide additional indicators of emerging capacity loss and operational imbalance @S019 */ }
            perform action a1 { doc /* receive runway-specific capacity values @S114 */ }
            perform action a2 { doc /* maintain separate queues @S280 */ }
            perform action a3 { doc /* maintain independent queue counts @S359 */ }
            perform action a4 { doc /* applies the same planning principle to its assigned runway stream @S455 */ }
            perform action a5 { doc /* preserving separation from arrival regulation actions @S455 */ }
            perform action a6 { doc /* support independent checks of queue length @S845 */ }
        }
        part southportAirport : SouthportAirport;
        part stakeholderOrganization : StakeholderOrganization {
            perform action a0 { doc /* assign accountable representatives @S048 */ }
            perform action a1 { doc /* maintain current contact details @S048 */ }
            perform action a2 { doc /* follow agreed data use rules @S048 */ }
            perform action a3 { doc /* support post-operational review of decisions made through the Regional Flow Platform @S048 */ }
        }
        part stand : Stand {
            perform action a0 { doc /* returns to an inspection-required state @S663 */ }
            exhibit state modes {
                state s0 { doc /* inspection-required state @S663 */ }
            }
        }
        part standAccessRouting : StandAccessRouting;
        part standardServiceDeskCoverage : StandardServiceDeskCoverage;
        part stewardshipReviews : StewardshipReviews {
            perform action a0 { doc /* update training @S837 */ }
            perform action a1 { doc /* adjust validation rules @S837 */ }
            perform action a2 { doc /* improve the reliability of information @S837 */ }
        }
        part surfaceDecisionFunctions : SurfaceDecisionFunctions {
            perform action a0 { doc /* used by surface decision functions @S828 */ }
        }
        part surfaceSurveillanceAdapter : SurfaceSurveillanceAdapter {
            perform action a0 { doc /* provide the data feeds needed to maintain a current and consistent operational picture @S018 */ }
            perform action a1 { doc /* provide managed integration points with external systems @S033 */ }
            perform action a2 { doc /* consolidates position updates @S179 */ }
            perform action a3 { doc /* presents movement indications to the Airport CDM Portal @S179 */ }
            perform action a4 { doc /* confirming aircraft position, stand occupancy, and blocking conditions on critical apron lanes @S204 */ }
            perform action a5 { doc /* confirms whether an aircraft is still at stand, entering the movement area, holding short, or already committed to the departure stream @S281 */ }
            perform action a6 { doc /* confirms that aircraft leaving the pad follow the assigned route @S389 */ }
            perform action a7 { doc /* provides current movement area occupancy and equipment status indicators @S445 */ }
            perform action a8 { doc /* verifies that the apron position is physically clear @S474 */ }
            perform action a9 { doc /* normalizes apron sensing data into movement, occupancy, and blockage events @S580 */ }
            perform action a10 { doc /* produces the Runway Lighting Outage Card @S606 */ }
            perform action a11 { doc /* apply position quality checks @S828 */ }
            perform action a12 { doc /* mark uncertain observations @S828 */ }
        }
        part systemPart : System {
            perform action a0 { doc /* support rapid development of a Tactical Regulation Proposal @S022 */ }
            perform action a1 { doc /* consistent communication of the resulting Ground Delay Program @S022 */ }
            perform action a2 { doc /* help stakeholders restore scheduled flow @S023 */ }
            perform action a3 { doc /* monitoring Target Off Block Time, Calculated Takeoff Time, and Slot Compliance State performance @S023 */ }
            perform action a4 { doc /* detects a material difference from the published schedule @S104 */ }
            perform action a5 { doc /* assumes that typical service durations remain valid @S318 */ }
            perform action a6 { doc /* does not release every aircraft as soon as it becomes ready @S320 */ }
            perform action a7 { doc /* proposes a broader departure delay @S459 */ }
            perform action a8 { doc /* prioritizes removal of surface holds that constrain multiple rotations @S465 */ }
            perform action a9 { doc /* optimizing isolated punctuality impacts @S465 */ }
            perform action a10 { doc /* treats passenger disruption information as a secondary planning signal @S738 */ }
            perform action a11 { doc /* records these actions as operational context @S752 */ }
            perform action a12 { doc /* prevent a single user from creating, approving, and technically concealing a material change @S774 */ }
            perform action a13 { doc /* impose a Ground Delay Program @S953 */ }
            perform action a14 { doc /* change an Airport Acceptance Rate @S953 */ }
            perform action a15 { doc /* alter a tactical measure @S953 */ }
            exhibit state modes {
                state s0 { doc /* Adverse Weather Mode @S022,S047,S219,S319,S464 */ }
                state s1 { doc /* Capacity Reduction State @S022,S047,S220 */ }
                state s2 { doc /* Contingency Fallback State @S047,S786 */ }
                state s3 { doc /* Normal Operations @S047,S318,S397,S788 */ }
                state s4 { doc /* Recovery Phase @S023,S047,S320,S465,S951 */ }
                state s5 { doc /* Slot Compliance State @S047,S791 */ }
                state s6 { doc /* active operating state @S746 */ }
            }
        }
        part systemSupportEngineer : SystemSupportEngineer {
            perform action a0 { doc /* maintain data quality, access control, operational continuity, and controlled configuration of the Regional Flow Platform @S042 */ }
            perform action a1 { doc /* monitors portal availability, interface latency, user session faults, and synchronization status against the Time Synchronization Service @S171 */ }
            perform action a2 { doc /* investigates technical failures in submission, validation, or publication @S688 */ }
            perform action a3 { doc /* confirmed data quality @S727 */ }
            perform action a4 { doc /* classifies the technical condition @S732 */ }
            perform action a5 { doc /* isolates failed components @S732 */ }
            perform action a6 { doc /* advises whether partial restoration is safe for operational use @S732 */ }
            perform action a7 { doc /* maintain infrastructure components @S772 */ }
            perform action a8 { doc /* investigate technical faults @S772 */ }
            perform action a9 { doc /* investigate technical gaps @S807 */ }
            perform action a10 { doc /* investigate technical causes of missing, delayed, duplicated, or transformed records @S835 */ }
            perform action a11 { doc /* provide evidence needed for stewardship decisions @S835 */ }
            perform action a12 { doc /* train superusers on service status checks, access fault escalation, and safe use of the Contingency Operations Console @S877 */ }
            perform action a13 { doc /* monitor defect trends, data quality, access changes, and user adoption @S910 */ }
            perform action a14 { doc /* provide round the clock on call coverage for production incidents @S914 */ }
            perform action a15 { doc /* join the Digital Briefing Room without delay @S916 */ }
            perform action a16 { doc /* advise operational supervisors on technical status, known workarounds, data integrity concerns, and recovery options @S918 */ }
            perform action a17 { doc /* maintain an incident record @S923 */ }
            perform action a18 { doc /* verify that fallback tools, exported operational data, and restoration checkpoints are available @S927 */ }
            perform action a19 { doc /* advising that normal technical service can resume @S927 */ }
        }
        part tacticalRegulationProposal : TacticalRegulationProposal;
        part targetOffBlockTime : TargetOffBlockTime;
        part temporalSequenceChecks : TemporalSequenceChecks;
        part terminalCurbSpace : TerminalCurbSpace;
        part timeAboveThreshold : TimeAboveThreshold;
        part timeNeededToClearPassengersFromTheAircraftVicinity : TimeNeededToClearPassengersFromTheAircraftVicinity;
        part timeOrderedControlSheet : TimeOrderedControlSheet;
        part timeSynchronizationService : TimeSynchronizationService {
            perform action a0 { doc /* provide governance, security, traceability, and performance measurement capabilities @S034 */ }
            perform action a1 { doc /* provides the reference clock @S110 */ }
            perform action a2 { doc /* time-stamped all airline integration transactions @S149 */ }
            perform action a3 { doc /* keep tower, duty desk, surveillance, and portal event times aligned @S187 */ }
            perform action a4 { doc /* time stamped all allocation runs @S245 */ }
            perform action a5 { doc /* provides the reference clock for all target time calculations @S256 */ }
            perform action a6 { doc /* timestamped Fluid status updates @S382 */ }
            perform action a7 { doc /* provides the common time reference @S651 */ }
            perform action a8 { doc /* provide the common time basis @S824 */ }
        }
        part towerSequenceManager : TowerSequenceManager {
            perform action a0 { doc /* support the transition from regional planning decisions to executable airport and tower actions @S017 */ }
            perform action a1 { doc /* support tactical airport and regional coordination @S032 */ }
            perform action a2 { doc /* reflects the current runway configuration @S089 */ }
            perform action a3 { doc /* support local sequencing decisions @S180 */ }
            perform action a4 { doc /* receives the current ramp intent @S217 */ }
            perform action a5 { doc /* maintains the tactical runway sequence expectation @S254 */ }
            perform action a6 { doc /* highlights cases where the Calculated Takeoff Time is inconsistent with the local departure order @S254 */ }
            perform action a7 { doc /* translates the frozen operational targets from the regional flow process into an executable runway order for departures @S275 */ }
            perform action a8 { doc /* builds a provisional order by runway, departure fix, aircraft wake category, and locally configured spacing rule @S279 */ }
            perform action a9 { doc /* applies the active spacing rules from the Business Rules Registry @S297 */ }
            perform action a10 { doc /* highlights flights that may miss their Calculated Takeoff Time @S297 */ }
            perform action a11 { doc /* refresh affected departure sequence advisories @S334 */ }
            perform action a12 { doc /* reserves departure sequence positions @S380 */ }
            perform action a13 { doc /* confirms stable spacing and runway occupancy performance @S411 */ }
            perform action a14 { doc /* uses the hold advice to prevent a departure from being sequenced ahead of a fueling constraint @S450 */ }
            perform action a15 { doc /* receives a stable readiness indicator and an escalation flag @S536 */ }
            perform action a16 { doc /* does not advance an aircraft toward an active departure sequence @S552 */ }
            perform action a17 { doc /* considers confirmed apron blockage @S583 */ }
            perform action a18 { doc /* sequence advisory @S601 */ }
            perform action a19 { doc /* displays the accepted constraint @S702 */ }
            perform action a20 { doc /* provide actual movement milestones @S801 */ }
            perform action a21 { doc /* provide runway sequence counts @S844 */ }
            exhibit state modes {
                state s0 { doc /* Adverse Weather Mode @S297 */ }
                state s1 { doc /* Capacity Reduction State @S297 */ }
            }
        }
        part towerSequenceWorkflow : TowerSequenceWorkflow {
            perform action a0 { doc /* emphasizes measured acceleration rather than first-come recovery @S298 */ }
        }
        part towerSupervisor : TowerSupervisor {
            perform action a0 { doc /* represent local airport, tower, ramp, handling, and winter operations considerations @S040 */ }
            perform action a1 { doc /* sends the Runway Inspection Note @S060 */ }
            perform action a2 { doc /* declares anticipated runway configuration, usable operating length assumptions, and any local sequencing constraints @S061 */ }
            perform action a3 { doc /* confirms that the Tower Sequence Manager reflects the current runway configuration @S089 */ }
            perform action a4 { doc /* reviews metering effects in the Tower Sequence Manager @S143 */ }
            perform action a5 { doc /* reviewing runway configuration assumptions, departure sequence feasibility, and tactical tower constraints @S160 */ }
            perform action a6 { doc /* keeps the Airport Duty Manager informed of conditions @S175 */ }
            perform action a7 { doc /* agree on the operational interpretation @S183 */ }
            perform action a8 { doc /* verifies that any proposed reduction in declared runway use is consistent with observed traffic, controller workload, and the current safety position @S189 */ }
            perform action a9 { doc /* confirmed that the movement can be integrated with the active ground route and runway plan @S202 */ }
            perform action a10 { doc /* reject a proposed departure opportunity @S243 */ }
            perform action a11 { doc /* challenge a proposed Calculated Takeoff Time @S263 */ }
            perform action a12 { doc /* uses the Tower Sequence Manager to confirm that each flight can be advanced without creating unsafe surface compression @S277 */ }
            perform action a13 { doc /* view both queues together @S280 */ }
            perform action a14 { doc /* intervene @S287 */ }
            perform action a15 { doc /* compares pad release expectations with runway queue gaps @S296 */ }
            perform action a16 { doc /* accepting an aircraft into the active departure stream @S296 */ }
            perform action a17 { doc /* confirm that any revised off-block sequence remains compatible with the Departure Metering Service @S313 */ }
            perform action a18 { doc /* monitors whether the planned release rate remains compatible with departure spacing and runway crossing demand @S358 */ }
            perform action a19 { doc /* agree whether the metering horizon should be extended @S368 */ }
            perform action a20 { doc /* protects runway departure spacing @S388 */ }
            perform action a21 { doc /* confirms whether the proposed landing rate is compatible @S401 */ }
            perform action a22 { doc /* see runway assignment pressure, airborne sequence spacing, and expected crossing points @S425 */ }
            perform action a23 { doc /* coordinates airborne sequencing with the Airspace Sector Planner @S500 */ }
            perform action a24 { doc /* uses the same result to understand whether a runway queue is being held @S605 */ }
            perform action a25 { doc /* does not use a stand readiness indication as clearance for aircraft movement @S655 */ }
            perform action a26 { doc /* reject a swap @S676 */ }
            perform action a27 { doc /* confirm which runway lighting elements are unavailable @S693 */ }
            perform action a28 { doc /* approving the operational status shown in the Tower Sequence Manager @S693 */ }
            perform action a29 { doc /* retains authority over tactical runway sequencing @S748 */ }
            perform action a30 { doc /* reject any advisory that would impair safe separation, wake spacing, or local controller workload @S748 */ }
            perform action a31 { doc /* receive role profiles @S766 */ }
            perform action a32 { doc /* operate the Tower Sequence Manager @S769 */ }
            perform action a33 { doc /* view runway metering information @S769 */ }
            perform action a34 { doc /* own tower sequence status data @S817 */ }
            perform action a35 { doc /* receive practical training on the Tower Sequence Manager, Departure Metering Service, Arrival Regulation Console, North Runway Meter, and South Runway Meter @S866 */ }
            perform action a36 { doc /* retain operational command authority @S917 */ }
            perform action a37 { doc /* compare recommendations with actual outcomes @S959 */ }
        }
        part towerSupervisoryPersonnel : TowerSupervisoryPersonnel;
        part towingProviders : TowingProviders;
        part trainingAssessments : TrainingAssessments {
            perform action a0 { doc /* verify that users can identify stale data, time synchronization problems, duplicate flights, conflicting constraints, and inappropriate automation reliance @S886 */ }
        }
        part turnaroundStatus : TurnaroundStatus;
        part users : Users {
            perform action a0 { doc /* compare automated recommendations with local knowledge @S883 */ }
            perform action a1 { doc /* document significant decisions in the Collaborative Decision Log @S883 */ }
            perform action a2 { doc /* explain departures from system proposals @S883 */ }
            perform action a3 { doc /* identify stale data, time synchronization problems, duplicate flights, conflicting constraints, and inappropriate automation reliance @S886 */ }
        }
        part validationRules : ValidationRules;
        part vehicles : Vehicles;
        part weatherFeed : WeatherFeed {
            exhibit state modes {
                state s0 { doc /* degraded @S111 */ }
            }
        }
        part weatherIngestGateway : WeatherIngestGateway {
            perform action a0 { doc /* provide the data feeds needed to maintain a current and consistent operational picture @S018 */ }
            perform action a1 { doc /* provide managed integration points with external systems @S033 */ }
            perform action a2 { doc /* makes the outlook available to the Capacity Assessment Module @S057 */ }
            perform action a3 { doc /* preserves the forecast issue time for audit and later performance review @S057 */ }
            perform action a4 { doc /* normalizes external and local meteorological feeds @S102 */ }
            perform action a5 { doc /* accepts aviation forecasts, radar-derived precipitation fields, lightning alerts, wind forecasts, ceiling and visibility forecasts, and runway condition weather inputs from approved sources @S108 */ }
            perform action a6 { doc /* marks the feed as degraded @S111 */ }
            perform action a7 { doc /* issue time-stamped weather condition updates @S182 */ }
            perform action a8 { doc /* updates the arrival model @S409 */ }
            perform action a9 { doc /* accepted operational weather classification inputs @S819 */ }
        }
        part weatherProducts : WeatherProducts;
        part westApronSensor : WestApronSensor {
            perform action a0 { doc /* provide additional indicators of emerging capacity loss and operational imbalance @S019 */ }
            perform action a1 { doc /* detecting aircraft movement @S282 */ }
            perform action a2 { doc /* provide supporting movement evidence for the reopened area @S474 */ }
            perform action a3 { doc /* provide supporting surveillance cues @S645 */ }
            perform action a4 { doc /* support independent checks of queue length @S845 */ }
        }
        part workstationLayouts : WorkstationLayouts {
            perform action a0 { doc /* support rapid comparison between the Common Situation Display, Airport CDM Portal, Tower Sequence Manager, Ramp Movement Board, and relevant advisory messages @S885 */ }
        }
        flow f0 of OperationalReadinessInformationItem from airportStakeholders to airportCDMPortal { doc /* @S016 */ }
        flow f1 of SharedViewOfDemandCapacityConstraintsAndActiveTrafficManagementMeasuresItem from commonSituationDisplay to authorizedUsers { doc /* @S020 */ }
        flow f2 of NormalizedScheduleItem from flightDataExchange to demandPredictionService { doc /* @S053 */ }
        flow f3 of MorningWeatherOutlookItem from meteorologyBriefingOfficer to weatherIngestGateway { doc /* @S057 */ }
        flow f4 of MorningWeatherOutlookItem from weatherIngestGateway to capacityAssessmentModule { doc /* @S057 */ }
        flow f5 of InformationItem from rampMovementBoard to rampControlLead { doc /* @S063 */ }
        flow f6 of InformationItem from eastApronSensor to rampControlLead { doc /* @S063 */ }
        flow f7 of InformationItem from westApronSensor to rampControlLead { doc /* @S063 */ }
        flow f8 of MorningWeatherOutlookItem from meteorologyBriefingOfficer to capacityAssessmentModule { doc /* @S066 */ }
        flow f9 of UnresolvedAssumptionsItem from digitalBriefingRoom to collaborativeDecisionLog { doc /* @S071 */ }
        flow f10 of MorningPlanAvailabilityNotificationItem from alertDistributionHub to participatingRoles { doc /* @S073 */ }
        flow f11 of AirportCapacityPlanItem from digitalBriefingRoom to regionalFlowManager { doc /* @S078 */ }
        flow f12 of GroundDelayProgramItem from systemPart to regionalFlowManager { doc /* @S078 */ }
        flow f13 of BusinessRulesRegistryParametersItem from businessRulesRegistry to slotAllocationEngine { doc /* @S080 */ }
        flow f14 of ExternalCoordinationOutcomesItem from networkOperationsLiaison to collaborativeDecisionLog { doc /* @S084 */ }
        flow f15 of ForecastConfidenceTimingRiskAndExpectedOperationalImpactItem from meteorologyBriefingOfficer to digitalBriefingRoom { doc /* @S086 */ }
        flow f16 of DataItem from weatherIngestGateway to meteorologyBriefingOfficer { doc /* @S086 */ }
        flow f17 of MaterialDeviationsItem from groundHandlingDispatcher to airportDutyManager { doc /* @S091 */ }
        flow f18 of AlertItem from militaryAirspaceLiaison to regionalFlowManager { doc /* @S093 */ }
        flow f19 of OutputsItem from departureMeteringService to commonSituationDisplay { doc /* @S095 */ }
        flow f20 of OutputsItem from arrivalRegulationConsole to commonSituationDisplay { doc /* @S095 */ }
        flow f21 of SynchronizedTimestampsItem from timeSynchronizationService to auditEventLedger { doc /* @S098 */ }
        flow f22 of DecisionsAndUnresolvedIssuesItem from accountableRoles to performanceAnalyticsWarehouse { doc /* @S099 */ }
        flow f23 of DecisionsAndUnresolvedIssuesItem from performanceAnalyticsWarehouse to postOperationsReport { doc /* @S099 */ }
        flow f24 of DemandForecastItem from demandPredictionService to regionalFlowPlatform { doc /* @S101 */ }
        flow f25 of FiledFlightInformationItem from flightDataExchange to demandPredictionService { doc /* @S103 */ }
        flow f26 of CurrentOperatingScheduleItem from airlineInterfaceAdapter to demandPredictionService { doc /* @S103 */ }
        flow f27 of AirportCapacityPlanItem from digitalBriefingRoom to capacityAssessmentModule { doc /* @S107 */ }
        flow f28 of DemandProjectionsItem from demandPredictionService to capacityAssessmentModule { doc /* @S107 */ }
        flow f29 of WeatherFeedItem from weatherIngestGateway to regionalFlowPlatform { doc /* @S109 */ }
        flow f30 of RunwaySpecificCapacityValuesItem from capacityAssessmentModule to northRunwayMeter { doc /* @S114 */ }
        flow f31 of RunwaySpecificCapacityValuesItem from capacityAssessmentModule to southRunwayMeter { doc /* @S114 */ }
        flow f32 of ForecastDemandAssessedCapacityAndActiveGroundDelayProgramEffectsItem from commonSituationDisplay to regionalFlowManager { doc /* @S117 */ }
        flow f33 of CapacityChangeNotificationItem from alertDistributionHub to regionalFlowManager { doc /* @S121 */ }
        flow f34 of CapacityChangeNotificationItem from alertDistributionHub to towerSupervisor { doc /* @S121 */ }
        flow f35 of CapacityChangeNotificationItem from alertDistributionHub to airlineOperationsCoordinator { doc /* @S121 */ }
        flow f36 of SynchronizedTimestampsItem from timeSynchronizationService to collaborativeDecisionLog { doc /* @S122 */ }
        flow f37 of TraceItem from auditEventLedger to performanceAnalyticsWarehouse { doc /* @S123 */ }
        flow f38 of FlightIntentMessageItem from airlineOperationsCentre to airlineInterfaceAdapter { doc /* @S126 */ }
        flow f39 of AcceptedIntentDataItem from airlineInterfaceAdapter to flightDataExchange { doc /* @S128 */ }
        flow f40 of CurrentAirlineIntentsItem from airlineOperationsCentre to demandPredictionService { doc /* @S131 */ }
        flow f42 of DemandItem from demandPredictionService to capacityAssessmentModule { doc /* @S132 */ }
        flow f43 of ConstraintsItem from airlineInterfaceAdapter to airlineOperationsCentre { doc /* @S135 */ }
        flow f44 of ConstraintsItem from airlineInterfaceAdapter to collaborativeDecisionLog { doc /* @S145 */ }
        flow f45 of AirlineIntegrationTransactionsItem from timeSynchronizationService to auditEventLedger { doc /* @S149 */ }
        flow f46 of AcceptedSlotAdjustmentsRejectedSlotAdjustmentsAndUnresolvedSlotConflictsItem from slotCoordinator to collaborativeDecisionLog { doc /* @S161 */ }
        flow f47 of WeatherInterpretationForecastConfidenceAndExpectedTimingOfOperationalImpactsItem from meteorologyBriefingOfficer to airportCDMPortal { doc /* @S163 */ }
        flow f48 of RegionalDemandAndConstraintContextItem from regionalFlowPlatform to airportCDMPortal { doc /* @S164 */ }
        flow f49 of StaleMilestoneNotificationItem from airportCDMPortal to alertDistributionHub { doc /* @S166 */ }
        flow f50 of MandatoryFieldsPermissibleStatusValuesRetentionRulesAndDataQualityThresholdsItem from dataGovernanceSteward to airportCDMPortal { doc /* @S170 */ }
        flow f51 of ConditionsItem from towerSupervisor to airportDutyManager { doc /* @S175 */ }
        flow f52 of PositionUpdatesItem from eastApronSensor to surfaceSurveillanceAdapter { doc /* @S179 */ }
        flow f53 of PositionUpdatesItem from westApronSensor to surfaceSurveillanceAdapter { doc /* @S179 */ }
        flow f54 of MovementIndicationsItem from surfaceSurveillanceAdapter to airportCDMPortal { doc /* @S179 */ }
        flow f55 of RunwayInspectionNoteItem from towerSupervisor to airportDutyManager { doc /* @S181 */ }
        flow f56 of DutyDeskConfirmationsItem from airportDutyDesk to airportCDMPortal { doc /* @S185 */ }
        flow f57 of TransactionItem from identityAccessService to auditEventLedger { doc /* @S194 */ }
        flow f58 of InputsItem from surfaceSurveillanceAdapter to rampControlLead { doc /* @S204 */ }
        flow f59 of IndicationsItem from eastApronSensor to rampControlLead { doc /* @S205 */ }
        flow f60 of IndicationsItem from westApronSensor to rampControlLead { doc /* @S205 */ }
        flow f61 of AlertItem from gateConflictDetector to rampControlLead { doc /* @S210 */ }
        flow f62 of ConstraintsItem from handlingResourcePlanner to rampControlLead { doc /* @S213 */ }
        flow f63 of CurrentRampIntentItem from systemPart to towerSequenceManager { doc /* @S217 */ }
        flow f64 of ConditionItem from rampControlLead to towerSupervisor { doc /* @S218 */ }
        flow f65 of ConditionItem from rampControlLead to airportDutyManager { doc /* @S218 */ }
        flow f66 of MovementUpdatesItem from rampMovementBoard to auditEventLedger { doc /* @S222 */ }
        flow f67 of DemandItem from demandPredictionService to slotAllocationEngine { doc /* @S225 */ }
        flow f68 of ConstraintsItem from capacityAssessmentModule to slotAllocationEngine { doc /* @S225 */ }
        flow f69 of CrewBusDelaySlipItem from groundHandlingDispatcher to airlineOperationsCoordinator { doc /* @S237 */ }
        flow f70 of AcceptedOrRejectedExemptionItem from slotCoordinator to collaborativeDecisionLog { doc /* @S239 */ }
        flow f71 of ProposedDepartureOpportunitiesAndAssociatedCalculatedTakeoffTimeValuesItem from departureMeteringService to towerSequenceManager { doc /* @S242 */ }
        flow f73 of ProposedDepartureOpportunitiesAndAssociatedCalculatedTakeoffTimeValuesItem from departureMeteringService to slotCoordinator { doc /* @S258 */ }
        flow f74 of CurrentAgreedTargetSetItem from commonSituationDisplay to operationalParticipants { doc /* @S265 */ }
        flow f75 of BoardingLoadingDoorClosureAndTowReadinessMilestonesItem from groundHandlingDispatcher to operationalInterface { doc /* @S292 */ }
        flow f76 of TowerReadinessChangesItem from airportCDMPortal to authenticatedAirlineAndHandlingUsers { doc /* @S293 */ }
        flow f77 of ActiveSpacingRulesItem from businessRulesRegistry to towerSequenceManager { doc /* @S297 */ }
        flow f78 of ExpectedServiceCompletionTimesItem from groundHandlingDispatcher to handlingResourcePlanner { doc /* @S302 */ }
        flow f79 of StandTowRequestFormItem from rampControlLead to handlingResourcePlanner { doc /* @S304 */ }
        flow f80 of ResourceDrivenFeasibilityStatusItem from airportCDMPortal to airlineOperationsCoordinator { doc /* @S312 */ }
        flow f81 of ResourceDrivenFeasibilityStatusItem from airportCDMPortal to aircraftOperatorRepresentative { doc /* @S312 */ }
        flow f82 of ConstraintItem from handlingResourcePlanner to systemPart { doc /* @S318 */ }
        flow f83 of DemandItem from demandPredictionService to sectorLoadMonitor { doc /* @S329 */ }
        flow f84 of SubscriptionRulesItem from businessRulesRegistry to alertDistributionHub { doc /* @S332 */ }
        flow f85 of AirspaceAlertAcknowledgementAndDownstreamDecisionItem from regionalFlowPlatform to auditEventLedger { doc /* @S333 */ }
        flow f86 of ActiveRestrictionStatusExpectedOperationalEffectAndRelatedCoordinationNotesItem from airportCDMPortal to commonSituationDisplay { doc /* @S337 */ }
        flow f87 of AirportCapacityPlanItem from digitalBriefingRoom to regionalFlowPlatform { doc /* @S349 */ }
        flow f89 of ReconsiderationRequestItem from aircraftOperatorRepresentative to airportCDMPortal { doc /* @S363 */ }
        flow f90 of AffectedRunwayQueueItem from alertDistributionHub to commonSituationDisplay { doc /* @S366 */ }
        flow f91 of AirportCapacityPlanItem from digitalBriefingRoom to slotAllocationEngine { doc /* @S374 */ }
        flow f92 of DeicingPadQueueCardItem from deicingCoordinator to rampControlLead { doc /* @S378 */ }
        flow f93 of GroundDelayProgramItem from systemPart to slotAllocationEngine { doc /* @S398 */ }
        flow f94 of TemporaryRestrictionNoticeItem from militaryAirspaceLiaison to regionalFlowManager { doc /* @S399 */ }
        flow f95 of OperationalBasisForEachValueItem from capacityAssessmentModule to commonSituationDisplay { doc /* @S400 */ }
        flow f96 of ActiveSpacingRulesItem from businessRulesRegistry to slotAllocationEngine { doc /* @S404 */ }
        flow f97 of ArrivalPlanItem from airportCDMPortal to aircraftOperatorRepresentative { doc /* @S405 */ }
        flow f98 of AcknowledgementsItem from airportCDMPortal to collaborativeDecisionLog { doc /* @S405 */ }
        flow f99 of RecordedRegulationHistoryItem from auditEventLedger to performanceAnalyticsWarehouse { doc /* @S418 */ }
        flow f100 of CombinedTacticalViewItem from integratedTacticalManagementPosition to regionalFlowManager { doc /* @S420 */ }
        flow f101 of BaseMapTimelineFlightListAndMeasureStatusPanelsItem from commonSituationDisplay to integratedTacticalManagementPosition { doc /* @S421 */ }
        flow f102 of RunwayAssignmentPressureAirborneSequenceSpacingAndExpectedCrossingPointsItem from commonSituationDisplay to towerSupervisor { doc /* @S425 */ }
        flow f103 of AgreedTargetOffBlockTimeValuesAndStakeholderRemarksItem from airportCDMPortal to integratedTacticalManagementPosition { doc /* @S429 */ }
        flow f104 of SectorDemandItem from sectorLoadMonitor to airspaceSectorPlanner { doc /* @S432 */ }
        flow f105 of WeatherImpactsItem from weatherIngestGateway to meteorologyBriefingOfficer { doc /* @S434 */ }
        flow f106 of HandlingResourcePlannerViewItem from handlingResourcePlanner to groundHandlingDispatcher { doc /* @S438 */ }
        flow f107 of CurrentMovementAreaOccupancyAndEquipmentStatusIndicatorsItem from surfaceSurveillanceAdapter to rampMovementBoard { doc /* @S445 */ }
        flow f108 of CurrentMovementAreaOccupancyAndEquipmentStatusIndicatorsItem from surfaceSurveillanceAdapter to towerSequenceManager { doc /* @S445 */ }
        flow f109 of OperationalSignificanceOfTheConditionItem from airportDutyManager to airportCDMPortal { doc /* @S447 */ }
        flow f110 of SurfaceConstraintsItem from eastApronSensor to capacityAssessmentModule { doc /* @S448 */ }
        flow f111 of FuelTruckHoldAdviceItem from rampMovementBoard to towerSequenceManager { doc /* @S450 */ }
        flow f112 of SurfaceSurveillanceInputsItem from surfaceSurveillanceAdapter to northRunwayMeter { doc /* @S454 */ }
        flow f113 of CandidatePushbackSpacingItem from departureMeteringService to slotAllocationEngine { doc /* @S456 */ }
        flow f114 of ActiveSurfaceAdvisoriesItem from commonSituationDisplay to authorizedUsers { doc /* @S462 */ }
        flow f115 of SurfaceEquipmentAndApronCongestionAdvisoriesItem from alertDistributionHub to regionalFlowManager { doc /* @S463 */ }
        flow f116 of GateReopeningMemoItem from gateConflictDetector to airlineOperationsCoordinator { doc /* @S472 */ }
        flow f117 of AirportCapacityPlanItem from digitalBriefingRoom to demandPredictionService { doc /* @S493 */ }
        flow f118 of TacticalRegulationProposalItem from alertDistributionHub to airspaceSectorPlanner { doc /* @S501 */ }
        flow f119 of PushbackWindowTokenItem from slotAllocationEngine to airportCDMPortal { doc /* @S503 */ }
        flow f120 of DiversionRationalePriorityClassificationResourceCommitmentAndAgreedRecoveryTargetItem from digitalBriefingRoom to collaborativeDecisionLog { doc /* @S506 */ }
        flow f121 of ConstraintItem from handlingResourcePlanner to groundHandlingDispatcher { doc /* @S508 */ }
        flow f122 of LateBaggageTagListItem from airlineInterfaceAdapter to groundHandlingDispatcher { doc /* @S519 */ }
        flow f123 of PlannedRemoteStandOperatingPostureItem from airportDutyManager to airportCDMPortal { doc /* @S544 */ }
        flow f124 of TowbarShortageReportItem from groundHandlingDispatcher to rampControlLead { doc /* @S556 */ }
        flow f125 of MedicalDiversionNoticeItem from airportDutyManager to arrivalRegulationConsole { doc /* @S576 */ }
        flow f126 of SectorDemandItem from sectorLoadMonitor to regionalFlowPlatform { doc /* @S593 */ }
        flow f127 of ScheduledMovementsItem from flightDataExchange to regionalFlowPlatform { doc /* @S593 */ }
        flow f128 of PredictedReadinessItem from demandPredictionService to regionalFlowPlatform { doc /* @S593 */ }
        flow f129 of DepartureFixLoadSheetItem from sectorLoadMonitor to regionalFlowManager { doc /* @S598 */ }
        flow f130 of NotificationsItem from alertDistributionHub to regionalFlowManager { doc /* @S614 */ }
        flow f131 of NotificationsItem from alertDistributionHub to towerSupervisor { doc /* @S614 */ }
        flow f132 of NotificationsItem from alertDistributionHub to rampControlLead { doc /* @S614 */ }
        flow f133 of NotificationsItem from alertDistributionHub to slotCoordinator { doc /* @S614 */ }
        flow f134 of NotificationsItem from alertDistributionHub to networkOperationsLiaison { doc /* @S614 */ }
        flow f135 of CrewLegalityInputsItem from aircraftOperatorRepresentative to airlineInterfaceAdapter { doc /* @S622 */ }
        flow f136 of CrewLegalityInputsItem from aircraftOperatorRepresentative to airportCDMPortal { doc /* @S622 */ }
        flow f137 of ConstraintsItem from airlineInterfaceAdapter to slotAllocationEngine { doc /* @S625 */ }
        flow f138 of FeasibilityResultAndTimingBoundaryItem from airportCDMPortal to departureMeteringService { doc /* @S626 */ }
        flow f139 of CrewLegalityImpactsItem from commonSituationDisplay to authorizedUsers { doc /* @S627 */ }
        flow f140 of RemoteStandShuttleCountItem from handlingResourcePlanner to airportCDMPortal { doc /* @S648 */ }
        flow f141 of PersonnelEquipmentOrCleaningVehiclesReassignmentItem from groundHandlingDispatcher to handlingResourcePlanner { doc /* @S653 */ }
        flow f142 of StandReadinessStatusItem from rampMovementBoard to gateConflictDetector { doc /* @S657 */ }
        flow f143 of ToleranceItem from businessRulesRegistry to slotAllocationEngine { doc /* @S659 */ }
        flow f144 of ProposedSubstitutionItem from airlineOperationsCoordinator to airportCDMPortal { doc /* @S667 */ }
        flow f145 of ExceptionItem from slotAllocationEngine to slotCoordinator { doc /* @S671 */ }
        flow f146 of ConcurrenceItem from aircraftOperatorRepresentative to airportCDMPortal { doc /* @S673 */ }
        flow f147 of StandOccupancyPushbackSpacingAndTugAvailabilityItem from rampMovementBoard to rampControlLead { doc /* @S677 */ }
        flow f148 of ApronSweepCompletionNoteItem from rampControlLead to airportDutyManager { doc /* @S678 */ }
        flow f149 of CustomsHoldReleaseNoteItem from airportDutyManager to airlineOperationsCoordinator { doc /* @S679 */ }
        flow f150 of RunwayLightingOutageCardItem from surfaceSurveillanceAdapter to towerSupervisor { doc /* @S693 */ }
        flow f152 of RevisedInputsItem from departureMeteringService to slotAllocationEngine { doc /* @S699 */ }
        flow f153 of ConstraintItem from handlingResourcePlanner to alertDistributionHub { doc /* @S705 */ }
        flow f154 of InfrastructureEventsItem from airportCDMPortal to performanceAnalyticsWarehouse { doc /* @S712 */ }
        flow f156 of CrewDutyExtensionLogItem from aircraftOperatorRepresentative to slotCoordinator { doc /* @S726 */ }
        flow f157 of CurrentOperatingBasisItem from airportDutyManager to digitalBriefingRoom { doc /* @S734 */ }
        flow f159 of LoggedRationaleItem from collaborativeDecisionLog to performanceAnalyticsWarehouse { doc /* @S760 */ }
        flow f160 of TimeItem from timeSynchronizationService to auditEventLedger { doc /* @S778 */ }
        flow f161 of SlotComplianceEventsItem from regionalFlowPlatform to auditEventLedger { doc /* @S789 */ }
        flow f162 of TimeSourceItem from timeSynchronizationService to auditEventLedger { doc /* @S792 */ }
        flow f163 of AuthenticatedRoleItem from identityAccessService to airportCDMPortal { doc /* @S793 */ }
        flow f164 of SlotSwapPermissionEmailItem from slotCoordinator to airlineOperationsCoordinator { doc /* @S795 */ }
        flow f165 of FreezeHorizonItem from businessRulesRegistry to regionalFlowManager { doc /* @S800 */ }
        flow f166 of OperationalWeatherClassificationInputsItem from meteorologyBriefingOfficer to weatherIngestGateway { doc /* @S819 */ }
        flow f167 of CommonTimeBasisItem from timeSynchronizationService to regionalFlowPlatform { doc /* @S824 */ }
        flow f168 of ObservationsItem from surfaceSurveillanceAdapter to surfaceDecisionFunctions { doc /* @S828 */ }
        flow f169 of DispositionItem from dataGovernanceSteward to auditEventLedger { doc /* @S833 */ }
        flow f170 of UrgentDiscrepanciesItem from alertDistributionHub to digitalBriefingRoom { doc /* @S834 */ }
        flow f171 of DataQualityMeasuresItem from performanceAnalyticsWarehouse to stewardshipReviews { doc /* @S837 */ }
        flow f172 of UnconstrainedDemandItem from demandPredictionService to performanceAnalyticsWarehouse { doc /* @S840 */ }
        flow f173 of RegulatedDemandItem from slotAllocationEngine to performanceAnalyticsWarehouse { doc /* @S840 */ }
        flow f174 of RealizedMovementTimesItem from flightDataExchange to performanceAnalyticsWarehouse { doc /* @S840 */ }
        flow f175 of PrincipalDelayAbsorptionIndicatorItem from principalDelayAbsorptionIndicator to regionalFlowManager { doc /* @S842 */ }
        flow f176 of PassengerMisconnectCountItem from airlineOperationsCoordinator to departureMeteringService { doc /* @S851 */ }
        flow f177 of SignificantDecisionsItem from users to collaborativeDecisionLog { doc /* @S883 */ }
        flow f178 of EvidenceItem from performanceAnalyticsWarehouse to postExerciseReviews { doc /* @S887 */ }
        flow f179 of EvidenceItem from auditEventLedger to postExerciseReviews { doc /* @S887 */ }
        flow f180 of ParallelOutputsItem from regionalFlowPlatform to operationalUsers { doc /* @S905 */ }
        flow f181 of OperationalDecisionsItem from localUsers to airportCDMPortal { doc /* @S907 */ }
        flow f182 of TechnicalStatusKnownWorkaroundsDataIntegrityConcernsAndRecoveryOptionsItem from systemSupportEngineer to operationalSupervisors { doc /* @S918 */ }
        flow f183 of RicherIntentDataItem from flightDataExchange to demandPredictionService { doc /* @S941 */ }
        flow f184 of MachineAssistedRecoveryOptionsItem from contingencyOperationsConsole to commonSituationDisplay { doc /* @S952 */ }
        flow f186 of CalculatedTakeoffTimeAndTargetOffBlockTimeItem from commonSituationDisplay to slotCoordinator { doc /* joined @S685,S161 */ }
        flow f187 of CalculatedTakeoffTimeAndTargetOffBlockTimeItem from commonSituationDisplay to airlineOperationsCoordinator { doc /* joined @S685,S259 */ }
        flow f188 of CalculatedTakeoffTimeAndTargetOffBlockTimeItem from commonSituationDisplay to collaborativeDecisionLog { doc /* joined @S685,S369 */ }
        flow f189 of CalculatedTakeoffTimeAndTargetOffBlockTimeItem from commonSituationDisplay to auditEventLedger { doc /* joined @S685,S369 */ }
        flow f190 of CalculatedTakeoffTimeAndTargetOffBlockTimeItem from commonSituationDisplay to slotAllocationEngine { doc /* joined @S685,S625 */ }
        flow f191 of CalculatedTakeoffTimeAndTargetOffBlockTimeItem from commonSituationDisplay to trainingAssessments { doc /* joined @S685,S886 */ }
    }
    requirement def R0 { doc /* The Airline Operations Coordinator, Aircraft Operator Representative, Airport Duty Manager, Tower Supervisor, Ramp Control Lead, and Slot Coordinator require a common basis for decisions rather than separate local views of the same operational picture. @S011 */ subject s : AirlineOperationsCoordinator; }
    requirement def R1 { doc /* The Common Situation Display is expected to give authorized users a shared view of demand, capacity, constraints, and active traffic management measures. @S020 */ subject s : CommonSituationDisplay; }
    requirement def R2 { doc /* The Collaborative Decision Log is expected to preserve the rationale, timing, and authorization of material operational decisions. @S021 */ subject s : CollaborativeDecisionLog; }
    requirement def R3 { doc /* The Audit Event Ledger is expected to preserve the rationale, timing, and authorization of material operational decisions. @S021 */ subject s : AuditEventLedger; }
    requirement def R4 { doc /* During Adverse Weather Mode or Capacity Reduction State, the system must support rapid development of a Tactical Regulation Proposal and consistent communication of the resulting Ground Delay Program when one is required. @S022 */ subject s : System; }
    requirement def R5 { doc /* During Recovery Phase, the system must help stakeholders restore scheduled flow while monitoring Target Off Block Time, Calculated Takeoff Time, and Slot Compliance State performance. @S023 */ subject s : System; }
    requirement def R6 { doc /* Participation in the regional system requires each stakeholder organization to assign accountable representatives, maintain current contact details, follow agreed data use rules, and support post-operational review of decisions made through the Regional Flow Platform. @S048 */ subject s : StakeholderOrganization; }
    requirement def R7 { doc /* conditional availability must be treated as uncertain @S059 */ subject s : MilitaryAirspaceLiaison; }
    requirement def R8 { doc /* changes must be entered through controlled Regional Flow Platform functions @S073 */ subject s : RegionalFlowPlatform; }
    requirement def R9 { doc /* is responsible for ensuring that operator commitments entered in the Airport CDM Portal are operationally achievable @S082 */ subject s : AircraftOperatorRepresentative; }
    requirement def R10 { doc /* The Departure Metering Service and Arrival Regulation Console are used only under the authority of the accountable flow roles, and their outputs must remain visible on the Common Situation Display. @S095 */ subject s : DepartureMeteringService; }
    requirement def R11 { doc /* The Departure Metering Service and Arrival Regulation Console are used only under the authority of the accountable flow roles, and their outputs must remain visible on the Common Situation Display. @S095 */ subject s : ArrivalRegulationConsole; }
    requirement def R12 { doc /* Escalation to the Emergency Response Coordinator is required when a safety event, security event, or emergency response activity may affect airport acceptance, surface movement, or airspace availability. @S096 */ subject s : EmergencyResponseCoordinator; }
    requirement def R13 { doc /* During Adverse Weather Mode or a Capacity Reduction State, airline operations centres are expected to submit conservative intents that distinguish firm operating plans from speculative recovery options. @S146 */ subject s : AirlineOperationsCentre; }
    requirement def R14 { doc /* The Airline Operations Coordinator is responsible for keeping the Flight Intent Message status, Target Off Block Time, passenger readiness indicator, and aircraft operational constraint notes current for each represented flight. @S157 */ subject s : AirlineOperationsCoordinator; }
    requirement def R15 { doc /* Cedarbell shall expose the current regional demand and constraint context to the shared workspace at each publication cycle without requiring manual re-entry. @S164 */ subject s : RegionalFlowPlatform; }
    requirement def R16 { doc /* When a milestone becomes stale, the Airport CDM Portal shall highlight the affected flight and notify the role accountable for the next update through the Alert Distribution Hub. @S166 */ subject s : AirportCDMPortal; }
    requirement def R17 { doc /* Each airport participant shall update a material change within two minutes of becoming aware of it during Normal Operations and within one minute during Adverse Weather Mode or Capacity Reduction State. @S167 */ subject s : AirportParticipant; }
    requirement def R18 { doc /* If the exact value is not yet known, the accountable participant shall enter a provisional value with an uncertainty flag rather than leaving the milestone unchanged. @S168 */ subject s : AirportParticipant; }
    requirement def R19 { doc /* During Contingency Fallback State, the Airport CDM Portal shall preserve the last synchronized milestone set and clearly mark any updates entered under degraded operating procedures. @S172 */ subject s : AirportCDMPortal; }
    requirement def R20 { doc /* Orchard shall issue time-stamped weather condition updates for use in tower and airport duty coordination. @S182 */ subject s : WeatherIngestGateway; }
    requirement def R21 { doc /* The Time Synchronization Service shall keep tower, duty desk, surveillance, and portal event times aligned so that later review can reconstruct the sequence of events. @S187 */ subject s : TimeSynchronizationService; }
    requirement def R22 { doc /* The Ramp Control Lead shall not release a pushback until the Tower Supervisor has confirmed that the movement can be integrated with the active ground route and runway plan. @S202 */ subject s : RampControlLead; }
    requirement def R23 { doc /* a parked aircraft must be repositioned to release a stand, remove an apron blockage, or support a confirmed operating plan @S208 */ subject s : RampControlLead; }
    requirement def R24 { doc /* Airline Operations Coordinator participation is required when a resequence would materially affect passenger boarding, connection protection, or aircraft rotation plans. @S214 */ subject s : AirlineOperationsCoordinator; }
    requirement def R25 { doc /* Marlinstone shall refresh stand demand forecasts when the Ramp Movement Board records a material change in planned off-block timing. @S216 */ subject s : DemandPredictionService; }
    requirement def R26 { doc /* The engine shall not improve one operator's position by imposing an excessive delay on another operator unless the rule basis is visible and logged. @S234 */ subject s : SlotAllocationEngine; }
    requirement def R27 { doc /* Saffron shall confirm any operator-requested Target Off Block Time revision in the Airport CDM Portal before the freeze horizon expires. @S260 */ subject s : AirlineOperationsCoordinator; }
    requirement def R28 { doc /* When a frozen value changes, the Airport CDM Portal requires a revised reason code and marks the earlier value as superseded rather than deleted. @S270 */ subject s : AirportCDMPortal; }
    requirement def R29 { doc /* Foxglove shall publish tower readiness changes to authenticated airline and handling users within the configured refresh interval. @S293 */ subject s : AirportCDMPortal; }
    requirement def R30 { doc /* Brindle must confirm that any revised off-block sequence remains compatible with the Departure Metering Service before the change is released to the airport community. @S313 */ subject s : TowerSupervisor; }
    requirement def R31 { doc /* The Aircraft Operator Representative is expected to declare whether the operator can accept a later off-block time without causing crew, connection, or aircraft rotation impacts. @S316 */ subject s : AircraftOperatorRepresentative; }
    requirement def R32 { doc /* Ironleaf must refresh affected departure sequence advisories when a restriction changes the usable departure routes or expected release spacing. @S334 */ subject s : TowerSequenceManager; }
    requirement def R33 { doc /* Blueharbor shall adjust allocated departure times when metering rules require additional stand absorption to preserve the planned runway sequence. @S355 */ subject s : SlotAllocationEngine; }
    requirement def R34 { doc /* Quartzline must coordinate every pad release with the Tower Supervisor before the aircraft leaves the treated area. @S387 */ subject s : RampControlLead; }
    requirement def R35 { doc /* Skylark must refresh the apron movement layer within five seconds of each validated surface event. @S427 */ subject s : RampMovementBoard; }
    requirement def R36 { doc /* must distribute surface equipment and apron congestion advisories to subscribed operational roles within the latency target defined in the Business Rules Registry @S461 */ subject s : AlertDistributionHub; }
    requirement def R37 { doc /* Nightjar shall suppress handler-exception annotations for arriving flights unless the exception changes the Airport Acceptance Rate or a regulated arrival sequence. @S535 */ subject s : ArrivalRegulationConsole; }
    requirement def R38 { doc /* The Time Synchronization Service is required because customs status events and apron sensor events must align with Calculated Takeoff Time and Target Off Block Time decisions. @S585 */ subject s : TimeSynchronizationService; }
    requirement def R39 { doc /* visual confirmation remains required where sensor coverage is obstructed by parked aircraft or ground equipment @S645 */ subject s : EastApronSensor; }
    requirement def R40 { doc /* is responsible for ensuring that declared service reductions are entered promptly and that the operational description is consistent with local aerodrome control procedures @S692 */ subject s : AirportDutyManager; }
    requirement def R41 { doc /* must not automatically overwrite issued times @S728 */ subject s : DepartureMeteringService; }
    requirement def R42 { doc /* Transition out of the Contingency Fallback State requires stable service performance, verified data consistency, successful user access, and agreement from the operational leads affected by the outage. @S735 */ subject s : ContingencyFallbackState; }
    requirement def R43 { doc /* Each named operational user shall authenticate with an individually assigned identity before accessing the Airport CDM Portal, Digital Briefing Room, or any operational console. @S764 */ subject s : OperationalUser; }
    requirement def R44 { doc /* Role profiles shall grant the minimum access needed to view, propose, approve, or administer operational data within the Regional Flow Platform. @S767 */ subject s : RegionalFlowPlatform; }
    requirement def R45 { doc /* operational approval privileges shall remain separated from technical administration privileges @S772 */ subject s : System; }
    requirement def R46 { doc /* Operational segregation shall prevent a single user from creating, approving, and technically concealing a material change to a Ground Delay Program, Airport Acceptance Rate, or Tactical Regulation Proposal. @S774 */ subject s : System; }
    requirement def R47 { doc /* Where dual control is required, the Regional Flow Platform shall record the initiating user, the approving user, the affected operational object, and the effective time of the decision. @S775 */ subject s : RegionalFlowPlatform; }
    requirement def R48 { doc /* Access to the Performance Analytics Warehouse shall be restricted to authorized analytical roles and shall not allow retrospective alteration of operational records held in the Audit Event Ledger. @S776 */ subject s : PerformanceAnalyticsWarehouse; }
    requirement def R49 { doc /* The Audit Event Ledger shall capture successful and failed authentication attempts, role changes, privilege elevations, operational approvals, configuration changes, data exports, and emergency access activations. @S777 */ subject s : AuditEventLedger; }
    requirement def R50 { doc /* All audit records shall use time derived from the Time Synchronization Service so that investigations can reconstruct event order across the Airport CDM Portal, Slot Allocation Engine, and Alert Distribution Hub. @S778 */ subject s : AuditEventLedger; }
    requirement def R51 { doc /* Audit records shall be protected against ordinary user modification and retained for a period agreed by the airport operator, regional authority, and participating aircraft operators. @S779 */ subject s : AuditEventLedger; }
    requirement def R52 { doc /* Security monitoring shall alert the System Support Engineer and Data Governance Steward when unusual access patterns indicate possible credential compromise or inappropriate privilege use. @S780 */ subject s : System; }
    requirement def R53 { doc /* The Identity Access Service shall support rapid suspension of accounts when a user changes role, leaves an organization, or becomes subject to an operational integrity concern. @S781 */ subject s : IdentityAccessService; }
    requirement def R54 { doc /* Temporary access shall have a defined sponsor, purpose, role scope, and expiry time, and shall be reviewed after the operational need has ended. @S782 */ subject s : System; }
    requirement def R55 { doc /* Silverpine shall accept emergency access activations only after the Identity Access Service records the authorizing incident reference and expiry time. @S783 */ subject s : ContingencyOperationsConsole; }
    requirement def R56 { doc /* When normal connectivity is restored, the Regional Flow Platform shall reconcile contingency actions with the Collaborative Decision Log so that accountability is preserved across the full incident timeline. @S787 */ subject s : RegionalFlowPlatform; }
    requirement def R57 { doc /* The Regional Flow Platform shall record slot compliance events in the Audit Event Ledger using the operating date, flight identifier, airport, runway direction, and applicable regulation reference. @S789 */ subject s : RegionalFlowPlatform; }
    requirement def R58 { doc /* The Slot Compliance State shall indicate whether a flight was compliant, early, late, exempted, substituted, cancelled, or pending review at the end of the traffic period. @S791 */ subject s : SlotComplianceState; }
    requirement def R59 { doc /* The Audit Event Ledger shall preserve the time source applied by the Time Synchronization Service so that later review can distinguish operational delay from data latency. @S792 */ subject s : AuditEventLedger; }
    requirement def R60 { doc /* The Collaborative Decision Log shall retain the stated reason, decision time, affected flight, and visible operational context for each material change to a slot or sequence. @S794 */ subject s : CollaborativeDecisionLog; }
    requirement def R61 { doc /* The Slot Coordinator shall review substitution activity after operations to confirm that priority rules were applied consistently across participating operators. @S798 */ subject s : SlotCoordinator; }
    requirement def R62 { doc /* The Tower Sequence Manager and Ramp Movement Board shall provide actual movement milestones that support independent verification of slot performance. @S801 */ subject s : TowerSequenceManager; }
    requirement def R63 { doc /* Surface movement evidence from the Surface Surveillance Adapter shall be retained long enough to support dispute resolution and regulatory audit requests. @S802 */ subject s : SurfaceSurveillanceAdapter; }
    requirement def R64 { doc /* Capacity changes made through the Capacity Assessment Module shall be correlated with the active Airport Capacity Plan and Airport Acceptance Rate used at the time of allocation. @S803 */ subject s : CapacityAssessmentModule; }
    requirement def R65 { doc /* The Performance Analytics Warehouse shall aggregate compliance outcomes by carrier, route group, regulation, airport operating configuration, and time band. @S804 */ subject s : PerformanceAnalyticsWarehouse; }
    requirement def R66 { doc /* The Data Governance Steward shall verify that audit fields required for slot performance reporting remain complete, immutable, and traceable to approved data definitions. @S806 */ subject s : DataGovernanceSteward; }
    requirement def R67 { doc /* The System Support Engineer shall investigate technical gaps when audit sequences show missing events, duplicate updates, or inconsistent timestamps. @S807 */ subject s : SystemSupportEngineer; }
    requirement def R68 { doc /* The Regional Flow Manager shall use the Post Operations Report to identify whether noncompliance resulted from operator choice, airport constraint, airspace constraint, weather impact, or system issue. @S808 */ subject s : RegionalFlowManager; }
    requirement def R69 { doc /* The Airport Duty Manager shall review late airport-driven changes that affected multiple flights and shall record whether the operational justification was valid. @S809 */ subject s : AirportDutyManager; }
    requirement def R70 { doc /* Data governance for the Regional Flow Platform shall assign accountable owners to each operational data domain and shall make those assignments visible in the Airport CDM Portal. @S812 */ subject s : RegionalFlowPlatform; }
    requirement def R71 { doc /* The Data Governance Steward shall maintain the data ownership register and shall coordinate updates through the Business Rules Registry. @S813 */ subject s : DataGovernanceSteward; }
    requirement def R72 { doc /* The Regional Flow Manager shall own flow management policy data, including Ground Delay Program parameters and Tactical Regulation Proposal status values. @S814 */ subject s : RegionalFlowManager; }
    requirement def R73 { doc /* The Slot Coordinator shall own slot allocation reference data, including Calculated Takeoff Time tolerances and Slot Compliance State definitions. @S815 */ subject s : SlotCoordinator; }
    requirement def R74 { doc /* The Airport Duty Manager shall own airport capacity declarations, including Airport Capacity Plan records and Airport Acceptance Rate values. @S816 */ subject s : AirportDutyManager; }
    requirement def R75 { doc /* The Tower Supervisor shall own tower sequence status data maintained for the Tower Sequence Manager. @S817 */ subject s : TowerSupervisor; }
    requirement def R76 { doc /* The Ramp Control Lead shall own ramp movement status data maintained for the Ramp Movement Board. @S818 */ subject s : RampControlLead; }
    requirement def R77 { doc /* The Meteorology Briefing Officer shall own operational weather classification inputs accepted by the Weather Ingest Gateway. @S819 */ subject s : MeteorologyBriefingOfficer; }
    requirement def R78 { doc /* The Airline Operations Coordinator shall be accountable for airline-supplied schedule intent, readiness status, and Target Off Block Time updates submitted through approved interfaces. @S820 */ subject s : AirlineOperationsCoordinator; }
    requirement def R79 { doc /* Each owned data element shall have a defined business meaning, allowed value range, update authority, retention class, and escalation contact. @S821 */ subject s : OwnedDataElement; }
    requirement def R80 { doc /* Freshness indicators shall be displayed on the Common Situation Display wherever stale data could affect sequencing, metering, regulation, or resource allocation decisions. @S822 */ subject s : CommonSituationDisplay; }
    requirement def R81 { doc /* The freshness indicator shall include the time of last accepted update, the maximum permitted age, and a visual state that distinguishes current, aging, stale, and unavailable data. @S823 */ subject s : FreshnessIndicator; }
    requirement def R82 { doc /* The Time Synchronization Service shall provide the common time basis used for freshness calculations across the Regional Flow Platform. @S824 */ subject s : TimeSynchronizationService; }
    requirement def R83 { doc /* The Demand Prediction Service, Capacity Assessment Module, Slot Allocation Engine, and Departure Metering Service shall reject data that lacks a trusted timestamp. @S825 */ subject s : DemandPredictionService; }
    requirement def R84 { doc /* Validation rules shall include schema checks, mandatory field checks, code set checks, temporal sequence checks, and operational plausibility checks. @S826 */ subject s : ValidationRules; }
    requirement def R85 { doc /* The Flight Data Exchange shall validate Flight Intent Message content before the data is made available for operational use. @S827 */ subject s : FlightDataExchange; }
    requirement def R86 { doc /* The Surface Surveillance Adapter shall apply position quality checks and shall mark uncertain observations before they are used by surface decision functions. @S828 */ subject s : SurfaceSurveillanceAdapter; }
    requirement def R87 { doc /* The Airline Interface Adapter shall apply carrier-specific format checks while preserving the common operational meaning required by the Regional Flow Platform. @S829 */ subject s : AirlineInterfaceAdapter; }
    requirement def R88 { doc /* The Handling Resource Planner shall validate resource quantities, task timing, and allocation identifiers against active operational reference data. @S830 */ subject s : HandlingResourcePlanner; }
    requirement def R89 { doc /* The Business Rules Registry shall hold the current validation thresholds, allowable reason codes, and exception rules approved for Normal Operations, Adverse Weather Mode, Capacity Reduction State, Recovery Phase, and Contingency Fallback State. @S831 */ subject s : BusinessRulesRegistry; }
    requirement def R90 { doc /* The Data Governance Steward shall coordinate discrepancy resolution with the responsible operational owner and shall record the disposition in the Audit Event Ledger. @S833 */ subject s : DataGovernanceSteward; }
    requirement def R91 { doc /* Urgent discrepancies that could change a metering, arrival regulation, or slot allocation decision shall be raised through the Alert Distribution Hub and reviewed in the Digital Briefing Room. @S834 */ subject s : AlertDistributionHub; }
    requirement def R92 { doc /* The System Support Engineer shall investigate technical causes of missing, delayed, duplicated, or transformed records and shall provide evidence needed for stewardship decisions. @S835 */ subject s : SystemSupportEngineer; }
    requirement def R93 { doc /* The Performance Analytics Warehouse shall retain data quality measures, including validation failure rates, freshness breaches, manual corrections, and recurring ownership conflicts. @S836 */ subject s : PerformanceAnalyticsWarehouse; }
    requirement def R94 { doc /* Stewardship reviews shall use those measures to update training, adjust validation rules, and improve the reliability of information used in operational decision making. @S837 */ subject s : StewardshipReviews; }
    requirement def R95 { doc /* Performance measurement for the Meridian Regional Air Traffic Flow Management and Airport Collaborative Decision-Making System shall convert operational events into repeatable indicators that can be reviewed after each operating day. @S838 */ subject s : MeridianRegionalAirTrafficFlowManagementAndAirportCollaborativeDecisionMakingSystem; }
    requirement def R96 { doc /* The Performance Analytics Warehouse shall calculate delay absorption as the portion of expected airborne or terminal-area delay that is converted into controlled ground delay before departure. @S839 */ subject s : PerformanceAnalyticsWarehouse; }
    requirement def R97 { doc /* Delay absorption shall be measured by comparing the unconstrained demand predicted by the Demand Prediction Service with the regulated demand produced by the Slot Allocation Engine and the realized movement times captured through the Flight Data Exchange. @S840 */ subject s : PerformanceAnalyticsWarehouse; }
    requirement def R98 { doc /* The principal delay absorption indicator shall report minutes absorbed at origin, minutes remaining in the arrival stream, and minutes transferred to surface queues within the region. @S841 */ subject s : PrincipalDelayAbsorptionIndicator; }
    requirement def R99 { doc /* The Regional Flow Manager shall use this indicator to verify that a Ground Delay Program reduced airborne holding without creating excessive departure congestion at constrained airports. @S842 */ subject s : RegionalFlowManager; }
    requirement def R100 { doc /* Queue length performance shall be measured for runway departure queues, arrival metering queues, apron movement queues, and regulation waiting lists. @S843 */ subject s : QueueLengthPerformance; }
    requirement def R101 { doc /* The Tower Sequence Manager shall provide runway sequence counts @S844 */ subject s : TowerSequenceManager; }
    requirement def R102 { doc /* the Ramp Movement Board shall provide surface queue counts based on movement status and surveillance confirmation. @S844 */ subject s : RampMovementBoard; }
    requirement def R103 { doc /* The North Runway Meter, South Runway Meter, East Apron Sensor, and West Apron Sensor shall support independent checks of queue length where surveillance coverage is available. @S845 */ subject s : NorthRunwayMeter; }
    requirement def R104 { doc /* Queue metrics shall include maximum queue length, average queue length, time above threshold, and recovery time after a constraint is lifted. @S846 */ subject s : QueueMetrics; }
    requirement def R105 { doc /* Slot adherence shall be measured as the difference between actual movement times and the assigned Calculated Takeoff Time or Target Off Block Time. @S847 */ subject s : SlotAdherence; }
    requirement def R106 { doc /* The Slot Coordinator shall review slot adherence by operator, airport, time band, and regulation identifier to detect recurring causes of noncompliance. @S848 */ subject s : SlotCoordinator; }
    requirement def R107 { doc /* A flight shall be counted within tolerance when the actual takeoff or off-block event occurs inside the operating window defined in the Business Rules Registry. @S849 */ subject s : Flight; }
    requirement def R108 { doc /* The Slot Compliance State shall be used to identify periods when adherence monitoring has operational priority over advisory optimization. @S850 */ subject s : SlotComplianceState; }
    requirement def R109 { doc /* The Capacity Assessment Module shall record the available Airport Acceptance Rate used in each baseline so that avoided cancellation estimates remain traceable. @S853 */ subject s : CapacityAssessmentModule; }
    requirement def R110 { doc /* The Airline Operations Coordinator and Aircraft Operator Representative shall be able to challenge cancellation avoidance results through the Collaborative Decision Log when local business decisions affected the outcome. @S854 */ subject s : AirlineOperationsCoordinator; }
    requirement def R111 { doc /* The Airline Operations Coordinator and Aircraft Operator Representative shall be able to challenge cancellation avoidance results through the Collaborative Decision Log when local business decisions affected the outcome. @S854 */ subject s : AircraftOperatorRepresentative; }
    requirement def R112 { doc /* The Performance Analytics Warehouse shall apply approved fuel burn and emissions factors by aircraft category, operating phase, and delay location. @S856 */ subject s : PerformanceAnalyticsWarehouse; }
    requirement def R113 { doc /* The Meteorology Briefing Officer shall support interpretation of emissions results by identifying periods when weather routing or convective avoidance dominated fuel performance. @S858 */ subject s : MeteorologyBriefingOfficer; }
    requirement def R114 { doc /* The Airport Duty Manager shall receive benefit summaries that show changes in stand occupancy, surface congestion, recovery duration, and passenger-facing disruption indicators. @S860 */ subject s : AirportDutyManager; }
    requirement def R115 { doc /* The Data Governance Steward shall ensure that published performance measures identify data sources, calculation versions, confidence limits, and known exclusions. @S861 */ subject s : DataGovernanceSteward; }
    requirement def R116 { doc /* The Post Operations Report shall present regional benefits alongside operational trade-offs so that decision makers can see whether delay, queue, slot, cancellation, and emissions objectives were balanced in practice. @S862 */ subject s : PostOperationsReport; }
    requirement def R117 { doc /* Training for the Meridian Regional Air Traffic Flow Management and Airport Collaborative Decision-Making System shall be role based and shall cover normal coordination, constrained operations, recovery actions, and degraded system use. @S863 */ subject s : MeridianRegionalAirTrafficFlowManagementAndAirportCollaborativeDecisionMakingSystem; }
    requirement def R118 { doc /* The Regional Flow Manager shall receive advanced instruction on interpreting demand and capacity information, leading collaborative decisions, and authorizing operational measures in the Regional Flow Platform. @S864 */ subject s : RegionalFlowManager; }
    requirement def R119 { doc /* Air traffic controllers shall be trained to understand how flow measures, sequencing changes, and calculated times affect sector workload, runway demand, and controller tactical flexibility. @S865 */ subject s : AirTrafficControllers; }
    requirement def R120 { doc /* The Tower Supervisor shall receive practical training on the Tower Sequence Manager, Departure Metering Service, Arrival Regulation Console, North Runway Meter, and South Runway Meter. @S866 */ subject s : TowerSupervisor; }
    requirement def R121 { doc /* Ramp personnel shall be trained under the direction of the Ramp Control Lead to use the Ramp Movement Board without substituting system indications for required visual checks, radio coordination, and local safety procedures. @S867 */ subject s : RampPersonnel; }
    requirement def R122 { doc /* The Airline Operations Coordinator and Aircraft Operator Representative shall be trained to submit, review, and update Flight Intent Message data through approved interfaces and to assess the operational effect of Calculated Takeoff Time and Target Off Block Time changes. @S868 */ subject s : AirlineOperationsCoordinator; }
    requirement def R123 { doc /* The Airline Operations Coordinator and Aircraft Operator Representative shall be trained to submit, review, and update Flight Intent Message data through approved interfaces and to assess the operational effect of Calculated Takeoff Time and Target Off Block Time changes. @S868 */ subject s : AircraftOperatorRepresentative; }
    requirement def R124 { doc /* Ground handling personnel shall be trained by the Ground Handling Dispatcher on the Handling Resource Planner and on procedures for confirming that resource constraints are represented accurately before they influence collaborative decisions. @S869 */ subject s : GroundHandlingPersonnel; }
    requirement def R125 { doc /* The Slot Coordinator shall receive training on the Slot Allocation Engine, Airport CDM Portal, and applicable Business Rules Registry entries so that slot actions are applied consistently and transparently. @S870 */ subject s : SlotCoordinator; }
    requirement def R126 { doc /* The Network Operations Liaison and Airspace Sector Planner shall be trained to coordinate regional constraints, sector load conditions, and network measures using the Sector Load Monitor and Common Situation Display. @S871 */ subject s : NetworkOperationsLiaison; }
    requirement def R127 { doc /* The Network Operations Liaison and Airspace Sector Planner shall be trained to coordinate regional constraints, sector load conditions, and network measures using the Sector Load Monitor and Common Situation Display. @S871 */ subject s : AirspaceSectorPlanner; }
    requirement def R128 { doc /* The Airport Duty Manager shall be trained to recognize when an Airport Capacity Plan requires revision and when the operational state should move from Normal Operations to Adverse Weather Mode or Capacity Reduction State. @S872 */ subject s : AirportDutyManager; }
    requirement def R129 { doc /* The Meteorology Briefing Officer shall be trained to explain weather uncertainty in operational terms and to verify that the Weather Ingest Gateway supports the assumptions used during briefings. @S873 */ subject s : MeteorologyBriefingOfficer; }
    requirement def R130 { doc /* The Emergency Response Coordinator shall participate in recurrent training so that emergency priorities are integrated into flow management decisions without obscuring command authority or safety responsibilities. @S874 */ subject s : EmergencyResponseCoordinator; }
    requirement def R131 { doc /* The Deicing Coordinator shall receive seasonal refresher training on how deicing capacity assumptions are represented in demand and departure metering tools. @S875 */ subject s : DeicingCoordinator; }
    requirement def R132 { doc /* The Data Governance Steward shall train operational users on data quality responsibilities, privacy expectations, and the correct interpretation of audit records in the Audit Event Ledger. @S876 */ subject s : DataGovernanceSteward; }
    requirement def R133 { doc /* The System Support Engineer shall train superusers on service status checks, access fault escalation, and safe use of the Contingency Operations Console during partial outages. @S877 */ subject s : SystemSupportEngineer; }
    requirement def R134 { doc /* Initial training shall include classroom instruction, supervised workstation practice, scenario walkthroughs in the Digital Briefing Room, and observed operational shadowing before independent system use is authorized. @S878 */ subject s : InitialTraining; }
    requirement def R135 { doc /* Recurrent training shall be required at least annually and after major changes to the Regional Flow Platform, Demand Prediction Service, Capacity Assessment Module, or Flight Data Exchange. @S879 */ subject s : RecurrentTraining; }
    requirement def R136 { doc /* Simulation exercises shall use realistic traffic samples, weather constraints, surface congestion, airline schedule pressure, handling resource shortages, and recovery objectives to test coordinated decision making. @S880 */ subject s : SimulationExercises; }
    requirement def R137 { doc /* Each exercise shall include participants from tower, ramp, airline operations, handling, airport operations, network coordination, meteorology, data governance, and system support functions when those functions are relevant to the scenario. @S881 */ subject s : Exercise; }
    requirement def R138 { doc /* Exercises shall cover transitions among Normal Operations, Adverse Weather Mode, Capacity Reduction State, Recovery Phase, Contingency Fallback State, and Slot Compliance State. @S882 */ subject s : Exercises; }
    requirement def R139 { doc /* Simulation events shall require users to compare automated recommendations with local knowledge, document significant decisions in the Collaborative Decision Log, and explain departures from system proposals. @S883 */ subject s : SimulationEvents; }
    requirement def R140 { doc /* Human factors safeguards shall include workload monitoring, clear alert prioritization, consistent terminology, confirmation steps for high impact actions, and protection against silent mode changes. @S884 */ subject s : HumanFactorsSafeguards; }
    requirement def R141 { doc /* Workstation layouts shall support rapid comparison between the Common Situation Display, Airport CDM Portal, Tower Sequence Manager, Ramp Movement Board, and relevant advisory messages without forcing users to copy critical values manually. @S885 */ subject s : WorkstationLayouts; }
    requirement def R142 { doc /* Training assessments shall verify that users can identify stale data, time synchronization problems, duplicate flights, conflicting constraints, and inappropriate automation reliance before such issues affect live operations. @S886 */ subject s : TrainingAssessments; }
    requirement def R143 { doc /* Post-exercise reviews shall use evidence from the Performance Analytics Warehouse and Audit Event Ledger to improve procedures, refine training materials, and confirm that human performance concerns are assigned to accountable owners. @S887 */ subject s : PostExerciseReviews; }
    requirement def R144 { doc /* Deployment of the Regional Flow Platform shall proceed through phased increments that limit operational exposure while progressively adding airports, interfaces, and decision support functions. @S888 */ subject s : RegionalFlowPlatform; }
    requirement def R145 { doc /* The first increment shall establish the core operational baseline for the Regional Flow Manager, Network Operations Liaison, Data Governance Steward, and System Support Engineer in a controlled production environment. @S889 */ subject s : FirstIncrement; }
    requirement def R146 { doc /* This baseline shall include the Identity Access Service, Time Synchronization Service, Audit Event Ledger, Performance Analytics Warehouse, and Business Rules Registry before any airport is permitted to exchange operational data. @S890 */ subject s : CoreOperationalBaseline; }
    requirement def R147 { doc /* Pilot airport selection shall favor locations with stable operational leadership, representative traffic complexity, available surface surveillance data, and demonstrated willingness to participate in joint procedure development. @S891 */ subject s : PilotAirportSelection; }
    requirement def R148 { doc /* The initial pilot shall include one constrained primary airport and one less constrained regional airport so that both high-demand and routine operating patterns are exercised. @S892 */ subject s : InitialPilot; }
    requirement def R149 { doc /* Each candidate airport shall provide evidence that the Airport Duty Manager, Tower Supervisor, Ramp Control Lead, Airline Operations Coordinator, Ground Handling Dispatcher, and Aircraft Operator Representative have named accountable implementation contacts. @S893 */ subject s : CandidateAirport; }
    requirement def R150 { doc /* Readiness Gate 1 shall confirm that governance, security approvals, user role definitions, operating hours, and support escalation paths are documented and accepted by local stakeholders. @S894 */ subject s : ReadinessGate1; }
    requirement def R151 { doc /* Readiness Gate 2 shall confirm that the Flight Data Exchange, Airline Interface Adapter, Surface Surveillance Adapter, and Weather Ingest Gateway can be connected without disrupting existing airport operations. @S895 */ subject s : ReadinessGate2; }
    requirement def R152 { doc /* Readiness Gate 3 shall confirm that local procedures have been mapped to the Airport CDM Portal, Tower Sequence Manager, Ramp Movement Board, Departure Metering Service, and Arrival Regulation Console. @S896 */ subject s : ReadinessGate3; }
    requirement def R153 { doc /* Readiness Gate 4 shall confirm that training, shadow operations, contingency procedures, and operational acceptance criteria have been completed before live collaborative decisions are made through the Regional Flow Platform. @S897 */ subject s : ReadinessGate4; }
    requirement def R154 { doc /* The migration plan shall classify each local tool as retired, retained for read-only reference, integrated through an approved interface, or replaced by a Regional Flow Platform function. @S903 */ subject s : MigrationPlan; }
    requirement def R155 { doc /* No local tool shall be retired until the responsible operational owner verifies that its essential decisions, timing assumptions, and audit needs are supported in the target process. @S904 */ subject s : LocalTool; }
    requirement def R156 { doc /* During shadow operations, local tools shall remain the authoritative source while the Regional Flow Platform produces parallel outputs for comparison by operational users. @S905 */ subject s : LocalTool; }
    requirement def R157 { doc /* After cutover, local users shall enter operational decisions through the Airport CDM Portal and shall avoid reintroducing uncontrolled parallel records that undermine common situational awareness. @S907 */ subject s : LocalUsers; }
    requirement def R158 { doc /* The Contingency Operations Console shall be available at each onboarded airport before reliance on the Regional Flow Platform is declared for Normal Operations, Adverse Weather Mode, Capacity Reduction State, Recovery Phase, or Contingency Fallback State. @S908 */ subject s : ContingencyOperationsConsole; }
    requirement def R159 { doc /* Expansion beyond the pilot airports shall occur in waves that group airports by interface maturity, traffic dependency, stakeholder readiness, and available support capacity. @S909 */ subject s : ExpansionBeyondThePilotAirports; }
    requirement def R160 { doc /* Each onboarding wave shall include a stabilization period in which the System Support Engineer and Data Governance Steward monitor defect trends, data quality, access changes, and user adoption. @S910 */ subject s : OnboardingWave; }
    requirement def R161 { doc /* Full regional deployment shall be declared only after the Regional Flow Manager confirms that operational benefits, safety constraints, cyber controls, and stakeholder obligations remain stable across multiple airports and traffic conditions. @S911 */ subject s : RegionalFlowManager; }
    requirement def R162 { doc /* Operational service management for the Regional Flow Platform shall begin when a deployed airport is accepted into steady state support after the regional stabilization period. @S912 */ subject s : RegionalFlowPlatform; }
    requirement def R163 { doc /* The service model shall distinguish continuous operational support from planned engineering support so that safety related traffic flow functions remain protected at all times. @S913 */ subject s : ServiceModel; }
    requirement def R164 { doc /* The System Support Engineer shall provide round the clock on call coverage for production incidents affecting the Regional Flow Platform, Airport CDM Portal, Slot Allocation Engine, Departure Metering Service, Arrival Regulation Console, and Alert Distribution Hub. @S914 */ subject s : SystemSupportEngineer; }
    requirement def R165 { doc /* Standard service desk coverage for access requests, reporting questions, configuration inquiries, and minor usability issues shall be available during normal regional administrative hours on business days. @S915 */ subject s : StandardServiceDeskCoverage; }
    requirement def R166 { doc /* During published peak traffic periods, Adverse Weather Mode, Capacity Reduction State, and Recovery Phase, the on call support posture shall be raised so that the System Support Engineer can join the Digital Briefing Room without delay. @S916 */ subject s : OnCallSupportPosture; }
    requirement def R167 { doc /* The Regional Flow Manager, Tower Supervisor, Ramp Control Lead, Airport Duty Manager, and Network Operations Liaison shall retain operational command authority during support activity. @S917 */ subject s : RegionalFlowManager; }
    requirement def R168 { doc /* The System Support Engineer shall advise operational supervisors on technical status, known workarounds, data integrity concerns, and recovery options, but shall not issue traffic management instructions. @S918 */ subject s : SystemSupportEngineer; }
    requirement def R169 { doc /* Incidents shall be classified by operational effect, with the highest priority assigned to loss of common situational awareness, loss of slot computation, corruption of operational timing data, or failure of alert distribution during active traffic management. @S919 */ subject s : Incidents; }
    requirement def R170 { doc /* A critical incident shall be acknowledged within fifteen minutes and shall have continuous technical ownership until service is restored or an agreed operational workaround is in place. @S920 */ subject s : CriticalIncident; }
    requirement def R171 { doc /* A high priority incident that degrades a major function without stopping tactical coordination shall be acknowledged within thirty minutes and shall be reviewed with the affected operational supervisor at least hourly. @S921 */ subject s : HighPriorityIncident; }
    requirement def R172 { doc /* Medium and low priority incidents shall be handled through the service queue, with target updates provided at intervals appropriate to their operational impact and planned resolution path. @S922 */ subject s : MediumAndLowPriorityIncidents; }
    requirement def R173 { doc /* The System Support Engineer shall maintain an incident record that captures the initial symptom, affected components, operational state, timeline, mitigation actions, data corrections, and supervisor decisions. @S923 */ subject s : SystemSupportEngineer; }
    requirement def R174 { doc /* Incident records shall reference the Audit Event Ledger where user actions, configuration changes, interface events, or automated decisions are relevant to the investigation. @S924 */ subject s : IncidentRecord; }
    requirement def R175 { doc /* The Collaborative Decision Log shall be used to preserve the operational context of major incidents when traffic management decisions are made while a technical degradation is present. @S925 */ subject s : CollaborativeDecisionLog; }
    requirement def R176 { doc /* The System Support Engineer shall verify that fallback tools, exported operational data, and restoration checkpoints are available before advising that normal technical service can resume. @S927 */ subject s : SystemSupportEngineer; }
    requirement def R177 { doc /* Future enhancement of the Regional Flow Platform should be treated as an incremental extension of the operational service rather than as a replacement of the current concept. @S936 */ subject s : RegionalFlowPlatform; }
    requirement def R178 { doc /* Cross-border exchange should use standardized message structures where practical, but the Business Rules Registry should retain the local parameters needed for Meridian operations. @S939 */ subject s : BusinessRulesRegistry; }
    requirement def R179 { doc /* The Flight Data Exchange should be enhanced to accept richer intent data, including improved route options, expected cruise profiles, and updated departure readiness information. @S940 */ subject s : FlightDataExchange; }
    requirement def R180 { doc /* The Demand Prediction Service should use this data to create more stable demand pictures across longer planning horizons while still preserving tactical responsiveness. @S941 */ subject s : DemandPredictionService; }
    requirement def R181 { doc /* The Weather Ingest Gateway and Sector Load Monitor should provide the common inputs needed to connect airspace capacity and airport capacity in the same prediction cycle. @S943 */ subject s : WeatherIngestGateway; }
    requirement def R182 { doc /* The Capacity Assessment Module should evolve from a mainly rules-based assessment into a service that can compare planned capacity, observed throughput, and predicted constraint persistence. @S944 */ subject s : CapacityAssessmentModule; }
    requirement def R183 { doc /* The Airport CDM Portal, Airline Interface Adapter, Handling Resource Planner, and Ramp Movement Board should provide the main operational inputs for this capability. @S947 */ subject s : AirportCDMPortal; }
    requirement def R184 { doc /* Predicted changes to Target Off Block Time should be presented with confidence levels rather than as unconditional system corrections. @S948 */ subject s : TargetOffBlockTime; }
    requirement def R185 { doc /* The Slot Allocation Engine should use improved turnaround predictions to protect feasible Calculated Takeoff Time assignments and to reduce avoidable re-sequencing. @S949 */ subject s : SlotAllocationEngine; }
    requirement def R186 { doc /* The Tower Sequence Manager and Departure Metering Service should receive only the information needed for tactical sequencing, with detailed airline operational data controlled by policy. @S950 */ subject s : TowerSequenceManager; }
    requirement def R187 { doc /* These options should be generated by the Contingency Operations Console and reviewed through the Common Situation Display before any operational decision is applied. @S952 */ subject s : ContingencyOperationsConsole; }
    requirement def R188 { doc /* The system should not automatically impose a Ground Delay Program, change an Airport Acceptance Rate, or alter a tactical measure without authorized human confirmation. @S953 */ subject s : System; }
    requirement def R189 { doc /* Recovery recommendations should include the operational rationale, expected benefit, key assumptions, and possible secondary effects on connected flights and surface movements. @S954 */ subject s : RecoveryRecommendations; }
    requirement def R190 { doc /* The Collaborative Decision Log and Audit Event Ledger should record each proposed option, the user response, and the final decision so that performance can be reviewed after operations. @S955 */ subject s : CollaborativeDecisionLog; }
    requirement def R191 { doc /* The Collaborative Decision Log and Audit Event Ledger should record each proposed option, the user response, and the final decision so that performance can be reviewed after operations. @S955 */ subject s : AuditEventLedger; }
    requirement def R192 { doc /* Regional expansion should include a repeatable onboarding pattern for new airports, airspace sectors, airlines, and handling organizations. @S956 */ subject s : RegionalExpansion; }
    requirement def R193 { doc /* The Identity Access Service, Time Synchronization Service, and Performance Analytics Warehouse should be scaled early because they form shared foundations for a wider regional deployment. @S957 */ subject s : IdentityAccessService; }
    requirement def R194 { doc /* The Identity Access Service, Time Synchronization Service, and Performance Analytics Warehouse should be scaled early because they form shared foundations for a wider regional deployment. @S957 */ subject s : TimeSynchronizationService; }
    requirement def R195 { doc /* The Identity Access Service, Time Synchronization Service, and Performance Analytics Warehouse should be scaled early because they form shared foundations for a wider regional deployment. @S957 */ subject s : PerformanceAnalyticsWarehouse; }
    requirement def R196 { doc /* Data governance should remain under the Data Governance Steward, with clear rules for retention, consent, quality thresholds, and permitted operational use. @S958 */ subject s : DataGovernanceSteward; }
    requirement def R197 { doc /* Future releases should be validated in shadow mode before operational activation so that the Regional Flow Manager, Airline Operations Coordinator, Tower Supervisor, and Airport Duty Manager can compare recommendations with actual outcomes. @S959 */ subject s : FutureReleases; }
    requirement def R198 { doc /* Sustained regional ATFM and A-CDM operation requires each participating organization to treat the operating picture as a shared operational asset rather than a local advisory product. @S960 */ subject s : ParticipatingOrganization; }
    requirement def R199 { doc /* should be kept consistent with the Regional Flow Platform and Airport CDM Portal @S974 */ subject s : CommonSituationDisplay; }
    requirement def R200 { doc /* Calculated Takeoff Time and Target Off Block Time commitments should be treated as executable operating constraints unless they are revised through the agreed coordination process @S976 */ subject s : CalculatedTakeoffTimeAndTargetOffBlockTime; }
    requirement def R201 { doc /* Ground Delay Program decisions, Tactical Regulation Proposal review, and Airport Acceptance Rate changes should be visible to affected participants before they are applied whenever operational time permits @S977 */ subject s : GroundDelayProgram; }
    requirement def R202 { doc /* must be operated with monitored data quality thresholds and clear fallback procedures @S979 */ subject s : FlightDataExchange; }
    requirement def R203 { doc /* must be operated with monitored data quality thresholds and clear fallback procedures @S979 */ subject s : AirlineInterfaceAdapter; }
    requirement def R204 { doc /* must be operated with monitored data quality thresholds and clear fallback procedures @S979 */ subject s : SurfaceSurveillanceAdapter; }
    requirement def R205 { doc /* must be operated with monitored data quality thresholds and clear fallback procedures @S979 */ subject s : WeatherIngestGateway; }
    requirement def R206 { doc /* must use the approved rules recorded in the Business Rules Registry @S980 */ subject s : SlotAllocationEngine; }
    requirement def R207 { doc /* must use the approved rules recorded in the Business Rules Registry @S980 */ subject s : DepartureMeteringService; }
    requirement def R208 { doc /* must use the approved rules recorded in the Business Rules Registry @S980 */ subject s : ArrivalRegulationConsole; }
    requirement def R209 { doc /* must use the approved rules recorded in the Business Rules Registry @S980 */ subject s : TowerSequenceManager; }
    requirement def R210 { doc /* must use the approved rules recorded in the Business Rules Registry @S980 */ subject s : RampMovementBoard; }
    requirement def R211 { doc /* must support traceability, least-privilege access, and after-action accountability for all operationally significant changes @S981 */ subject s : IdentityAccessService; }
    requirement def R212 { doc /* must support traceability, least-privilege access, and after-action accountability for all operationally significant changes @S981 */ subject s : AuditEventLedger; }
    requirement def R213 { doc /* should be used to measure compliance, delay outcomes, capacity use, and the effectiveness of collaborative decisions @S982 */ subject s : PerformanceAnalyticsWarehouse; }
    requirement def R214 { doc /* should be used to measure compliance, delay outcomes, capacity use, and the effectiveness of collaborative decisions @S982 */ subject s : PostOperationsReport; }
    requirement def R215 { doc /* should favor transparent decision making, timely challenge by affected parties, documented resolution of disputes, and continuous improvement through training, exercises, and post-operations review @S983 */ subject s : Governance; }
}
