package L2Model {
    item def AcceptedIntentDataItem { doc /* @S128 */ }
    item def ActiveRestrictionStatusExpectedOperationalEffectAndAnyRelatedCoordinationNotesItem { doc /* @S337 */ }
    item def AffectedRunwayQueueItem { doc /* @S366 */ }
    item def AgreedTargetOffBlockTimeValuesAndStakeholderRemarksItem { doc /* @S429 */ }
    item def AircraftTreatmentStatusItem { doc /* @S377 */ }
    item def AirportCapacityPlanItem { doc /* @S071 */ }
    item def AlertsItem { doc /* @S407 */ }
    item def ApprovedDutyCoordinationAlertsItem { doc /* @S193 */ }
    item def ApronSweepCompletionNoteItem { doc /* @S647,S678 */ }
    item def ArrivalPlanItem { doc /* @S405 */ }
    item def CalculatedTakeoffTimeValuesAndTargetOffBlockTimeGuidanceItem { doc /* @S135 */ }
    item def CandidatePushbackSpacingItem { doc /* @S456 */ }
    item def CombinedTacticalViewItem { doc /* @S420 */ }
    item def CommonSituationDisplayItem { doc /* @S153 */ }
    item def ConstraintsItem { doc /* @S225 */ }
    item def ConvertedMeasuresItem { doc /* @S613 */ }
    item def CrewBusDelaySlipItem { doc /* @S140,S237 */ }
    item def CrewDutyExtensionLogItem { doc /* @S620,S726 */ }
    item def CrewLegalityImpactsItem { doc /* @S627 */ }
    item def CurrentAgreedTargetSetItem { doc /* @S265 */ }
    item def CurrentMovementAreaOccupancyAndEquipmentStatusIndicatorsItem { doc /* @S445 */ }
    item def CurrentOperatingScheduleItem { doc /* @S103 */ }
    item def CurrentRegionalDemandAndConstraintContextItem { doc /* @S164 */ }
    item def CustomsHoldReleaseNoteItem { doc /* @S679 */ }
    item def DeicingPadQueueCardItem { doc /* @S294,S378 */ }
    item def DemandItem { doc /* @S225 */ }
    item def DemandForecastItem { doc /* @S101 */ }
    item def DepartureFixLoadSheetItem { doc /* @S598 */ }
    item def EarlyStandReadinessInformationItem { doc /* @S063 */ }
    item def ExpectedLandingDemandStandAllocationRiskInboundRegulationEffectsAndHandlingReadinessIndicatorsItem { doc /* @S155 */ }
    item def FiledFlightInformationItem { doc /* @S103 */ }
    item def FlightIntentMessageItem { doc /* @S126 */ }
    item def FreshnessIndicatorItem { doc /* @S822 */ }
    item def FuelTruckHoldAdviceItem { doc /* @S450 */ }
    item def GateReopeningMemoItem { doc /* @S472 */ }
    item def LateBaggageTagListItem { doc /* @S519 */ }
    item def MedicalDiversionNoticeItem { doc /* @S496,S576 */ }
    item def MorningWeatherOutlookItem { doc /* @S057 */ }
    item def MovementIndicationsItem { doc /* @S179 */ }
    item def NormalizedScheduleItem { doc /* @S053 */ }
    item def NotificationsItem { doc /* @S614 */ }
    item def OccupiedStandsBlockedServiceRoadsAndPendingPushbackAreasItem { doc /* @S311 */ }
    item def OperationalBasisForEachValueItem { doc /* @S400 */ }
    item def PassengerMisconnectCountItem { doc /* @S740,S851 */ }
    item def PositionUpdatesItem { doc /* @S179 */ }
    item def PreTacticalBaselineItem { doc /* @S072 */ }
    item def ProposedArrivalOpportunitiesItem { doc /* @S241 */ }
    item def ProposedDepartureOpportunitiesAndAssociatedCalculatedTakeoffTimeValuesItem { doc /* @S242 */ }
    item def PushbackWindowTokenItem { doc /* @S503 */ }
    item def RampIntentItem { doc /* @S217 */ }
    item def RegionalBenefitsAlongsideOperationalTradeOffsItem { doc /* @S862 */ }
    item def RemoteStandOccupancyExpectedTowingActionsAndBusServiceReadinessItem { doc /* @S551 */ }
    item def RemoteStandShuttleCountItem { doc /* @S648 */ }
    item def ResourceDrivenFeasibilityStatusItem { doc /* @S312 */ }
    item def RevisedConstraintSetItem { doc /* @S137 */ }
    item def RevisedDepartureMeteringAdvisoriesItem { doc /* @S426 */ }
    item def RevisedFlightIntentMessageContentItem { doc /* @S684 */ }
    item def RicherIntentDataItem { doc /* @S941 */ }
    item def RunwayInspectionNoteItem { doc /* @S060,S181 */ }
    item def RunwayLightingOutageCardItem { doc /* @S693 */ }
    item def RunwaySpecificCapacityValuesItem { doc /* @S114 */ }
    item def SharedViewOfDemandCapacityConstraintsAndActiveTrafficManagementMeasuresItem { doc /* @S020 */ }
    item def SlotSwapPermissionEmailItem { doc /* @S672,S795 */ }
    item def StandLevelExceptionItem { doc /* @S525 */ }
    item def StandOccupancyTransitionsPushbackLaneBlockageDurationsAndSensorConfidenceValuesItem { doc /* @S578 */ }
    item def StandTowRequestFormItem { doc /* @S208,S304 */ }
    item def StormCellSnapshotItem { doc /* @S133 */ }
    item def SurfaceEquipmentAndApronCongestionAdvisoriesItem { doc /* @S461 */ }
    item def TemporaryRestrictionNoticeItem { doc /* @S325,S399 */ }
    item def TimeStampedWeatherConditionUpdatesItem { doc /* @S182 */ }
    item def TowbarShortageReportItem { doc /* @S523,S556 */ }
    item def TowerReadinessChangesItem { doc /* @S293 */ }
    part def AccountableParticipant { doc /* @S168 */ }
    part def AirTrafficControllers { doc /* @S865 */ }
    part def AircraftOperatorRepresentative { doc /* @S039,S055,S082,S312,S405,S620,S726 */ }
    part def AircraftRegistration { doc /* @S127 */ }
    part def AirlineInterfaceAdapter { doc /* @S033,S103,S126,S128,S235,S452,S519,S829 */ }
    part def AirlineOperationsCentre { doc /* @S126,S135 */ }
    part def AirlineOperationsCoordinator { doc /* @S039,S054,S081,S138,S214,S237,S260,S312,S472,S679,S740,S795,S820,S851 */ }
    part def AirportAcceptanceRate { doc /* @S046 */ }
    part def AirportCDMPortal { doc /* @S016,S031,S150,S166,S172,S179,S185,S264,S270,S293,S312,S337,S381,S405,S429,S503,S648 */ }
    part def AirportCapacityPlan { doc /* @S046 */ }
    part def AirportDutyManager { doc /* @S062,S088,S116,S144,S177,S181,S196,S435,S496,S568,S576,S678,S679,S809,S816,S860,S872 */ }
    part def AirportNetwork { doc /* @S003,S026 */ }
    part def AirportParticipant { doc /* @S167 */ }
    part def AirspaceSectorPlanner { doc /* @S058,S079,S326 */ }
    part def AlertDistributionHub { doc /* @S033,S073,S121,S193,S332,S366,S461,S614 */ }
    part def ArrivalRegulationConsole { doc /* @S032,S070,S095,S241,S407,S535,S576,S980 */ }
    part def ArrivalWorkspace { doc /* @S155 */ }
    part def AuditEventLedger { doc /* @S021,S034,S123,S222,S271,S777,S792,S955,S981 */ }
    part def AuditRecords { doc /* @S778,S779 */ }
    part def AuthenticatedAirlineAndHandlingUsers { doc /* @S293 */ }
    part def AuthorizedUsers { doc /* @S020 */ }
    part def BusinessRulesRegistry { doc /* @S034,S831,S939 */ }
    part def CalculatedTakeoffTime { doc /* @S046 */ }
    part def CapacityAssessmentModule { doc /* @S014,S031,S057,S066,S107,S114,S120,S133,S192,S225,S341,S351,S373,S400,S803,S825,S853,S944 */ }
    part def CargoAndGeneralAviationAerodromes { doc /* @S001 */ }
    part def CollaborativeDecisionLog { doc /* @S021,S046,S169,S186,S267,S794,S925,S955 */ }
    part def CommonServices { doc /* @S030 */ }
    part def CommonSituationDisplay { doc /* @S020,S046,S072,S165,S265,S337,S366,S400,S613,S627,S822,S974 */ }
    part def ComplianceAssessment { doc /* @S790 */ }
    part def ConfidenceRecord { doc /* @S119 */ }
    part def ContingencyOperationsConsole { doc /* @S032,S195,S247,S783,S908,S952 */ }
    part def CrewReadiness { doc /* @S127 */ }
    part def CriticalIncident { doc /* @S920 */ }
    part def DataGovernanceSteward { doc /* @S098,S170,S806,S813,S833,S861,S876,S958 */ }
    part def DedicatedMilestoneView { doc /* @S156 */ }
    part def DeicingCoordinator { doc /* @S092,S294,S378,S390,S875 */ }
    part def DemandPredictionService { doc /* @S013,S031,S053,S101,S103,S105,S131,S216,S225,S251,S350,S825,S941 */ }
    part def DepartureMeteringService { doc /* @S032,S069,S095,S242,S278,S348,S352,S426,S456,S728,S825,S851,S980 */ }
    part def DigitalBriefingRoom { doc /* @S031,S071,S506 */ }
    part def EastApronSensor { doc /* @S035,S063,S179,S578 */ }
    part def EmergencyAccess { doc /* @S785 */ }
    part def EmergencyResponseCoordinator { doc /* @S096,S874 */ }
    part def FlightDataExchange { doc /* @S033,S052,S053,S103,S128,S278,S684,S827,S940,S941 */ }
    part def FlightIntentMessage { doc /* @S046,S127 */ }
    part def FreshnessIndicator { doc /* @S822,S823 */ }
    part def GateConflictDetector { doc /* @S035,S210,S386,S472 */ }
    part def GroundHandlingDispatcher { doc /* @S064,S091,S140,S237,S302,S519,S523,S556 */ }
    part def GroundHandlingPersonnel { doc /* @S869 */ }
    part def HandlingResourcePlanner { doc /* @S065,S141,S303,S304,S547,S648,S830 */ }
    part def HarborEastAirport { doc /* @S026 */ }
    part def HighFrequencyDomesticAirports { doc /* @S001 */ }
    part def HighPriorityIncident { doc /* @S921 */ }
    part def IdentityAccessService { doc /* @S034,S152,S194,S781,S783,S981 */ }
    part def IncidentRecord { doc /* @S924 */ }
    part def IntegratedTacticalManagementPosition { doc /* @S420,S429 */ }
    part def LakesideRegionalAirport { doc /* @S026 */ }
    part def MeridianInternationalAirport { doc /* @S026 */ }
    part def MeridianRegion { doc /* @S001 */ }
    part def MeridianRegionalAirTrafficFlowManagementAndAirportCollaborativeDecisionMakingSystem { doc /* @S838,S863 */ }
    part def MeteorologyBriefingOfficer { doc /* @S056,S057,S085,S086,S087,S112,S133,S819,S858,S873 */ }
    part def MilitaryAirspaceLiaison { doc /* @S059,S093,S325,S399 */ }
    part def NamedOperationalUser { doc /* @S764 */ }
    part def NetworkOperationsLiaison { doc /* @S039,S083,S084,S614 */ }
    part def NorthRunwayMeter { doc /* @S035,S114,S280,S454 */ }
    part def NorthValleyAirport { doc /* @S026 */ }
    part def Null { doc /* @S009,S023,S049,S060,S067,S071,S072,S073,S085,S099,S100,S109,S113,S118,S122,S129,S137,S140,S145,S149,S153,S155,S182,S193,S208,S241,S265,S294,S311,S321,S325,S374,S377,S407,S426,S440,S461,S496,S523,S525,S551,S578,S613,S620,S627,S646,S647,S663,S672,S684,S740,S772,S780,S786,S788,S793,S797,S799,S800,S805,S810,S811,S821,S822,S823,S825,S826,S832,S834,S837,S840,S841,S843,S844,S845,S846,S847,S849,S852,S854,S855,S857,S859,S862,S868,S871,S878,S879,S880,S881,S882,S883,S884,S885,S886,S887,S889,S890,S891,S892,S893,S898,S899,S900,S901,S902,S903,S904,S905,S906,S907,S909,S910,S911,S913,S915,S916,S917,S919,S920,S921,S922,S928,S929,S930,S931,S932,S933,S934,S935,S939,S942,S943,S945,S946,S947,S950,S951,S952,S954,S955,S956,S957,S959,S960,S976,S977,S979,S980,S981,S982,S983 */ }
    part def OperationalSegregation { doc /* @S774 */ }
    part def PassengerConnectionSensitivity { doc /* @S127 */ }
    part def PerformanceAnalyticsWarehouse { doc /* @S034,S074,S148,S173,S776,S804,S836,S839,S856 */ }
    part def PostOperationsReport { doc /* @S046,S862 */ }
    part def PreferredRoute { doc /* @S127 */ }
    part def PrimaryInternationalHub { doc /* @S001 */ }
    part def PrimaryWorkspace { doc /* @S153 */ }
    part def RampControlLead { doc /* @S063,S090,S142,S200,S202,S208,S219,S304,S378,S387,S556,S614,S647,S678,S818 */ }
    part def RampMovementBoard { doc /* @S032,S063,S216,S217,S255,S311,S361,S377,S427,S445,S450,S525,S551,S801,S844,S980 */ }
    part def RampPersonnel { doc /* @S867 */ }
    part def ReadinessGate1 { doc /* @S894 */ }
    part def ReadinessGate2 { doc /* @S895 */ }
    part def ReadinessGate3 { doc /* @S896 */ }
    part def ReadinessGate4 { doc /* @S897 */ }
    part def RegionalFlowManager { doc /* @S010,S050,S078,S094,S117,S137,S393,S399,S420,S598,S614,S808,S814,S842,S864 */ }
    part def RegionalFlowPlatform { doc /* @S012,S030,S031,S032,S033,S034,S035,S051,S101,S130,S147,S164,S191,S250,S268,S314,S333,S349,S371,S422,S775,S787,S789,S812,S888,S905,S912,S936 */ }
    part def RegionalSystem { doc /* @S028 */ }
    part def RequestedDepartureTiming { doc /* @S127 */ }
    part def ResponsibleSweepTeam { doc /* @S647 */ }
    part def RoleProfiles { doc /* @S767 */ }
    part def SectorLoadMonitor { doc /* @S035,S106,S484,S598,S943 */ }
    part def SharedOperationalPicture { doc /* @S046 */ }
    part def SharedWorkspace { doc /* @S164 */ }
    part def SlotAllocationEngine { doc /* @S015,S031,S134,S135,S137,S225,S227,S234,S253,S355,S374,S398,S428,S456,S503,S825,S949,S980 */ }
    part def SlotComplianceState { doc /* @S791,S850 */ }
    part def SlotCoordinator { doc /* @S039,S068,S080,S136,S229,S239,S356,S614,S672,S724,S726,S795,S798,S815,S848,S870 */ }
    part def SouthRunwayMeter { doc /* @S035,S114,S280 */ }
    part def SouthportAirport { doc /* @S026 */ }
    part def StakeholderOrganization { doc /* @S048 */ }
    part def SubstitutionRecords { doc /* @S796 */ }
    part def SurfaceSurveillanceAdapter { doc /* @S033,S179,S281,S445,S606,S693,S802,S828 */ }
    part def System { doc /* @S022,S023,S047,S104,S953 */ }
    part def SystemSupportEngineer { doc /* @S171,S807,S835,S877,S914,S918,S923,S927 */ }
    part def TacticalRegulationProposal { doc /* @S046 */ }
    part def TargetOffBlockTime { doc /* @S046,S948 */ }
    part def TemporaryAccess { doc /* @S782 */ }
    part def TimeSynchronizationService { doc /* @S034,S110,S149,S187,S585,S824 */ }
    part def TowerSequenceManager { doc /* @S032,S217,S242,S254,S279,S334,S445,S450,S801,S844,S980 */ }
    part def TowerSupervisor { doc /* @S060,S061,S089,S143,S175,S181,S202,S313,S614,S693,S817,S866 */ }
    part def TurnaroundStatus { doc /* @S127 */ }
    part def WeatherIngestGateway { doc /* @S033,S057,S102,S108,S111,S182,S943 */ }
    part def WestApronSensor { doc /* @S035,S063,S179 */ }
    part system {
        part accountableParticipant : AccountableParticipant {
            perform action a0 { doc /* enter a provisional value with an uncertainty flag rather than leaving the milestone unchanged @S168 */ }
        }
        part airTrafficControllers : AirTrafficControllers;
        part aircraftOperatorRepresentative : AircraftOperatorRepresentative {
            perform action a0 { doc /* participate to align airline intentions, schedule constraints, and slot management decisions with the shared plan @S039 */ }
            perform action a1 { doc /* validates that operator priorities are visible where they are allowed by the Business Rules Registry and local coordination agreements @S055 */ }
            perform action a2 { doc /* provides aircraft-specific constraints when requested @S082 */ }
            perform action a3 { doc /* sends the Crew Duty Extension Log @S620 */ }
        }
        part aircraftRegistration : AircraftRegistration;
        part airlineInterfaceAdapter : AirlineInterfaceAdapter {
            perform action a0 { doc /* validates message structure @S128 */ }
            perform action a1 { doc /* maps carrier codes to the Business Rules Registry @S128 */ }
            perform action a2 { doc /* forwards accepted intent data to the Flight Data Exchange @S128 */ }
            perform action a3 { doc /* supplies operator preferences @S235 */ }
            perform action a4 { doc /* produces the Late Baggage Tag List @S452 */ }
            perform action a5 { doc /* apply carrier-specific format checks @S829 */ }
        }
        part airlineOperationsCentre : AirlineOperationsCentre {
            perform action a0 { doc /* submits a Flight Intent Message through the Airline Interface Adapter using an authenticated system account managed by the Identity Access Service @S126 */ }
            perform action a1 { doc /* receive those constraints through the Airline Interface Adapter @S135 */ }
        }
        part airlineOperationsCoordinator : AirlineOperationsCoordinator {
            perform action a0 { doc /* participate to align airline intentions, schedule constraints, and slot management decisions with the shared plan @S039 */ }
            perform action a1 { doc /* reviews material deviations from filed intent, including aircraft swaps, early cancellations, recovery flights, and known connection protection actions @S054 */ }
            perform action a2 { doc /* represents carrier operating priorities @S081 */ }
            perform action a3 { doc /* confirms that Flight Intent Message updates are complete, timely, and traceable @S081 */ }
            perform action a4 { doc /* evaluates each constraint against crew legality, aircraft rotation continuity, maintenance positioning, and passenger recovery commitments @S138 */ }
            perform action a5 { doc /* uses the delay slip when requesting an exemption review for a crew connectivity constraint that is not already represented in the allocation data @S237 */ }
            perform action a6 { doc /* confirm any operator-requested Target Off Block Time revision in the Airport CDM Portal @S260 */ }
            perform action a7 { doc /* uses the Gate Reopening Memo to confirm when a previously unavailable gate can be planned again for arrival handling, boarding, and connection recovery @S472 */ }
            perform action a8 { doc /* uses the release note to confirm that a candidate substitution is eligible for customs release @S679 */ }
            perform action a9 { doc /* sends the Passenger Misconnect Count @S740 */ }
            perform action a10 { doc /* uses the permission email to justify an approved slot substitution during post-operations review @S795 */ }
        }
        part airportAcceptanceRate : AirportAcceptanceRate;
        part airportCDMPortal : AirportCDMPortal {
            perform action a0 { doc /* provides airport stakeholders with a controlled interface for sharing operational readiness information and confirming decisions that affect the surface and terminal sequence @S016 */ }
            perform action a1 { doc /* provides the shared operational workspace @S150 */ }
            perform action a2 { doc /* highlight the affected flight @S166 */ }
            perform action a3 { doc /* notify the role accountable for the next update through the Alert Distribution Hub @S166 */ }
            perform action a4 { doc /* preserve the last synchronized milestone set @S172 */ }
            perform action a5 { doc /* clearly mark any updates entered under degraded operating procedures @S172 */ }
            perform action a6 { doc /* records duty desk confirmations as operational annotations linked to the relevant runway, taxiway, apron, or stand area @S185 */ }
            perform action a7 { doc /* presents each proposed value with its confidence status, last update time, and the reason code assigned by the proposing function or authorized user @S264 */ }
            perform action a8 { doc /* requires a revised reason code @S270 */ }
            perform action a9 { doc /* marks the earlier value as superseded rather than deleted @S270 */ }
            perform action a10 { doc /* publish tower readiness changes to authenticated airline and handling users within the configured refresh interval @S293 */ }
            perform action a11 { doc /* presents the resource-driven feasibility status to the Airline Operations Coordinator and the Aircraft Operator Representative @S312 */ }
            perform action a12 { doc /* displays the active restriction status, expected operational effect, and any related coordination notes on the Common Situation Display @S337 */ }
            perform action a13 { doc /* records the selected fluid type, mixture ratio, treatment start time, treatment completion time, and expected holdover reference for each treated aircraft @S381 */ }
            perform action a14 { doc /* presents the resulting arrival plan to Aircraft Operator Representative users @S405 */ }
            perform action a15 { doc /* records acknowledgements in the Collaborative Decision Log @S405 */ }
            perform action a16 { doc /* exposes agreed Target Off Block Time values and stakeholder remarks to the tactical position in read-only mode @S429 */ }
            perform action a17 { doc /* uses the window token to preserve the agreed pushback opportunity @S503 */ }
            perform action a18 { doc /* uses the shuttle count to confirm that remote-stand passenger transfer demand is consistent with stand readiness timing @S648 */ }
        }
        part airportCapacityPlan : AirportCapacityPlan;
        part airportDutyManager : AirportDutyManager {
            perform action a0 { doc /* confirms terminal opening status, essential facility readiness, and airport service constraints that may affect the first operational waves @S062 */ }
            perform action a1 { doc /* confirms that airport-side constraints are reflected consistently across the Airport CDM Portal and the Common Situation Display @S088 */ }
            perform action a2 { doc /* request a manual capacity review @S116 */ }
            perform action a3 { doc /* monitors the Common Situation Display to ensure airline recovery decisions remain consistent with terminal capacity and passenger processing conditions @S144 */ }
            perform action a4 { doc /* maintains the airport duty desk as the single operational point for airport status confirmation during Normal Operations, Adverse Weather Mode, Capacity Reduction State, and Recovery Phase @S177 */ }
            perform action a5 { doc /* uses the Runway Inspection Note to confirm that the duty desk has a current record of pavement status @S181 */ }
            perform action a6 { doc /* briefs open safety checks, unresolved surveillance discrepancies, and any tower coordination points that remain active @S196 */ }
            perform action a7 { doc /* declare Normal Operations, Adverse Weather Mode, Capacity Reduction State, Recovery Phase, or Contingency Fallback State from the tactical header @S435 */ }
            perform action a8 { doc /* sends the Medical Diversion Notice @S496 */ }
            perform action a9 { doc /* produces the Customs Hold Release Note @S568 */ }
            perform action a10 { doc /* uses the Apron Sweep Completion Note to confirm that apron availability constraints do not invalidate an approved substitution @S678 */ }
            perform action a11 { doc /* review late airport-driven changes that affected multiple flights @S809 */ }
            perform action a12 { doc /* record whether the operational justification was valid @S809 */ }
        }
        part airportNetwork : AirportNetwork {
            perform action a0 { doc /* routinely operates near declared capacity during Normal Operations @S003 */ }
            exhibit state modes {
                state s0 { doc /* Normal Operations @S003 */ }
            }
        }
        part airportParticipant : AirportParticipant {
            perform action a0 { doc /* update a material change within two minutes of becoming aware of it during Normal Operations and within one minute during Adverse Weather Mode or Capacity Reduction State @S167 */ }
        }
        part airspaceSectorPlanner : AirspaceSectorPlanner {
            perform action a0 { doc /* declares expected sector constraints, route availability assumptions, and any planned staffing limitations that could influence arrival or departure metering @S058 */ }
            perform action a1 { doc /* validating sector constraints in the Sector Load Monitor @S079 */ }
            perform action a2 { doc /* advising whether demand smoothing is required before tactical execution @S079 */ }
            perform action a3 { doc /* converts confirmed restricted area information into sector availability assumptions @S326 */ }
            perform action a4 { doc /* checks whether existing flight plans require rerouting, metering, or ground delay action @S326 */ }
        }
        part alertDistributionHub : AlertDistributionHub {
            perform action a0 { doc /* notifies participating roles that the morning plan is available and that changes must be entered through controlled Regional Flow Platform functions @S073 */ }
            perform action a1 { doc /* notifies the Regional Flow Manager, Tower Supervisor, and Airline Operations Coordinator that the capacity picture may change @S121 */ }
            perform action a2 { doc /* distributes approved duty coordination alerts to affected operational roles @S193 */ }
            perform action a3 { doc /* applies subscription rules from the Business Rules Registry @S332 */ }
            perform action a4 { doc /* highlights the affected runway queue on the Common Situation Display @S366 */ }
            perform action a5 { doc /* distribute surface equipment and apron congestion advisories to subscribed operational roles within the latency target defined in the Business Rules Registry @S461 */ }
            perform action a6 { doc /* sends notifications to Regional Flow Manager, Tower Supervisor, Ramp Control Lead, Slot Coordinator, and Network Operations Liaison @S614 */ }
        }
        part arrivalRegulationConsole : ArrivalRegulationConsole {
            perform action a0 { doc /* highlights inbound demand periods where holding, speed control, or upstream sequencing may be needed if the forecast capacity materializes @S070 */ }
            perform action a1 { doc /* presents proposed arrival opportunities with the capacity source, regulation start time, and expected delay for each affected flight @S241 */ }
            perform action a2 { doc /* issues alerts before predicted holding stacks form @S407 */ }
            perform action a3 { doc /* suppress handler-exception annotations for arriving flights unless the exception changes the Airport Acceptance Rate or a regulated arrival sequence @S535 */ }
            perform action a4 { doc /* uses the Medical Diversion Notice to protect arrival priority, stand assignment timing, and downstream border coordination in the active arrival plan @S576 */ }
            perform action a5 { doc /* use the approved rules recorded in the Business Rules Registry @S980 */ }
        }
        part arrivalWorkspace : ArrivalWorkspace {
            perform action a0 { doc /* shows expected landing demand, stand allocation risk, inbound regulation effects, and handling readiness indicators needed to protect the Airport Acceptance Rate @S155 */ }
        }
        part auditEventLedger : AuditEventLedger {
            perform action a0 { doc /* preserve the rationale, timing, and authorization of material operational decisions @S021 */ }
            perform action a1 { doc /* retains the trace from incoming forecast product to capacity value @S123 */ }
            perform action a2 { doc /* retains movement updates from the Ramp Movement Board @S222 */ }
            perform action a3 { doc /* stores the previous value, new value, responsible user or automated function, timestamp, authority basis, and applicable operating state for every target time change @S271 */ }
            perform action a4 { doc /* capture successful and failed authentication attempts, role changes, privilege elevations, operational approvals, configuration changes, data exports, and emergency access activations @S777 */ }
            perform action a5 { doc /* preserve the time source applied by the Time Synchronization Service @S792 */ }
            perform action a6 { doc /* record each proposed option, the user response, and the final decision @S955 */ }
            perform action a7 { doc /* support traceability, least-privilege access, and after-action accountability for all operationally significant changes @S981 */ }
        }
        part auditRecords : AuditRecords;
        part authenticatedAirlineAndHandlingUsers : AuthenticatedAirlineAndHandlingUsers;
        part authorizedUsers : AuthorizedUsers;
        part businessRulesRegistry : BusinessRulesRegistry {
            perform action a0 { doc /* retain the local parameters needed for Meridian operations @S939 */ }
        }
        part calculatedTakeoffTime : CalculatedTakeoffTime;
        part capacityAssessmentModule : CapacityAssessmentModule {
            perform action a0 { doc /* supports the assessment of declared and tactical capacity using weather, runway availability, sector loading, and airport resource conditions @S014 */ }
            perform action a1 { doc /* combines the runway declaration, weather outlook, airspace constraints, stand readiness, and ground resource assumptions into a proposed Airport Acceptance Rate by period @S066 */ }
            perform action a2 { doc /* combines demand projections with the Airport Capacity Plan to determine whether a published Airport Acceptance Rate remains feasible @S107 */ }
            perform action a3 { doc /* applies the current wind, visibility, and precipitation assumptions @S114 */ }
            perform action a4 { doc /* flags the associated capacity values as provisional @S120 */ }
            perform action a5 { doc /* uses the Storm Cell Snapshot to qualify capacity confidence during convective weather impacts @S133 */ }
            perform action a6 { doc /* use the confirmed airport position to recalculate available capacity @S192 */ }
            perform action a7 { doc /* recalculates the effective Airport Acceptance Rate @S341 */ }
            perform action a8 { doc /* passes the revised assumption into the operational planning cycle @S341 */ }
            perform action a9 { doc /* compares that demand with the active Airport Acceptance Rate, runway configuration, taxiway constraints, and sector limits @S351 */ }
            perform action a10 { doc /* reduces practical departure capacity to account for deicing time, pad transit time, and slower ramp taxi speeds @S373 */ }
            perform action a11 { doc /* calculates candidate Airport Acceptance Rate values for each runway configuration @S400 */ }
            perform action a12 { doc /* exposes the operational basis for each value on the Common Situation Display @S400 */ }
            perform action a13 { doc /* reject data that lacks a trusted timestamp @S825 */ }
            perform action a14 { doc /* record the available Airport Acceptance Rate used in each baseline @S853 */ }
        }
        part cargoAndGeneralAviationAerodromes : CargoAndGeneralAviationAerodromes {
            perform action a0 { doc /* operating within shared terminal airspace @S001 */ }
        }
        part collaborativeDecisionLog : CollaborativeDecisionLog {
            perform action a0 { doc /* preserve the rationale, timing, and authorization of material operational decisions @S021 */ }
            perform action a1 { doc /* records who changed a value, when the change was made, whether the change was provisional or confirmed, and what operational decision relied on it @S169 */ }
            perform action a2 { doc /* captures the time, origin, and rationale for each local coordination decision that affects capacity or surface flow @S186 */ }
            perform action a3 { doc /* records each challenge, counterproposal, acceptance, rejection, and reason code associated with the Target Off Block Time and Calculated Takeoff Time @S267 */ }
            perform action a4 { doc /* retain the stated reason, decision time, affected flight, and visible operational context for each material change to a slot or sequence @S794 */ }
            perform action a5 { doc /* record each proposed option, the user response, and the final decision @S955 */ }
        }
        part commonServices : CommonServices;
        part commonSituationDisplay : CommonSituationDisplay {
            perform action a0 { doc /* give authorized users a shared view of demand, capacity, constraints, and active traffic management measures @S020 */ }
            perform action a1 { doc /* presents the approved pre-tactical baseline as the shared reference for Normal Operations, Adverse Weather Mode, Capacity Reduction State, and early Recovery Phase decisions @S072 */ }
            perform action a2 { doc /* distinguishes values supplied by connected services, values confirmed by users, and values that have exceeded the configured freshness threshold @S165 */ }
            perform action a3 { doc /* shows the current agreed target set @S265 */ }
            perform action a4 { doc /* shows crew legality impacts as coded operational states, such as feasible, time critical, infeasible, or operator review required @S627 */ }
        }
        part complianceAssessment : ComplianceAssessment;
        part confidenceRecord : ConfidenceRecord {
            perform action a0 { doc /* stores the originating feed, the processing time, the transformation version, and any manual override applied by the Meteorology Briefing Officer @S119 */ }
        }
        part contingencyOperationsConsole : ContingencyOperationsConsole {
            perform action a0 { doc /* provides a degraded channel for recording tower and duty desk decisions until normal service is restored @S195 */ }
            perform action a1 { doc /* preserves the last valid allocation @S247 */ }
            perform action a2 { doc /* supports manual amendments @S247 */ }
            perform action a3 { doc /* marks the resulting Slot Compliance State as provisional @S247 */ }
            perform action a4 { doc /* accept emergency access activations @S783 */ }
            perform action a5 { doc /* generated by the Contingency Operations Console @S952 */ }
        }
        part crewReadiness : CrewReadiness;
        part criticalIncident : CriticalIncident;
        part dataGovernanceSteward : DataGovernanceSteward {
            perform action a0 { doc /* verifies that operational decisions, role acknowledgements, and exception handling are captured in the Audit Event Ledger with synchronized timestamps from the Time Synchronization Service @S098 */ }
            perform action a1 { doc /* defines the mandatory fields, permissible status values, retention rules, and data quality thresholds used by the Airport CDM Portal @S170 */ }
            perform action a2 { doc /* verify that audit fields required for slot performance reporting remain complete, immutable, and traceable to approved data definitions @S806 */ }
            perform action a3 { doc /* maintain the data ownership register @S813 */ }
            perform action a4 { doc /* coordinate updates through the Business Rules Registry @S813 */ }
            perform action a5 { doc /* coordinate discrepancy resolution with the responsible operational owner @S833 */ }
            perform action a6 { doc /* record the disposition in the Audit Event Ledger @S833 */ }
            perform action a7 { doc /* train operational users on data quality responsibilities, privacy expectations, and the correct interpretation of audit records in the Audit Event Ledger @S876 */ }
        }
        part dedicatedMilestoneView : DedicatedMilestoneView {
            perform action a0 { doc /* records the planned, target, estimated, actual, and manually confirmed times for each turnaround event that affects a regulated departure or constrained arrival @S156 */ }
        }
        part deicingCoordinator : DeicingCoordinator {
            perform action a0 { doc /* provides pre-tactical and tactical advice @S092 */ }
            perform action a1 { doc /* sends the Deicing Pad Queue Card @S294 */ }
            perform action a2 { doc /* marks the treatment as expired @S390 */ }
            perform action a3 { doc /* returns the aircraft to the appropriate queue state @S390 */ }
        }
        part demandPredictionService : DemandPredictionService {
            perform action a0 { doc /* estimates expected demand from scheduled operations, Flight Intent Message data, known airline recovery plans, and near-term operational changes @S013 */ }
            perform action a1 { doc /* converts the normalized schedule into expected arrival and departure demand by time band, runway direction, terminal area, and major traffic flow @S053 */ }
            perform action a2 { doc /* generates the demand forecast used by the Regional Flow Platform @S101 */ }
            perform action a3 { doc /* receives filed flight information through the Flight Data Exchange @S103 */ }
            perform action a4 { doc /* compares it with the current operating schedule held by the Airline Interface Adapter @S103 */ }
            perform action a5 { doc /* uses recent conformance history, aircraft rotation timing, and known bank structures to estimate arrival and departure loads by planning interval @S105 */ }
            perform action a6 { doc /* uses current airline intents to refine departure demand, arrival demand, and recovery demand by time band @S131 */ }
            perform action a7 { doc /* refresh stand demand forecasts @S216 */ }
            perform action a8 { doc /* estimates demand pressure over the next planning horizon @S251 */ }
            perform action a9 { doc /* marks flights whose proposed Target Off Block Time values are likely to cause runway or sector imbalance @S251 */ }
            perform action a10 { doc /* estimates the departure demand profile by stand, apron area, runway, and departure fix @S350 */ }
            perform action a11 { doc /* reject data that lacks a trusted timestamp @S825 */ }
        }
        part departureMeteringService : DepartureMeteringService {
            perform action a0 { doc /* estimates provisional Target Off Block Time sensitivity @S069 */ }
            perform action a1 { doc /* presents proposed departure opportunities and associated Calculated Takeoff Time values for coordination with the Tower Sequence Manager @S242 */ }
            perform action a2 { doc /* aligns each Target Off Block Time with the applicable Calculated Takeoff Time @S278 */ }
            perform action a3 { doc /* converts runway demand into controlled stand delay @S348 */ }
            perform action a4 { doc /* derives a feasible Target Off Block Time that protects the Calculated Takeoff Time without overloading the surface movement area @S352 */ }
            perform action a5 { doc /* sends revised departure metering advisories @S426 */ }
            perform action a6 { doc /* translates runway metering limits into candidate pushback spacing for the Slot Allocation Engine @S456 */ }
            perform action a7 { doc /* reject data that lacks a trusted timestamp @S825 */ }
            perform action a8 { doc /* uses the Passenger Misconnect Count to weight departure sequencing decisions when connection protection is an approved local objective @S851 */ }
            perform action a9 { doc /* use the approved rules recorded in the Business Rules Registry @S980 */ }
            exhibit state modes {
                state s0 { doc /* monitoring mode @S728 */ }
            }
        }
        part digitalBriefingRoom : DigitalBriefingRoom {
            perform action a0 { doc /* displays the emerging Airport Capacity Plan @S071 */ }
            perform action a1 { doc /* records unresolved assumptions in the Collaborative Decision Log for confirmation during the morning coordination briefing @S071 */ }
            perform action a2 { doc /* records the diversion rationale, priority classification, resource commitment, and agreed recovery target in the Collaborative Decision Log @S506 */ }
        }
        part eastApronSensor : EastApronSensor {
            perform action a0 { doc /* reports stand occupancy transitions, pushback lane blockage durations, and sensor confidence values at a synchronized event time @S578 */ }
        }
        part emergencyAccess : EmergencyAccess;
        part emergencyResponseCoordinator : EmergencyResponseCoordinator;
        part flightDataExchange : FlightDataExchange {
            perform action a0 { doc /* normalizes flight identifiers, aircraft types, routing fields, and planned operating times @S052 */ }
            perform action a1 { doc /* provides current flight intent data @S278 */ }
            perform action a2 { doc /* publishes revised Flight Intent Message content @S684 */ }
            perform action a3 { doc /* validate Flight Intent Message content @S827 */ }
            perform action a4 { doc /* accept richer intent data, including improved route options, expected cruise profiles, and updated departure readiness information @S940 */ }
        }
        part flightIntentMessage : FlightIntentMessage;
        part freshnessIndicator : FreshnessIndicator;
        part gateConflictDetector : GateConflictDetector {
            perform action a0 { doc /* alerts the Ramp Control Lead when a planned arrival, departure, or tow would create an overlapping occupancy condition at a stand or adjacent service lane @S210 */ }
            perform action a1 { doc /* produces the Gate Reopening Memo @S386 */ }
        }
        part groundHandlingDispatcher : GroundHandlingDispatcher {
            perform action a0 { doc /* confirms whether planned handling teams and equipment coverage are sufficient for the expected concentration of turns in each apron area @S064 */ }
            perform action a1 { doc /* confirms that handling resource assumptions are current in the Handling Resource Planner @S091 */ }
            perform action a2 { doc /* escalates material deviations through the Airport Duty Manager @S091 */ }
            perform action a3 { doc /* sends the Crew Bus Delay Slip @S140 */ }
            perform action a4 { doc /* updates the Handling Resource Planner with expected service completion times @S302 */ }
            perform action a5 { doc /* uses the tag list to confirm which flights require baggage reconciliation @S519 */ }
            perform action a6 { doc /* sends the Towbar Shortage Report @S523 */ }
        }
        part groundHandlingPersonnel : GroundHandlingPersonnel;
        part handlingResourcePlanner : HandlingResourcePlanner {
            perform action a0 { doc /* compares the demand curve with available ground resources @S065 */ }
            perform action a1 { doc /* flags time bands where aircraft turn performance is likely to reduce stand availability @S065 */ }
            perform action a2 { doc /* correlated by the Handling Resource Planner with stand occupancy, baggage readiness, catering status, and boarding progress @S141 */ }
            perform action a3 { doc /* maintains the operational view of dispatch teams, tow teams, ramp buses, belt loaders, high loaders, stairs, ground power units, air start units, and potable water equipment @S303 */ }
            perform action a4 { doc /* uses the Stand Tow Request Form to reserve towing capacity and to test whether the requested movement can be completed before the proposed Target Off Block Time @S304 */ }
            perform action a5 { doc /* produces the Remote Stand Shuttle Count at regular operating intervals to represent available passenger transfer capacity for remote stand activity @S547 */ }
            perform action a6 { doc /* validate resource quantities, task timing, and allocation identifiers against active operational reference data @S830 */ }
        }
        part harborEastAirport : HarborEastAirport;
        part highFrequencyDomesticAirports : HighFrequencyDomesticAirports;
        part highPriorityIncident : HighPriorityIncident;
        part identityAccessService : IdentityAccessService {
            perform action a0 { doc /* controlled by the Identity Access Service @S152 */ }
            perform action a1 { doc /* restricts entry of duty desk confirmations to authorized airport operations staff @S194 */ }
            perform action a2 { doc /* records each transaction in the Audit Event Ledger @S194 */ }
            perform action a3 { doc /* support rapid suspension of accounts @S781 */ }
            perform action a4 { doc /* records the authorizing incident reference and expiry time @S783 */ }
            perform action a5 { doc /* support traceability, least-privilege access, and after-action accountability for all operationally significant changes @S981 */ }
        }
        part incidentRecord : IncidentRecord;
        part integratedTacticalManagementPosition : IntegratedTacticalManagementPosition {
            perform action a0 { doc /* presents a combined tactical view @S420 */ }
        }
        part lakesideRegionalAirport : LakesideRegionalAirport;
        part meridianInternationalAirport : MeridianInternationalAirport;
        part meridianRegion : MeridianRegion;
        part meridianRegionalAirTrafficFlowManagementAndAirportCollaborativeDecisionMakingSystem : MeridianRegionalAirTrafficFlowManagementAndAirportCollaborativeDecisionMakingSystem;
        part meteorologyBriefingOfficer : MeteorologyBriefingOfficer {
            perform action a0 { doc /* provides the morning weather outlook with emphasis on wind trend, ceiling, visibility, convective risk, temperature limits, and confidence over the planning horizon @S056 */ }
            perform action a1 { doc /* produces the Storm Cell Snapshot @S085 */ }
            perform action a2 { doc /* briefs forecast confidence, timing risk, and expected operational impact in the Digital Briefing Room using data supplied through the Weather Ingest Gateway @S086 */ }
            perform action a3 { doc /* states the trigger conditions that would justify moving from Normal Operations to Adverse Weather Mode @S087 */ }
            perform action a4 { doc /* reviews degraded weather inputs @S112 */ }
        }
        part militaryAirspaceLiaison : MilitaryAirspaceLiaison {
            perform action a0 { doc /* confirms whether shared airspace assumptions remain valid for the morning @S059 */ }
            perform action a1 { doc /* identifies any conditional availability that must be treated as uncertain @S059 */ }
            perform action a2 { doc /* confirms military airspace availability assumptions @S093 */ }
            perform action a3 { doc /* alerts the Regional Flow Manager when civil routing options may be constrained @S093 */ }
            perform action a4 { doc /* sends the Temporary Restriction Notice @S325 */ }
            perform action a5 { doc /* confirming the activation window, affected volume, controlling authority, and any published contingency conditions @S325 */ }
        }
        part namedOperationalUser : NamedOperationalUser {
            perform action a0 { doc /* authenticate with an individually assigned identity @S764 */ }
        }
        part networkOperationsLiaison : NetworkOperationsLiaison {
            perform action a0 { doc /* participate to align airline intentions, schedule constraints, and slot management decisions with the shared plan @S039 */ }
            perform action a1 { doc /* coordinates with adjacent network units @S083 */ }
            perform action a2 { doc /* confirms that regional measures remain compatible with upstream and downstream flow constraints @S083 */ }
            perform action a3 { doc /* records external coordination outcomes in the Collaborative Decision Log @S084 */ }
        }
        part northRunwayMeter : NorthRunwayMeter {
            perform action a0 { doc /* receive runway-specific capacity values @S114 */ }
            perform action a1 { doc /* maintain separate queues @S280 */ }
            perform action a2 { doc /* reduces the departure release rate @S454 */ }
        }
        part northValleyAirport : NorthValleyAirport;
        part nullPart : Null {
            perform action a0 { doc /* provide a shared air traffic flow management and airport collaborative decision-making capability @S009 */ }
            perform action a1 { doc /* prepared each morning @S049 */ }
            perform action a2 { doc /* locked for operational use @S049 */ }
            perform action a3 { doc /* tested against the demand profile to identify overloads, underused capacity, and points where a Ground Delay Program may become necessary @S067 */ }
            perform action a4 { doc /* the pre-tactical capacity review begins @S085 */ }
            perform action a5 { doc /* confirm that decisions and unresolved issues are available to the Performance Analytics Warehouse for later inclusion in the Post Operations Report @S099 */ }
            perform action a6 { doc /* built from demand forecasts, observed traffic, airport resource status, airspace constraints, and weather products @S100 */ }
            perform action a7 { doc /* checked for source identity, issue time, valid time, spatial reference, and unit consistency @S109 */ }
            perform action a8 { doc /* made available to the Regional Flow Platform @S109 */ }
            perform action a9 { doc /* translated into capacity modifiers for runway configuration, arrival spacing, departure spacing, surface movement constraints, and approach sector availability @S113 */ }
            perform action a10 { doc /* recorded as a confidence class, a probability value where provided by the source, a valid time range, and the forecast horizon used for the calculation @S118 */ }
            perform action a11 { doc /* written to the Collaborative Decision Log with synchronized timestamps @S122 */ }
            perform action a12 { doc /* rejected with machine-readable reasons @S129 */ }
            perform action a13 { doc /* captured in the Collaborative Decision Log with the requesting airline, operational rationale, decision owner, and final resolution @S145 */ }
            perform action a14 { doc /* preserved in the Audit Event Ledger for post-operations reconstruction @S149 */ }
            perform action a15 { doc /* recorded in the Collaborative Decision Log with the reason code, revised Target Off Block Time, and affected flight identifier @S321 */ }
            perform action a16 { doc /* revised with a winter margin @S374 */ }
            perform action a17 { doc /* drafted directly from the display @S440 */ }
            perform action a18 { doc /* checked against current capacity assumptions @S440 */ }
            perform action a19 { doc /* routed through the Alert Distribution Hub for stakeholder acknowledgement @S440 */ }
            perform action a20 { doc /* displayed on Common Situation Display with the source constraint, effective interval, affected runway or fix, and expected delay impact @S613 */ }
            perform action a21 { doc /* displayed on the Common Situation Display @S822 */ }
            perform action a22 { doc /* acknowledged within fifteen minutes @S920 */ }
            perform action a23 { doc /* acknowledged within thirty minutes @S921 */ }
            perform action a24 { doc /* reviewed with the affected operational supervisor at least hourly @S921 */ }
            exhibit state modes {
                state s0 { doc /* Slot Compliance State @S023 */ }
                state s1 { doc /* aging @S823 */ }
                state s2 { doc /* blocked @S646 */ }
                state s3 { doc /* cleaned @S646 */ }
                state s4 { doc /* current @S823 */ }
                state s5 { doc /* feasible @S627 */ }
                state s6 { doc /* infeasible @S627 */ }
                state s7 { doc /* inspection-required state @S663 */ }
                state s8 { doc /* operator review required @S627 */ }
                state s9 { doc /* ready @S646 */ }
                state s10 { doc /* stale @S823 */ }
                state s11 { doc /* time critical @S627 */ }
                state s12 { doc /* unavailable @S823 */ }
                state s13 { doc /* unchecked @S646 */ }
                state s14 { doc /* under inspection @S646 */ }
            }
        }
        part operationalSegregation : OperationalSegregation;
        part passengerConnectionSensitivity : PassengerConnectionSensitivity;
        part performanceAnalyticsWarehouse : PerformanceAnalyticsWarehouse {
            perform action a0 { doc /* retains the baseline inputs, capacity declarations, and approval timestamps @S074 */ }
            perform action a1 { doc /* compares submitted intents, issued constraints, actual off-block times, and achieved arrival outcomes to improve recovery playbooks @S148 */ }
            perform action a2 { doc /* uses the recorded milestones and decision history to compare planned outcomes with actual off-block, takeoff, landing, and stand events @S173 */ }
            perform action a3 { doc /* aggregate compliance outcomes by carrier, route group, regulation, airport operating configuration, and time band @S804 */ }
            perform action a4 { doc /* retain data quality measures, including validation failure rates, freshness breaches, manual corrections, and recurring ownership conflicts @S836 */ }
            perform action a5 { doc /* calculate delay absorption as the portion of expected airborne or terminal-area delay that is converted into controlled ground delay before departure @S839 */ }
            perform action a6 { doc /* apply approved fuel burn and emissions factors by aircraft category, operating phase, and delay location @S856 */ }
        }
        part postOperationsReport : PostOperationsReport {
            perform action a0 { doc /* present regional benefits alongside operational trade-offs @S862 */ }
        }
        part preferredRoute : PreferredRoute;
        part primaryInternationalHub : PrimaryInternationalHub;
        part primaryWorkspace : PrimaryWorkspace {
            perform action a0 { doc /* presents the Common Situation Display with synchronized clocks, active operating state, airport demand, runway configuration, stand occupancy, and milestone status for each managed movement @S153 */ }
        }
        part rampControlLead : RampControlLead {
            perform action a0 { doc /* reviews early stand readiness using information from the Ramp Movement Board, East Apron Sensor, West Apron Sensor, and handling coordination calls @S063 */ }
            perform action a1 { doc /* maintains the Ramp Movement Board in a state that supports reliable departure metering @S090 */ }
            perform action a2 { doc /* uses the Ramp Movement Board to identify whether the proposed recovery action can be supported without creating surface congestion @S142 */ }
            perform action a3 { doc /* maintains the operational sequence for pushbacks, stand exits, stand entries, and towing movements within the controlled apron area @S200 */ }
            perform action a4 { doc /* release a pushback @S202 */ }
            perform action a5 { doc /* sends the Stand Tow Request Form @S208 */ }
            perform action a6 { doc /* increases spacing between pushbacks and towing movements to account for slower ground servicing and reduced driver visibility @S219 */ }
            perform action a7 { doc /* uses the queue card to verify pad entry order @S378 */ }
            perform action a8 { doc /* coordinate every pad release with the Tower Supervisor @S387 */ }
            perform action a9 { doc /* uses the Towbar Shortage Report to determine whether remote stand aircraft can be repositioned without creating secondary apron congestion @S556 */ }
            perform action a10 { doc /* sends the Apron Sweep Completion Note @S647 */ }
        }
        part rampMovementBoard : RampMovementBoard {
            perform action a0 { doc /* records a material change in planned off-block timing @S216 */ }
            perform action a1 { doc /* maintains milestone timestamps for stand readiness, boarding completion, doors closed, start approval readiness, taxi start, and other locally configured departure events @S255 */ }
            perform action a2 { doc /* shows occupied stands, blocked service roads, and pending pushback areas @S311 */ }
            perform action a3 { doc /* produces the Fuel Truck Hold Advice @S361 */ }
            perform action a4 { doc /* displays each aircraft as pending push, taxi to pad, in treatment, awaiting release, or returning to stand @S377 */ }
            perform action a5 { doc /* refresh the apron movement layer within five seconds of each validated surface event @S427 */ }
            perform action a6 { doc /* displays the resulting constraint as a stand-level exception with a time band rather than as a continuous stream of equipment messages @S525 */ }
            perform action a7 { doc /* displays remote stand occupancy, expected towing actions, and bus service readiness in a shared view for airside coordination @S551 */ }
            perform action a8 { doc /* provide actual movement milestones that support independent verification of slot performance @S801 */ }
            perform action a9 { doc /* provide surface queue counts based on movement status and surveillance confirmation @S844 */ }
            perform action a10 { doc /* use the approved rules recorded in the Business Rules Registry @S980 */ }
        }
        part rampPersonnel : RampPersonnel;
        part readinessGate1 : ReadinessGate1 {
            perform action a0 { doc /* confirm that governance, security approvals, user role definitions, operating hours, and support escalation paths are documented and accepted by local stakeholders @S894 */ }
        }
        part readinessGate2 : ReadinessGate2;
        part readinessGate3 : ReadinessGate3;
        part readinessGate4 : ReadinessGate4;
        part regionalFlowManager : RegionalFlowManager {
            perform action a0 { doc /* balancing demand against capacity across the Meridian region @S010 */ }
            perform action a1 { doc /* coordinating regional traffic management actions @S010 */ }
            perform action a2 { doc /* confirms that the planning horizon, cutover time, and review checkpoints are understood by the participating operational roles @S050 */ }
            perform action a3 { doc /* reviews the Airport Capacity Plan, the Ground Delay Program status, and any Tactical Regulation Proposal @S078 */ }
            perform action a4 { doc /* chairs decision checkpoints @S094 */ }
            perform action a5 { doc /* authorizes changes to flow measures @S094 */ }
            perform action a6 { doc /* uses the Common Situation Display to compare forecast demand, assessed capacity, and any active Ground Delay Program effects in one operational view @S117 */ }
            perform action a7 { doc /* confirms airline recovery priorities @S137 */ }
            perform action a8 { doc /* authorizes a controlled transition from Capacity Reduction State toward Recovery Phase @S393 */ }
            perform action a9 { doc /* uses the restriction notice to bound the arrival regulation timeline @S399 */ }
            perform action a10 { doc /* uses the load sheet to confirm whether a departure fix constraint should be represented as an airport departure measure @S598 */ }
            perform action a11 { doc /* use the Post Operations Report to identify whether noncompliance resulted from operator choice, airport constraint, airspace constraint, weather impact, or system issue @S808 */ }
        }
        part regionalFlowPlatform : RegionalFlowPlatform {
            perform action a0 { doc /* integrate planning, tactical regulation, airport readiness, and post-event analysis into a single operational environment @S012 */ }
            perform action a1 { doc /* creates the initial demand picture from published schedules, approved seasonal allocations, overnight schedule changes, and received Flight Intent Message data @S051 */ }
            perform action a2 { doc /* reconciles them with airport and airspace constraints @S130 */ }
            perform action a3 { doc /* permits more frequent intent updates @S147 */ }
            perform action a4 { doc /* retaining the previous values needed for audit and performance review @S147 */ }
            perform action a5 { doc /* expose the current regional demand and constraint context to the shared workspace at each publication cycle without requiring manual re-entry @S164 */ }
            perform action a6 { doc /* receives confirmed capacity impacts through normal system interfaces @S191 */ }
            perform action a7 { doc /* creates the initial Target Off Block Time proposal from current flight intent, stand readiness, turnaround progress, and applicable airport capacity constraints @S250 */ }
            perform action a8 { doc /* locks the Target Off Block Time unless a rule-based exception or an authorized operational override is recorded @S268 */ }
            perform action a9 { doc /* marks a proposed Target Off Block Time as conditional @S314 */ }
            perform action a10 { doc /* records each airspace alert, acknowledgement, and downstream decision in the Audit Event Ledger for traceability and later review @S333 */ }
            perform action a11 { doc /* normalizes each Flight Intent Message against the current Airport Capacity Plan @S349 */ }
            perform action a12 { doc /* enters the winter operating mode @S371 */ }
            perform action a13 { doc /* synchronizes the tactical display with the Time Synchronization Service @S422 */ }
            perform action a14 { doc /* record the initiating user, the approving user, the affected operational object, and the effective time of the decision @S775 */ }
            perform action a15 { doc /* reconcile contingency actions with the Collaborative Decision Log @S787 */ }
            perform action a16 { doc /* record slot compliance events in the Audit Event Ledger using the operating date, flight identifier, airport, runway direction, and applicable regulation reference @S789 */ }
            perform action a17 { doc /* produces parallel outputs for comparison by operational users @S905 */ }
            exhibit state modes {
                state s0 { doc /* winter operating mode @S371 */ }
            }
        }
        part regionalSystem : RegionalSystem {
            perform action a0 { doc /* provides a shared coordination layer @S028 */ }
        }
        part requestedDepartureTiming : RequestedDepartureTiming;
        part responsibleSweepTeam : ResponsibleSweepTeam {
            perform action a0 { doc /* confirms that the assigned apron area is clean, safe, and free of observed foreign object debris @S647 */ }
        }
        part roleProfiles : RoleProfiles {
            perform action a0 { doc /* grant the minimum access needed to view, propose, approve, or administer operational data within the Regional Flow Platform @S767 */ }
        }
        part sectorLoadMonitor : SectorLoadMonitor {
            perform action a0 { doc /* contributes airspace demand indicators @S106 */ }
            perform action a1 { doc /* produces the Departure Fix Load Sheet @S484 */ }
            perform action a2 { doc /* provide the common inputs needed to connect airspace capacity and airport capacity in the same prediction cycle @S943 */ }
        }
        part sharedOperationalPicture : SharedOperationalPicture;
        part sharedWorkspace : SharedWorkspace;
        part slotAllocationEngine : SlotAllocationEngine {
            perform action a0 { doc /* supports fair and traceable allocation of constrained departure and arrival opportunities @S015 */ }
            perform action a1 { doc /* converts accepted constraints into Calculated Takeoff Time values and Target Off Block Time guidance for affected flights @S134 */ }
            perform action a2 { doc /* publishes a revised constraint set @S137 */ }
            perform action a3 { doc /* proposes regulated departure and arrival opportunities by matching demand from the Demand Prediction Service to constraints supplied by the Capacity Assessment Module @S225 */ }
            perform action a4 { doc /* derives a Calculated Takeoff Time or arrival opportunity that preserves the declared capacity envelope @S227 */ }
            perform action a5 { doc /* derives the Calculated Takeoff Time by combining runway metering constraints, departure fix loading, and applicable Ground Delay Program rules @S253 */ }
            perform action a6 { doc /* adjust allocated departure times @S355 */ }
            perform action a7 { doc /* recalculates affected Calculated Takeoff Time values @S374 */ }
            perform action a8 { doc /* support a Ground Delay Program that meters selected arrivals @S398 */ }
            perform action a9 { doc /* produces the Pushback Window Token @S428 */ }
            perform action a10 { doc /* reject data that lacks a trusted timestamp @S825 */ }
            perform action a11 { doc /* use the approved rules recorded in the Business Rules Registry @S980 */ }
        }
        part slotComplianceState : SlotComplianceState;
        part slotCoordinator : SlotCoordinator {
            perform action a0 { doc /* participate to align airline intentions, schedule constraints, and slot management decisions with the shared plan @S039 */ }
            perform action a1 { doc /* uses the Slot Allocation Engine to prepare an initial slot feasibility view @S068 */ }
            perform action a2 { doc /* confirms that the Slot Allocation Engine applies the current Business Rules Registry parameters @S080 */ }
            perform action a3 { doc /* reviews airline requests for priority handling against published equity and operational feasibility rules @S136 */ }
            perform action a4 { doc /* administers the allocation run @S229 */ }
            perform action a5 { doc /* reviews exceptions @S229 */ }
            perform action a6 { doc /* confirms that proposed results are ready for publication through the Airport CDM Portal @S229 */ }
            perform action a7 { doc /* records each accepted or rejected exemption in the Collaborative Decision Log with the rule applied, the approving role, and the expected operational consequence @S239 */ }
            perform action a8 { doc /* records the agreed pushback window rationale in the coordination notes @S356 */ }
            perform action a9 { doc /* sends the Slot Swap Permission Email @S672 */ }
            perform action a10 { doc /* assigns any revised Calculated Takeoff Time @S724 */ }
            perform action a11 { doc /* confirming runway capacity with the Tower Supervisor and surface feasibility with the Ramp Control Lead @S724 */ }
            perform action a12 { doc /* uses the Crew Duty Extension Log to check whether manually issued slot times remain operationally achievable @S726 */ }
            perform action a13 { doc /* review substitution activity after operations to confirm that priority rules were applied consistently across participating operators @S798 */ }
            perform action a14 { doc /* review slot adherence by operator, airport, time band, and regulation identifier to detect recurring causes of noncompliance @S848 */ }
        }
        part southRunwayMeter : SouthRunwayMeter {
            perform action a0 { doc /* receive runway-specific capacity values @S114 */ }
            perform action a1 { doc /* maintain separate queues @S280 */ }
        }
        part southportAirport : SouthportAirport;
        part stakeholderOrganization : StakeholderOrganization;
        part substitutionRecords : SubstitutionRecords;
        part surfaceSurveillanceAdapter : SurfaceSurveillanceAdapter {
            perform action a0 { doc /* consolidates position updates from the East Apron Sensor and West Apron Sensor @S179 */ }
            perform action a1 { doc /* presents movement indications to the Airport CDM Portal @S179 */ }
            perform action a2 { doc /* confirms whether an aircraft is still at stand, entering the movement area, holding short, or already committed to the departure stream @S281 */ }
            perform action a3 { doc /* provides current movement area occupancy and equipment status indicators to the Ramp Movement Board and the Tower Sequence Manager @S445 */ }
            perform action a4 { doc /* produces the Runway Lighting Outage Card @S606 */ }
            perform action a5 { doc /* apply position quality checks @S828 */ }
            perform action a6 { doc /* mark uncertain observations @S828 */ }
        }
        part systemPart : System {
            perform action a0 { doc /* support rapid development of a Tactical Regulation Proposal and consistent communication of the resulting Ground Delay Program @S022 */ }
            perform action a1 { doc /* help stakeholders restore scheduled flow @S023 */ }
            perform action a2 { doc /* monitoring Target Off Block Time, Calculated Takeoff Time, and Slot Compliance State performance @S023 */ }
            perform action a3 { doc /* detects a material difference from the published schedule @S104 */ }
            exhibit state modes {
                state s0 { doc /* Adverse Weather Mode @S022 */ }
                state s1 { doc /* Capacity Reduction State @S022 */ }
                state s2 { doc /* Contingency Fallback State @S047 */ }
                state s3 { doc /* Recovery Phase @S023 */ }
            }
        }
        part systemSupportEngineer : SystemSupportEngineer {
            perform action a0 { doc /* monitors portal availability, interface latency, user session faults, and synchronization status against the Time Synchronization Service @S171 */ }
            perform action a1 { doc /* investigate technical gaps @S807 */ }
            perform action a2 { doc /* investigate technical causes of missing, delayed, duplicated, or transformed records @S835 */ }
            perform action a3 { doc /* provide evidence needed for stewardship decisions @S835 */ }
            perform action a4 { doc /* train superusers on service status checks, access fault escalation, and safe use of the Contingency Operations Console during partial outages @S877 */ }
            perform action a5 { doc /* provide round the clock on call coverage for production incidents affecting the Regional Flow Platform, Airport CDM Portal, Slot Allocation Engine, Departure Metering Service, Arrival Regulation Console, and Alert Distribution Hub @S914 */ }
            perform action a6 { doc /* advise operational supervisors on technical status, known workarounds, data integrity concerns, and recovery options @S918 */ }
            perform action a7 { doc /* maintain an incident record that captures the initial symptom, affected components, operational state, timeline, mitigation actions, data corrections, and supervisor decisions @S923 */ }
        }
        part tacticalRegulationProposal : TacticalRegulationProposal;
        part targetOffBlockTime : TargetOffBlockTime;
        part temporaryAccess : TemporaryAccess;
        part timeSynchronizationService : TimeSynchronizationService {
            perform action a0 { doc /* provides the reference clock used to compare forecast issue times with operational decision times @S110 */ }
            perform action a1 { doc /* time-stamped by the Time Synchronization Service @S149 */ }
            perform action a2 { doc /* keep tower, duty desk, surveillance, and portal event times aligned @S187 */ }
            perform action a3 { doc /* provide the common time basis used for freshness calculations across the Regional Flow Platform @S824 */ }
        }
        part towerSequenceManager : TowerSequenceManager {
            perform action a0 { doc /* receives the current ramp intent through system synchronization @S217 */ }
            perform action a1 { doc /* maintains the tactical runway sequence expectation @S254 */ }
            perform action a2 { doc /* highlights cases where the Calculated Takeoff Time is inconsistent with the local departure order @S254 */ }
            perform action a3 { doc /* builds a provisional order by runway, departure fix, aircraft wake category, and locally configured spacing rule @S279 */ }
            perform action a4 { doc /* refresh affected departure sequence advisories @S334 */ }
            perform action a5 { doc /* uses the hold advice to prevent a departure from being sequenced ahead of a fueling constraint that is still active @S450 */ }
            perform action a6 { doc /* provide actual movement milestones that support independent verification of slot performance @S801 */ }
            perform action a7 { doc /* provide runway sequence counts @S844 */ }
            perform action a8 { doc /* use the approved rules recorded in the Business Rules Registry @S980 */ }
        }
        part towerSupervisor : TowerSupervisor {
            perform action a0 { doc /* sends the Runway Inspection Note before the first planning consolidation window @S060 */ }
            perform action a1 { doc /* declares anticipated runway configuration, usable operating length assumptions, and any local sequencing constraints that affect the North Runway Meter and South Runway Meter @S061 */ }
            perform action a2 { doc /* confirms that the Tower Sequence Manager reflects the current runway configuration @S089 */ }
            perform action a3 { doc /* reviews metering effects in the Tower Sequence Manager @S143 */ }
            perform action a4 { doc /* keeps the Airport Duty Manager informed of conditions that may affect runway, taxiway, stand, or apron availability @S175 */ }
            perform action a5 { doc /* confirmed that the movement can be integrated with the active ground route and runway plan @S202 */ }
            perform action a6 { doc /* confirm that any revised off-block sequence remains compatible with the Departure Metering Service @S313 */ }
            perform action a7 { doc /* uses the Runway Lighting Outage Card to confirm which runway lighting elements are unavailable @S693 */ }
        }
        part turnaroundStatus : TurnaroundStatus;
        part weatherIngestGateway : WeatherIngestGateway {
            perform action a0 { doc /* makes the outlook available to the Capacity Assessment Module @S057 */ }
            perform action a1 { doc /* preserves the forecast issue time for audit and later performance review @S057 */ }
            perform action a2 { doc /* normalizes external and local meteorological feeds @S102 */ }
            perform action a3 { doc /* accepts aviation forecasts, radar-derived precipitation fields, lightning alerts, wind forecasts, ceiling and visibility forecasts, and runway condition weather inputs from approved sources @S108 */ }
            perform action a4 { doc /* marks the feed as degraded rather than silently excluding it from the operational picture @S111 */ }
            perform action a5 { doc /* issue time-stamped weather condition updates for use in tower and airport duty coordination @S182 */ }
            perform action a6 { doc /* provide the common inputs needed to connect airspace capacity and airport capacity in the same prediction cycle @S943 */ }
        }
        part westApronSensor : WestApronSensor;
        flow f0 of SharedViewOfDemandCapacityConstraintsAndActiveTrafficManagementMeasuresItem from commonSituationDisplay to authorizedUsers { doc /* @S020 */ }
        flow f1 of NormalizedScheduleItem from flightDataExchange to demandPredictionService { doc /* @S053 */ }
        flow f2 of MorningWeatherOutlookItem from meteorologyBriefingOfficer to weatherIngestGateway { doc /* @S057 */ }
        flow f3 of MorningWeatherOutlookItem from weatherIngestGateway to capacityAssessmentModule { doc /* @S057 */ }
        flow f4 of RunwayInspectionNoteItem from towerSupervisor to nullPart { doc /* @S060 */ }
        flow f5 of EarlyStandReadinessInformationItem from rampMovementBoard to rampControlLead { doc /* @S063 */ }
        flow f6 of EarlyStandReadinessInformationItem from eastApronSensor to rampControlLead { doc /* @S063 */ }
        flow f7 of EarlyStandReadinessInformationItem from westApronSensor to rampControlLead { doc /* @S063 */ }
        flow f8 of AirportCapacityPlanItem from digitalBriefingRoom to nullPart { doc /* @S071 */ }
        flow f9 of PreTacticalBaselineItem from commonSituationDisplay to nullPart { doc /* @S072 */ }
        flow f10 of DemandForecastItem from demandPredictionService to regionalFlowPlatform { doc /* @S101 */ }
        flow f11 of FiledFlightInformationItem from flightDataExchange to demandPredictionService { doc /* @S103 */ }
        flow f12 of CurrentOperatingScheduleItem from airlineInterfaceAdapter to demandPredictionService { doc /* @S103 */ }
        flow f13 of RunwaySpecificCapacityValuesItem from capacityAssessmentModule to northRunwayMeter { doc /* @S114 */ }
        flow f14 of RunwaySpecificCapacityValuesItem from capacityAssessmentModule to southRunwayMeter { doc /* @S114 */ }
        flow f15 of FlightIntentMessageItem from airlineOperationsCentre to airlineInterfaceAdapter { doc /* @S126 */ }
        flow f16 of AcceptedIntentDataItem from airlineInterfaceAdapter to flightDataExchange { doc /* @S128 */ }
        flow f17 of StormCellSnapshotItem from meteorologyBriefingOfficer to capacityAssessmentModule { doc /* @S133 */ }
        flow f18 of CalculatedTakeoffTimeValuesAndTargetOffBlockTimeGuidanceItem from slotAllocationEngine to airlineOperationsCentre { doc /* @S135 */ }
        flow f19 of RevisedConstraintSetItem from slotAllocationEngine to nullPart { doc /* @S137 */ }
        flow f20 of CrewBusDelaySlipItem from groundHandlingDispatcher to nullPart { doc /* @S140 */ }
        flow f21 of CommonSituationDisplayItem from primaryWorkspace to nullPart { doc /* @S153 */ }
        flow f22 of ExpectedLandingDemandStandAllocationRiskInboundRegulationEffectsAndHandlingReadinessIndicatorsItem from arrivalWorkspace to nullPart { doc /* @S155 */ }
        flow f23 of CurrentRegionalDemandAndConstraintContextItem from regionalFlowPlatform to sharedWorkspace { doc /* @S164 */ }
        flow f24 of PositionUpdatesItem from eastApronSensor to surfaceSurveillanceAdapter { doc /* @S179 */ }
        flow f25 of PositionUpdatesItem from westApronSensor to surfaceSurveillanceAdapter { doc /* @S179 */ }
        flow f26 of MovementIndicationsItem from surfaceSurveillanceAdapter to airportCDMPortal { doc /* @S179 */ }
        flow f27 of RunwayInspectionNoteItem from towerSupervisor to airportDutyManager { doc /* @S181 */ }
        flow f28 of TimeStampedWeatherConditionUpdatesItem from weatherIngestGateway to nullPart { doc /* @S182 */ }
        flow f29 of ApprovedDutyCoordinationAlertsItem from alertDistributionHub to nullPart { doc /* @S193 */ }
        flow f30 of StandTowRequestFormItem from rampControlLead to nullPart { doc /* @S208 */ }
        flow f31 of RampIntentItem from rampMovementBoard to towerSequenceManager { doc /* @S217 */ }
        flow f32 of DemandItem from demandPredictionService to slotAllocationEngine { doc /* @S225 */ }
        flow f33 of ConstraintsItem from capacityAssessmentModule to slotAllocationEngine { doc /* @S225 */ }
        flow f34 of CrewBusDelaySlipItem from groundHandlingDispatcher to airlineOperationsCoordinator { doc /* @S237 */ }
        flow f35 of ProposedArrivalOpportunitiesItem from arrivalRegulationConsole to nullPart { doc /* @S241 */ }
        flow f36 of ProposedDepartureOpportunitiesAndAssociatedCalculatedTakeoffTimeValuesItem from departureMeteringService to towerSequenceManager { doc /* @S242 */ }
        flow f37 of CurrentAgreedTargetSetItem from commonSituationDisplay to nullPart { doc /* @S265 */ }
        flow f38 of TowerReadinessChangesItem from airportCDMPortal to authenticatedAirlineAndHandlingUsers { doc /* @S293 */ }
        flow f39 of DeicingPadQueueCardItem from deicingCoordinator to nullPart { doc /* @S294 */ }
        flow f40 of StandTowRequestFormItem from rampControlLead to handlingResourcePlanner { doc /* @S304 */ }
        flow f41 of OccupiedStandsBlockedServiceRoadsAndPendingPushbackAreasItem from rampMovementBoard to nullPart { doc /* @S311 */ }
        flow f42 of ResourceDrivenFeasibilityStatusItem from airportCDMPortal to airlineOperationsCoordinator { doc /* @S312 */ }
        flow f43 of ResourceDrivenFeasibilityStatusItem from airportCDMPortal to aircraftOperatorRepresentative { doc /* @S312 */ }
        flow f44 of TemporaryRestrictionNoticeItem from militaryAirspaceLiaison to nullPart { doc /* @S325 */ }
        flow f45 of ActiveRestrictionStatusExpectedOperationalEffectAndAnyRelatedCoordinationNotesItem from airportCDMPortal to commonSituationDisplay { doc /* @S337 */ }
        flow f46 of AffectedRunwayQueueItem from alertDistributionHub to commonSituationDisplay { doc /* @S366 */ }
        flow f47 of AircraftTreatmentStatusItem from rampMovementBoard to nullPart { doc /* @S377 */ }
        flow f48 of DeicingPadQueueCardItem from deicingCoordinator to rampControlLead { doc /* @S378 */ }
        flow f49 of TemporaryRestrictionNoticeItem from militaryAirspaceLiaison to regionalFlowManager { doc /* @S399 */ }
        flow f50 of OperationalBasisForEachValueItem from capacityAssessmentModule to commonSituationDisplay { doc /* @S400 */ }
        flow f51 of ArrivalPlanItem from airportCDMPortal to aircraftOperatorRepresentative { doc /* @S405 */ }
        flow f52 of AlertsItem from arrivalRegulationConsole to nullPart { doc /* @S407 */ }
        flow f53 of CombinedTacticalViewItem from integratedTacticalManagementPosition to regionalFlowManager { doc /* @S420 */ }
        flow f54 of RevisedDepartureMeteringAdvisoriesItem from departureMeteringService to nullPart { doc /* @S426 */ }
        flow f55 of AgreedTargetOffBlockTimeValuesAndStakeholderRemarksItem from airportCDMPortal to integratedTacticalManagementPosition { doc /* @S429 */ }
        flow f56 of CurrentMovementAreaOccupancyAndEquipmentStatusIndicatorsItem from surfaceSurveillanceAdapter to rampMovementBoard { doc /* @S445 */ }
        flow f57 of CurrentMovementAreaOccupancyAndEquipmentStatusIndicatorsItem from surfaceSurveillanceAdapter to towerSequenceManager { doc /* @S445 */ }
        flow f58 of FuelTruckHoldAdviceItem from rampMovementBoard to towerSequenceManager { doc /* @S450 */ }
        flow f59 of CandidatePushbackSpacingItem from departureMeteringService to slotAllocationEngine { doc /* @S456 */ }
        flow f60 of SurfaceEquipmentAndApronCongestionAdvisoriesItem from alertDistributionHub to nullPart { doc /* @S461 */ }
        flow f61 of GateReopeningMemoItem from gateConflictDetector to airlineOperationsCoordinator { doc /* @S472 */ }
        flow f62 of MedicalDiversionNoticeItem from airportDutyManager to nullPart { doc /* @S496 */ }
        flow f63 of PushbackWindowTokenItem from slotAllocationEngine to airportCDMPortal { doc /* @S503 */ }
        flow f64 of LateBaggageTagListItem from airlineInterfaceAdapter to groundHandlingDispatcher { doc /* @S519 */ }
        flow f65 of TowbarShortageReportItem from groundHandlingDispatcher to nullPart { doc /* @S523 */ }
        flow f66 of StandLevelExceptionItem from rampMovementBoard to nullPart { doc /* @S525 */ }
        flow f67 of RemoteStandOccupancyExpectedTowingActionsAndBusServiceReadinessItem from rampMovementBoard to nullPart { doc /* @S551 */ }
        flow f68 of TowbarShortageReportItem from groundHandlingDispatcher to rampControlLead { doc /* @S556 */ }
        flow f69 of MedicalDiversionNoticeItem from airportDutyManager to arrivalRegulationConsole { doc /* @S576 */ }
        flow f70 of StandOccupancyTransitionsPushbackLaneBlockageDurationsAndSensorConfidenceValuesItem from eastApronSensor to nullPart { doc /* @S578 */ }
        flow f71 of DepartureFixLoadSheetItem from sectorLoadMonitor to regionalFlowManager { doc /* @S598 */ }
        flow f72 of ConvertedMeasuresItem from nullPart to commonSituationDisplay { doc /* @S613 */ }
        flow f73 of NotificationsItem from alertDistributionHub to regionalFlowManager { doc /* @S614 */ }
        flow f74 of NotificationsItem from alertDistributionHub to towerSupervisor { doc /* @S614 */ }
        flow f75 of NotificationsItem from alertDistributionHub to rampControlLead { doc /* @S614 */ }
        flow f76 of NotificationsItem from alertDistributionHub to slotCoordinator { doc /* @S614 */ }
        flow f77 of NotificationsItem from alertDistributionHub to networkOperationsLiaison { doc /* @S614 */ }
        flow f78 of CrewDutyExtensionLogItem from aircraftOperatorRepresentative to nullPart { doc /* @S620 */ }
        flow f79 of CrewLegalityImpactsItem from commonSituationDisplay to nullPart { doc /* @S627 */ }
        flow f80 of ApronSweepCompletionNoteItem from rampControlLead to nullPart { doc /* @S647 */ }
        flow f81 of RemoteStandShuttleCountItem from handlingResourcePlanner to airportCDMPortal { doc /* @S648 */ }
        flow f82 of SlotSwapPermissionEmailItem from slotCoordinator to nullPart { doc /* @S672 */ }
        flow f83 of ApronSweepCompletionNoteItem from rampControlLead to airportDutyManager { doc /* @S678 */ }
        flow f84 of CustomsHoldReleaseNoteItem from airportDutyManager to airlineOperationsCoordinator { doc /* @S679 */ }
        flow f85 of RevisedFlightIntentMessageContentItem from flightDataExchange to nullPart { doc /* @S684 */ }
        flow f86 of RunwayLightingOutageCardItem from surfaceSurveillanceAdapter to towerSupervisor { doc /* @S693 */ }
        flow f87 of CrewDutyExtensionLogItem from aircraftOperatorRepresentative to slotCoordinator { doc /* @S726 */ }
        flow f88 of PassengerMisconnectCountItem from airlineOperationsCoordinator to nullPart { doc /* @S740 */ }
        flow f89 of SlotSwapPermissionEmailItem from slotCoordinator to airlineOperationsCoordinator { doc /* @S795 */ }
        flow f90 of FreshnessIndicatorItem from nullPart to commonSituationDisplay { doc /* @S822 */ }
        flow f91 of PassengerMisconnectCountItem from airlineOperationsCoordinator to departureMeteringService { doc /* @S851 */ }
        flow f92 of RegionalBenefitsAlongsideOperationalTradeOffsItem from postOperationsReport to nullPart { doc /* @S862 */ }
        flow f93 of RicherIntentDataItem from flightDataExchange to demandPredictionService { doc /* @S941 */ }
    }
    requirement def R0 { doc /* During Adverse Weather Mode or Capacity Reduction State, the system must support rapid development of a Tactical Regulation Proposal and consistent communication of the resulting Ground Delay Program when one is required. @S022 */ subject s : System; }
    requirement def R1 { doc /* During Recovery Phase, the system must help stakeholders restore scheduled flow while monitoring Target Off Block Time, Calculated Takeoff Time, and Slot Compliance State performance. @S023 */ subject s : System; }
    requirement def R2 { doc /* Participation in the regional system requires each stakeholder organization to assign accountable representatives, maintain current contact details, follow agreed data use rules, and support post-operational review of decisions made through the Regional Flow Platform. @S048 */ subject s : StakeholderOrganization; }
    requirement def R3 { doc /* changes must be entered through controlled Regional Flow Platform functions @S073 */ subject s : Null; }
    requirement def R4 { doc /* outputs must remain visible on the Common Situation Display @S095 */ subject s : DepartureMeteringService; }
    requirement def R5 { doc /* outputs must remain visible on the Common Situation Display @S095 */ subject s : ArrivalRegulationConsole; }
    requirement def R6 { doc /* Escalation to the Emergency Response Coordinator is required when a safety event, security event, or emergency response activity may affect airport acceptance, surface movement, or airspace availability. @S096 */ subject s : EmergencyResponseCoordinator; }
    requirement def R7 { doc /* Cedarbell shall expose the current regional demand and constraint context to the shared workspace at each publication cycle without requiring manual re-entry. @S164 */ subject s : RegionalFlowPlatform; }
    requirement def R8 { doc /* When a milestone becomes stale, the Airport CDM Portal shall highlight the affected flight and notify the role accountable for the next update through the Alert Distribution Hub. @S166 */ subject s : AirportCDMPortal; }
    requirement def R9 { doc /* Each airport participant shall update a material change within two minutes of becoming aware of it during Normal Operations and within one minute during Adverse Weather Mode or Capacity Reduction State. @S167 */ subject s : AirportParticipant; }
    requirement def R10 { doc /* If the exact value is not yet known, the accountable participant shall enter a provisional value with an uncertainty flag rather than leaving the milestone unchanged. @S168 */ subject s : AccountableParticipant; }
    requirement def R11 { doc /* During Contingency Fallback State, the Airport CDM Portal shall preserve the last synchronized milestone set and clearly mark any updates entered under degraded operating procedures. @S172 */ subject s : AirportCDMPortal; }
    requirement def R12 { doc /* Orchard shall issue time-stamped weather condition updates for use in tower and airport duty coordination. @S182 */ subject s : WeatherIngestGateway; }
    requirement def R13 { doc /* The Time Synchronization Service shall keep tower, duty desk, surveillance, and portal event times aligned so that later review can reconstruct the sequence of events. @S187 */ subject s : TimeSynchronizationService; }
    requirement def R14 { doc /* The Ramp Control Lead shall not release a pushback until the Tower Supervisor has confirmed that the movement can be integrated with the active ground route and runway plan. @S202 */ subject s : RampControlLead; }
    requirement def R15 { doc /* Airline Operations Coordinator participation is required when a resequence would materially affect passenger boarding, connection protection, or aircraft rotation plans. @S214 */ subject s : AirlineOperationsCoordinator; }
    requirement def R16 { doc /* Marlinstone shall refresh stand demand forecasts when the Ramp Movement Board records a material change in planned off-block timing. @S216 */ subject s : DemandPredictionService; }
    requirement def R17 { doc /* The engine shall not improve one operator's position by imposing an excessive delay on another operator unless the rule basis is visible and logged. @S234 */ subject s : SlotAllocationEngine; }
    requirement def R18 { doc /* Saffron shall confirm any operator-requested Target Off Block Time revision in the Airport CDM Portal before the freeze horizon expires. @S260 */ subject s : AirlineOperationsCoordinator; }
    requirement def R19 { doc /* Foxglove shall publish tower readiness changes to authenticated airline and handling users within the configured refresh interval. @S293 */ subject s : AirportCDMPortal; }
    requirement def R20 { doc /* Brindle must confirm that any revised off-block sequence remains compatible with the Departure Metering Service before the change is released to the airport community. @S313 */ subject s : TowerSupervisor; }
    requirement def R21 { doc /* Ironleaf must refresh affected departure sequence advisories when a restriction changes the usable departure routes or expected release spacing. @S334 */ subject s : TowerSequenceManager; }
    requirement def R22 { doc /* Blueharbor shall adjust allocated departure times when metering rules require additional stand absorption to preserve the planned runway sequence. @S355 */ subject s : SlotAllocationEngine; }
    requirement def R23 { doc /* Quartzline must coordinate every pad release with the Tower Supervisor before the aircraft leaves the treated area. @S387 */ subject s : RampControlLead; }
    requirement def R24 { doc /* Skylark must refresh the apron movement layer within five seconds of each validated surface event. @S427 */ subject s : RampMovementBoard; }
    requirement def R25 { doc /* Lantern must distribute surface equipment and apron congestion advisories to subscribed operational roles within the latency target defined in the Business Rules Registry. @S461 */ subject s : AlertDistributionHub; }
    requirement def R26 { doc /* Nightjar shall suppress handler-exception annotations for arriving flights unless the exception changes the Airport Acceptance Rate or a regulated arrival sequence. @S535 */ subject s : ArrivalRegulationConsole; }
    requirement def R27 { doc /* The Time Synchronization Service is required because customs status events and apron sensor events must align with Calculated Takeoff Time and Target Off Block Time decisions. @S585 */ subject s : TimeSynchronizationService; }
    requirement def R28 { doc /* During manual operation, the Tower Sequence Manager and Ramp Movement Board are treated as advisory displays unless their data quality has been confirmed by the System Support Engineer. The Departure Metering Service may remain in monitoring mode while manual slot control is active, but it must not automatically overwrite issued times. @S728 */ subject s : DepartureMeteringService; }
    requirement def R29 { doc /* Each named operational user shall authenticate with an individually assigned identity before accessing the Airport CDM Portal, Digital Briefing Room, or any operational console. @S764 */ subject s : NamedOperationalUser; }
    requirement def R30 { doc /* Role profiles shall grant the minimum access needed to view, propose, approve, or administer operational data within the Regional Flow Platform. @S767 */ subject s : RoleProfiles; }
    requirement def R31 { doc /* operational approval privileges shall remain separated from technical administration privileges @S772 */ subject s : Null; }
    requirement def R32 { doc /* Operational segregation shall prevent a single user from creating, approving, and technically concealing a material change to a Ground Delay Program, Airport Acceptance Rate, or Tactical Regulation Proposal. @S774 */ subject s : OperationalSegregation; }
    requirement def R33 { doc /* Where dual control is required, the Regional Flow Platform shall record the initiating user, the approving user, the affected operational object, and the effective time of the decision. @S775 */ subject s : RegionalFlowPlatform; }
    requirement def R34 { doc /* Access to the Performance Analytics Warehouse shall be restricted to authorized analytical roles and shall not allow retrospective alteration of operational records held in the Audit Event Ledger. @S776 */ subject s : PerformanceAnalyticsWarehouse; }
    requirement def R35 { doc /* The Audit Event Ledger shall capture successful and failed authentication attempts, role changes, privilege elevations, operational approvals, configuration changes, data exports, and emergency access activations. @S777 */ subject s : AuditEventLedger; }
    requirement def R36 { doc /* All audit records shall use time derived from the Time Synchronization Service so that investigations can reconstruct event order across the Airport CDM Portal, Slot Allocation Engine, and Alert Distribution Hub. @S778 */ subject s : AuditRecords; }
    requirement def R37 { doc /* Audit records shall be protected against ordinary user modification and retained for a period agreed by the airport operator, regional authority, and participating aircraft operators. @S779 */ subject s : AuditRecords; }
    requirement def R38 { doc /* Security monitoring shall alert the System Support Engineer and Data Governance Steward when unusual access patterns indicate possible credential compromise or inappropriate privilege use. @S780 */ subject s : Null; }
    requirement def R39 { doc /* The Identity Access Service shall support rapid suspension of accounts when a user changes role, leaves an organization, or becomes subject to an operational integrity concern. @S781 */ subject s : IdentityAccessService; }
    requirement def R40 { doc /* Temporary access shall have a defined sponsor, purpose, role scope, and expiry time, and shall be reviewed after the operational need has ended. @S782 */ subject s : TemporaryAccess; }
    requirement def R41 { doc /* Silverpine shall accept emergency access activations only after the Identity Access Service records the authorizing incident reference and expiry time. @S783 */ subject s : ContingencyOperationsConsole; }
    requirement def R42 { doc /* Use of emergency access shall generate prominent audit events and shall require post-event review by the Data Governance Steward and the responsible operational authority. @S785 */ subject s : EmergencyAccess; }
    requirement def R43 { doc /* During Contingency Fallback State, access control shall continue to enforce role separation even when some integrations are unavailable and manual coordination becomes necessary. @S786 */ subject s : Null; }
    requirement def R44 { doc /* When normal connectivity is restored, the Regional Flow Platform shall reconcile contingency actions with the Collaborative Decision Log so that accountability is preserved across the full incident timeline. @S787 */ subject s : RegionalFlowPlatform; }
    requirement def R45 { doc /* After connectivity is restored, audit processing shall treat reconciled contingency actions as part of the same operational record as actions taken during Normal Operations. @S788 */ subject s : Null; }
    requirement def R46 { doc /* The Regional Flow Platform shall record slot compliance events in the Audit Event Ledger using the operating date, flight identifier, airport, runway direction, and applicable regulation reference. @S789 */ subject s : RegionalFlowPlatform; }
    requirement def R47 { doc /* Each compliance assessment shall compare the Calculated Takeoff Time, the Target Off Block Time, actual off-block time, and actual takeoff time against the tolerance defined in the Business Rules Registry. @S790 */ subject s : ComplianceAssessment; }
    requirement def R48 { doc /* The Slot Compliance State shall indicate whether a flight was compliant, early, late, exempted, substituted, cancelled, or pending review at the end of the traffic period. @S791 */ subject s : SlotComplianceState; }
    requirement def R49 { doc /* The Audit Event Ledger shall preserve the time source applied by the Time Synchronization Service so that later review can distinguish operational delay from data latency. @S792 */ subject s : AuditEventLedger; }
    requirement def R50 { doc /* User decisions entered through the Airport CDM Portal shall be linked to the authenticated role provided by the Identity Access Service. @S793 */ subject s : Null; }
    requirement def R51 { doc /* The Collaborative Decision Log shall retain the stated reason, decision time, affected flight, and visible operational context for each material change to a slot or sequence. @S794 */ subject s : CollaborativeDecisionLog; }
    requirement def R52 { doc /* Substitution records shall show the original flight, replacement flight, assigned Calculated Takeoff Time, acceptance status, and any subsequent cancellation or reversion. @S796 */ subject s : SubstitutionRecords; }
    requirement def R53 { doc /* When an Aircraft Operator Representative proposes a substitution, the audit trail shall capture whether the change preserved the constraints of the active Ground Delay Program. @S797 */ subject s : Null; }
    requirement def R54 { doc /* The Slot Coordinator shall review substitution activity after operations to confirm that priority rules were applied consistently across participating operators. @S798 */ subject s : SlotCoordinator; }
    requirement def R55 { doc /* Late operational changes shall be distinguished from planned updates by comparing the change timestamp with the freeze horizon held in the Business Rules Registry. @S799 */ subject s : Null; }
    requirement def R56 { doc /* Changes made inside the freeze horizon shall require a reason code and shall be visible to the Regional Flow Manager during post-operations review. @S800 */ subject s : Null; }
    requirement def R57 { doc /* The Tower Sequence Manager and Ramp Movement Board shall provide actual movement milestones that support independent verification of slot performance. @S801 */ subject s : TowerSequenceManager; }
    requirement def R58 { doc /* Surface movement evidence from the Surface Surveillance Adapter shall be retained long enough to support dispute resolution and regulatory audit requests. @S802 */ subject s : SurfaceSurveillanceAdapter; }
    requirement def R59 { doc /* Capacity changes made through the Capacity Assessment Module shall be correlated with the active Airport Capacity Plan and Airport Acceptance Rate used at the time of allocation. @S803 */ subject s : CapacityAssessmentModule; }
    requirement def R60 { doc /* The Performance Analytics Warehouse shall aggregate compliance outcomes by carrier, route group, regulation, airport operating configuration, and time band. @S804 */ subject s : PerformanceAnalyticsWarehouse; }
    requirement def R61 { doc /* Aggregated metrics shall support review of systemic lateness without exposing commercially sensitive detail beyond authorized roles. @S805 */ subject s : Null; }
    requirement def R62 { doc /* The Data Governance Steward shall verify that audit fields required for slot performance reporting remain complete, immutable, and traceable to approved data definitions. @S806 */ subject s : DataGovernanceSteward; }
    requirement def R63 { doc /* The System Support Engineer shall investigate technical gaps when audit sequences show missing events, duplicate updates, or inconsistent timestamps. @S807 */ subject s : SystemSupportEngineer; }
    requirement def R64 { doc /* The Regional Flow Manager shall use the Post Operations Report to identify whether noncompliance resulted from operator choice, airport constraint, airspace constraint, weather impact, or system issue. @S808 */ subject s : RegionalFlowManager; }
    requirement def R65 { doc /* The Airport Duty Manager shall review late airport-driven changes that affected multiple flights and shall record whether the operational justification was valid. @S809 */ subject s : AirportDutyManager; }
    requirement def R66 { doc /* Findings from the review shall feed adjustments to tolerance values, reason code definitions, and training material, subject to change control. @S810 */ subject s : Null; }
    requirement def R67 { doc /* All audit outputs shall be retained according to the approved records schedule and shall remain searchable for compliance investigations, performance meetings, and lessons-learned activity. @S811 */ subject s : Null; }
    requirement def R68 { doc /* Data governance for the Regional Flow Platform shall assign accountable owners to each operational data domain and shall make those assignments visible in the Airport CDM Portal. @S812 */ subject s : RegionalFlowPlatform; }
    requirement def R69 { doc /* The Data Governance Steward shall maintain the data ownership register and shall coordinate updates through the Business Rules Registry. @S813 */ subject s : DataGovernanceSteward; }
    requirement def R70 { doc /* The Regional Flow Manager shall own flow management policy data, including Ground Delay Program parameters and Tactical Regulation Proposal status values. @S814 */ subject s : RegionalFlowManager; }
    requirement def R71 { doc /* The Slot Coordinator shall own slot allocation reference data, including Calculated Takeoff Time tolerances and Slot Compliance State definitions. @S815 */ subject s : SlotCoordinator; }
    requirement def R72 { doc /* The Airport Duty Manager shall own airport capacity declarations, including Airport Capacity Plan records and Airport Acceptance Rate values. @S816 */ subject s : AirportDutyManager; }
    requirement def R73 { doc /* The Tower Supervisor shall own tower sequence status data maintained for the Tower Sequence Manager. @S817 */ subject s : TowerSupervisor; }
    requirement def R74 { doc /* The Ramp Control Lead shall own ramp movement status data maintained for the Ramp Movement Board. @S818 */ subject s : RampControlLead; }
    requirement def R75 { doc /* The Meteorology Briefing Officer shall own operational weather classification inputs accepted by the Weather Ingest Gateway. @S819 */ subject s : MeteorologyBriefingOfficer; }
    requirement def R76 { doc /* The Airline Operations Coordinator shall be accountable for airline-supplied schedule intent, readiness status, and Target Off Block Time updates submitted through approved interfaces. @S820 */ subject s : AirlineOperationsCoordinator; }
    requirement def R77 { doc /* Each owned data element shall have a defined business meaning, allowed value range, update authority, retention class, and escalation contact. @S821 */ subject s : Null; }
    requirement def R78 { doc /* Freshness indicators shall be displayed on the Common Situation Display wherever stale data could affect sequencing, metering, regulation, or resource allocation decisions. @S822 */ subject s : FreshnessIndicator; }
    requirement def R79 { doc /* The freshness indicator shall include the time of last accepted update, the maximum permitted age, and a visual state that distinguishes current, aging, stale, and unavailable data. @S823 */ subject s : FreshnessIndicator; }
    requirement def R80 { doc /* The Time Synchronization Service shall provide the common time basis used for freshness calculations across the Regional Flow Platform. @S824 */ subject s : TimeSynchronizationService; }
    requirement def R81 { doc /* The Demand Prediction Service, Capacity Assessment Module, Slot Allocation Engine, and Departure Metering Service shall reject data that lacks a trusted timestamp. @S825 */ subject s : Null; }
    requirement def R82 { doc /* Validation rules shall include schema checks, mandatory field checks, code set checks, temporal sequence checks, and operational plausibility checks. @S826 */ subject s : Null; }
    requirement def R83 { doc /* The Flight Data Exchange shall validate Flight Intent Message content before the data is made available for operational use. @S827 */ subject s : FlightDataExchange; }
    requirement def R84 { doc /* The Surface Surveillance Adapter shall apply position quality checks and shall mark uncertain observations before they are used by surface decision functions. @S828 */ subject s : SurfaceSurveillanceAdapter; }
    requirement def R85 { doc /* The Airline Interface Adapter shall apply carrier-specific format checks while preserving the common operational meaning required by the Regional Flow Platform. @S829 */ subject s : AirlineInterfaceAdapter; }
    requirement def R86 { doc /* The Handling Resource Planner shall validate resource quantities, task timing, and allocation identifiers against active operational reference data. @S830 */ subject s : HandlingResourcePlanner; }
    requirement def R87 { doc /* The Business Rules Registry shall hold the current validation thresholds, allowable reason codes, and exception rules approved for Normal Operations, Adverse Weather Mode, Capacity Reduction State, Recovery Phase, and Contingency Fallback State. @S831 */ subject s : BusinessRulesRegistry; }
    requirement def R88 { doc /* When a discrepancy is detected, the affected component shall mark the data as disputed and shall preserve the prior accepted value until an authorized correction is available. @S832 */ subject s : Null; }
    requirement def R89 { doc /* The Data Governance Steward shall coordinate discrepancy resolution with the responsible operational owner and shall record the disposition in the Audit Event Ledger. @S833 */ subject s : DataGovernanceSteward; }
    requirement def R90 { doc /* Urgent discrepancies that could change a metering, arrival regulation, or slot allocation decision shall be raised through the Alert Distribution Hub and reviewed in the Digital Briefing Room. @S834 */ subject s : Null; }
    requirement def R91 { doc /* The System Support Engineer shall investigate technical causes of missing, delayed, duplicated, or transformed records and shall provide evidence needed for stewardship decisions. @S835 */ subject s : SystemSupportEngineer; }
    requirement def R92 { doc /* The Performance Analytics Warehouse shall retain data quality measures, including validation failure rates, freshness breaches, manual corrections, and recurring ownership conflicts. @S836 */ subject s : PerformanceAnalyticsWarehouse; }
    requirement def R93 { doc /* Stewardship reviews shall use those measures to update training, adjust validation rules, and improve the reliability of information used in operational decision making. @S837 */ subject s : Null; }
    requirement def R94 { doc /* Performance measurement for the Meridian Regional Air Traffic Flow Management and Airport Collaborative Decision-Making System shall convert operational events into repeatable indicators that can be reviewed after each operating day. @S838 */ subject s : MeridianRegionalAirTrafficFlowManagementAndAirportCollaborativeDecisionMakingSystem; }
    requirement def R95 { doc /* The Performance Analytics Warehouse shall calculate delay absorption as the portion of expected airborne or terminal-area delay that is converted into controlled ground delay before departure. @S839 */ subject s : PerformanceAnalyticsWarehouse; }
    requirement def R96 { doc /* Delay absorption shall be measured by comparing the unconstrained demand predicted by the Demand Prediction Service with the regulated demand produced by the Slot Allocation Engine and the realized movement times captured through the Flight Data Exchange. @S840 */ subject s : Null; }
    requirement def R97 { doc /* The principal delay absorption indicator shall report minutes absorbed at origin, minutes remaining in the arrival stream, and minutes transferred to surface queues within the region. @S841 */ subject s : Null; }
    requirement def R98 { doc /* The Regional Flow Manager shall use this indicator to verify that a Ground Delay Program reduced airborne holding without creating excessive departure congestion at constrained airports. @S842 */ subject s : RegionalFlowManager; }
    requirement def R99 { doc /* Queue length performance shall be measured for runway departure queues, arrival metering queues, apron movement queues, and regulation waiting lists. @S843 */ subject s : Null; }
    requirement def R100 { doc /* The Tower Sequence Manager shall provide runway sequence counts, while the Ramp Movement Board shall provide surface queue counts based on movement status and surveillance confirmation. @S844 */ subject s : Null; }
    requirement def R101 { doc /* The North Runway Meter, South Runway Meter, East Apron Sensor, and West Apron Sensor shall support independent checks of queue length where surveillance coverage is available. @S845 */ subject s : Null; }
    requirement def R102 { doc /* Queue metrics shall include maximum queue length, average queue length, time above threshold, and recovery time after a constraint is lifted. @S846 */ subject s : Null; }
    requirement def R103 { doc /* Slot adherence shall be measured as the difference between actual movement times and the assigned Calculated Takeoff Time or Target Off Block Time. @S847 */ subject s : Null; }
    requirement def R104 { doc /* The Slot Coordinator shall review slot adherence by operator, airport, time band, and regulation identifier to detect recurring causes of noncompliance. @S848 */ subject s : SlotCoordinator; }
    requirement def R105 { doc /* A flight shall be counted within tolerance when the actual takeoff or off-block event occurs inside the operating window defined in the Business Rules Registry. @S849 */ subject s : Null; }
    requirement def R106 { doc /* The Slot Compliance State shall be used to identify periods when adherence monitoring has operational priority over advisory optimization. @S850 */ subject s : SlotComplianceState; }
    requirement def R107 { doc /* Cancellation avoidance shall be estimated by comparing actual cancellations with a baseline scenario derived from demand, capacity, weather, and historical disruption outcomes. @S852 */ subject s : Null; }
    requirement def R108 { doc /* The Capacity Assessment Module shall record the available Airport Acceptance Rate used in each baseline so that avoided cancellation estimates remain traceable. @S853 */ subject s : CapacityAssessmentModule; }
    requirement def R109 { doc /* The Airline Operations Coordinator and Aircraft Operator Representative shall be able to challenge cancellation avoidance results through the Collaborative Decision Log when local business decisions affected the outcome. @S854 */ subject s : Null; }
    requirement def R110 { doc /* Emissions reduction shall be estimated from reduced airborne holding, reduced taxi-out time, avoided engine running in queues, and smoother departure metering. @S855 */ subject s : Null; }
    requirement def R111 { doc /* The Performance Analytics Warehouse shall apply approved fuel burn and emissions factors by aircraft category, operating phase, and delay location. @S856 */ subject s : PerformanceAnalyticsWarehouse; }
    requirement def R112 { doc /* Emissions metrics shall distinguish between actual reductions and delay transfers that only move fuel burn from one phase of flight to another. @S857 */ subject s : Null; }
    requirement def R113 { doc /* The Meteorology Briefing Officer shall support interpretation of emissions results by identifying periods when weather routing or convective avoidance dominated fuel performance. @S858 */ subject s : MeteorologyBriefingOfficer; }
    requirement def R114 { doc /* Stakeholder benefit tracking shall allocate measured outcomes to aircraft operators, airport operations, air navigation service functions, ground handling activities, and passengers where the source data supports that attribution. @S859 */ subject s : Null; }
    requirement def R115 { doc /* The Airport Duty Manager shall receive benefit summaries that show changes in stand occupancy, surface congestion, recovery duration, and passenger-facing disruption indicators. @S860 */ subject s : AirportDutyManager; }
    requirement def R116 { doc /* The Data Governance Steward shall ensure that published performance measures identify data sources, calculation versions, confidence limits, and known exclusions. @S861 */ subject s : DataGovernanceSteward; }
    requirement def R117 { doc /* The Post Operations Report shall present regional benefits alongside operational trade-offs so that decision makers can see whether delay, queue, slot, cancellation, and emissions objectives were balanced in practice. @S862 */ subject s : PostOperationsReport; }
    requirement def R118 { doc /* Training for the Meridian Regional Air Traffic Flow Management and Airport Collaborative Decision-Making System shall be role based and shall cover normal coordination, constrained operations, recovery actions, and degraded system use. @S863 */ subject s : MeridianRegionalAirTrafficFlowManagementAndAirportCollaborativeDecisionMakingSystem; }
    requirement def R119 { doc /* The Regional Flow Manager shall receive advanced instruction on interpreting demand and capacity information, leading collaborative decisions, and authorizing operational measures in the Regional Flow Platform. @S864 */ subject s : RegionalFlowManager; }
    requirement def R120 { doc /* Air traffic controllers shall be trained to understand how flow measures, sequencing changes, and calculated times affect sector workload, runway demand, and controller tactical flexibility. @S865 */ subject s : AirTrafficControllers; }
    requirement def R121 { doc /* The Tower Supervisor shall receive practical training on the Tower Sequence Manager, Departure Metering Service, Arrival Regulation Console, North Runway Meter, and South Runway Meter. @S866 */ subject s : TowerSupervisor; }
    requirement def R122 { doc /* Ramp personnel shall be trained under the direction of the Ramp Control Lead to use the Ramp Movement Board without substituting system indications for required visual checks, radio coordination, and local safety procedures. @S867 */ subject s : RampPersonnel; }
    requirement def R123 { doc /* The Airline Operations Coordinator and Aircraft Operator Representative shall be trained to submit, review, and update Flight Intent Message data through approved interfaces and to assess the operational effect of Calculated Takeoff Time and Target Off Block Time changes. @S868 */ subject s : Null; }
    requirement def R124 { doc /* Ground handling personnel shall be trained by the Ground Handling Dispatcher on the Handling Resource Planner and on procedures for confirming that resource constraints are represented accurately before they influence collaborative decisions. @S869 */ subject s : GroundHandlingPersonnel; }
    requirement def R125 { doc /* The Slot Coordinator shall receive training on the Slot Allocation Engine, Airport CDM Portal, and applicable Business Rules Registry entries so that slot actions are applied consistently and transparently. @S870 */ subject s : SlotCoordinator; }
    requirement def R126 { doc /* The Network Operations Liaison and Airspace Sector Planner shall be trained to coordinate regional constraints, sector load conditions, and network measures using the Sector Load Monitor and Common Situation Display. @S871 */ subject s : Null; }
    requirement def R127 { doc /* The Airport Duty Manager shall be trained to recognize when an Airport Capacity Plan requires revision and when the operational state should move from Normal Operations to Adverse Weather Mode or Capacity Reduction State. @S872 */ subject s : AirportDutyManager; }
    requirement def R128 { doc /* The Meteorology Briefing Officer shall be trained to explain weather uncertainty in operational terms and to verify that the Weather Ingest Gateway supports the assumptions used during briefings. @S873 */ subject s : MeteorologyBriefingOfficer; }
    requirement def R129 { doc /* The Emergency Response Coordinator shall participate in recurrent training so that emergency priorities are integrated into flow management decisions without obscuring command authority or safety responsibilities. @S874 */ subject s : EmergencyResponseCoordinator; }
    requirement def R130 { doc /* The Deicing Coordinator shall receive seasonal refresher training on how deicing capacity assumptions are represented in demand and departure metering tools. @S875 */ subject s : DeicingCoordinator; }
    requirement def R131 { doc /* The Data Governance Steward shall train operational users on data quality responsibilities, privacy expectations, and the correct interpretation of audit records in the Audit Event Ledger. @S876 */ subject s : DataGovernanceSteward; }
    requirement def R132 { doc /* The System Support Engineer shall train superusers on service status checks, access fault escalation, and safe use of the Contingency Operations Console during partial outages. @S877 */ subject s : SystemSupportEngineer; }
    requirement def R133 { doc /* Initial training shall include classroom instruction, supervised workstation practice, scenario walkthroughs in the Digital Briefing Room, and observed operational shadowing before independent system use is authorized. @S878 */ subject s : Null; }
    requirement def R134 { doc /* Recurrent training shall be required at least annually and after major changes to the Regional Flow Platform, Demand Prediction Service, Capacity Assessment Module, or Flight Data Exchange. @S879 */ subject s : Null; }
    requirement def R135 { doc /* Simulation exercises shall use realistic traffic samples, weather constraints, surface congestion, airline schedule pressure, handling resource shortages, and recovery objectives to test coordinated decision making. @S880 */ subject s : Null; }
    requirement def R136 { doc /* Each exercise shall include participants from tower, ramp, airline operations, handling, airport operations, network coordination, meteorology, data governance, and system support functions when those functions are relevant to the scenario. @S881 */ subject s : Null; }
    requirement def R137 { doc /* Exercises shall cover transitions among Normal Operations, Adverse Weather Mode, Capacity Reduction State, Recovery Phase, Contingency Fallback State, and Slot Compliance State. @S882 */ subject s : Null; }
    requirement def R138 { doc /* Simulation events shall require users to compare automated recommendations with local knowledge, document significant decisions in the Collaborative Decision Log, and explain departures from system proposals. @S883 */ subject s : Null; }
    requirement def R139 { doc /* Human factors safeguards shall include workload monitoring, clear alert prioritization, consistent terminology, confirmation steps for high impact actions, and protection against silent mode changes. @S884 */ subject s : Null; }
    requirement def R140 { doc /* Workstation layouts shall support rapid comparison between the Common Situation Display, Airport CDM Portal, Tower Sequence Manager, Ramp Movement Board, and relevant advisory messages without forcing users to copy critical values manually. @S885 */ subject s : Null; }
    requirement def R141 { doc /* Training assessments shall verify that users can identify stale data, time synchronization problems, duplicate flights, conflicting constraints, and inappropriate automation reliance before such issues affect live operations. @S886 */ subject s : Null; }
    requirement def R142 { doc /* Post-exercise reviews shall use evidence from the Performance Analytics Warehouse and Audit Event Ledger to improve procedures, refine training materials, and confirm that human performance concerns are assigned to accountable owners. @S887 */ subject s : Null; }
    requirement def R143 { doc /* Deployment of the Regional Flow Platform shall proceed through phased increments that limit operational exposure while progressively adding airports, interfaces, and decision support functions. @S888 */ subject s : RegionalFlowPlatform; }
    requirement def R144 { doc /* The first increment shall establish the core operational baseline for the Regional Flow Manager, Network Operations Liaison, Data Governance Steward, and System Support Engineer in a controlled production environment. @S889 */ subject s : Null; }
    requirement def R145 { doc /* This baseline shall include the Identity Access Service, Time Synchronization Service, Audit Event Ledger, Performance Analytics Warehouse, and Business Rules Registry before any airport is permitted to exchange operational data. @S890 */ subject s : Null; }
    requirement def R146 { doc /* Pilot airport selection shall favor locations with stable operational leadership, representative traffic complexity, available surface surveillance data, and demonstrated willingness to participate in joint procedure development. @S891 */ subject s : Null; }
    requirement def R147 { doc /* The initial pilot shall include one constrained primary airport and one less constrained regional airport so that both high-demand and routine operating patterns are exercised. @S892 */ subject s : Null; }
    requirement def R148 { doc /* Each candidate airport shall provide evidence that the Airport Duty Manager, Tower Supervisor, Ramp Control Lead, Airline Operations Coordinator, Ground Handling Dispatcher, and Aircraft Operator Representative have named accountable implementation contacts. @S893 */ subject s : Null; }
    requirement def R149 { doc /* Readiness Gate 1 shall confirm that governance, security approvals, user role definitions, operating hours, and support escalation paths are documented and accepted by local stakeholders. @S894 */ subject s : ReadinessGate1; }
    requirement def R150 { doc /* Readiness Gate 2 shall confirm that the Flight Data Exchange, Airline Interface Adapter, Surface Surveillance Adapter, and Weather Ingest Gateway can be connected without disrupting existing airport operations. @S895 */ subject s : ReadinessGate2; }
    requirement def R151 { doc /* Readiness Gate 3 shall confirm that local procedures have been mapped to the Airport CDM Portal, Tower Sequence Manager, Ramp Movement Board, Departure Metering Service, and Arrival Regulation Console. @S896 */ subject s : ReadinessGate3; }
    requirement def R152 { doc /* Readiness Gate 4 shall confirm that training, shadow operations, contingency procedures, and operational acceptance criteria have been completed before live collaborative decisions are made through the Regional Flow Platform. @S897 */ subject s : ReadinessGate4; }
    requirement def R153 { doc /* Interface certification shall be performed separately from operational acceptance so that technical conformance defects do not become unresolved procedural issues. @S898 */ subject s : Null; }
    requirement def R154 { doc /* Each interface shall be tested for message structure, time stamping, identity attribution, replay handling, duplicate detection, outage recovery, and rejection behavior under degraded network conditions. @S899 */ subject s : Null; }
    requirement def R155 { doc /* The Demand Prediction Service, Capacity Assessment Module, Slot Allocation Engine, Gate Conflict Detector, Sector Load Monitor, North Runway Meter, and South Runway Meter shall be certified against agreed reference scenarios before they are used for operational recommendations. @S900 */ subject s : Null; }
    requirement def R156 { doc /* Certification results shall be recorded in the Collaborative Decision Log when they affect operational procedures and in the Audit Event Ledger when they affect access, configuration, or transaction traceability. @S901 */ subject s : Null; }
    requirement def R157 { doc /* Airport onboarding shall start with data discovery workshops that identify local tools, manual workarounds, unofficial spreadsheets, and locally maintained constraint registers. @S902 */ subject s : Null; }
    requirement def R158 { doc /* The migration plan shall classify each local tool as retired, retained for read-only reference, integrated through an approved interface, or replaced by a Regional Flow Platform function. @S903 */ subject s : Null; }
    requirement def R159 { doc /* No local tool shall be retired until the responsible operational owner verifies that its essential decisions, timing assumptions, and audit needs are supported in the target process. @S904 */ subject s : Null; }
    requirement def R160 { doc /* During shadow operations, local tools shall remain the authoritative source while the Regional Flow Platform produces parallel outputs for comparison by operational users. @S905 */ subject s : Null; }
    requirement def R161 { doc /* The cutover decision shall be based on measured agreement between local practice and Regional Flow Platform outputs, user confidence, defect closure, and demonstrated recovery from simulated failures. @S906 */ subject s : Null; }
    requirement def R162 { doc /* After cutover, local users shall enter operational decisions through the Airport CDM Portal and shall avoid reintroducing uncontrolled parallel records that undermine common situational awareness. @S907 */ subject s : Null; }
    requirement def R163 { doc /* The Contingency Operations Console shall be available at each onboarded airport before reliance on the Regional Flow Platform is declared for Normal Operations, Adverse Weather Mode, Capacity Reduction State, Recovery Phase, or Contingency Fallback State. @S908 */ subject s : ContingencyOperationsConsole; }
    requirement def R164 { doc /* Expansion beyond the pilot airports shall occur in waves that group airports by interface maturity, traffic dependency, stakeholder readiness, and available support capacity. @S909 */ subject s : Null; }
    requirement def R165 { doc /* Each onboarding wave shall include a stabilization period in which the System Support Engineer and Data Governance Steward monitor defect trends, data quality, access changes, and user adoption. @S910 */ subject s : Null; }
    requirement def R166 { doc /* Full regional deployment shall be declared only after the Regional Flow Manager confirms that operational benefits, safety constraints, cyber controls, and stakeholder obligations remain stable across multiple airports and traffic conditions. @S911 */ subject s : Null; }
    requirement def R167 { doc /* Operational service management for the Regional Flow Platform shall begin when a deployed airport is accepted into steady state support after the regional stabilization period. @S912 */ subject s : RegionalFlowPlatform; }
    requirement def R168 { doc /* The service model shall distinguish continuous operational support from planned engineering support so that safety related traffic flow functions remain protected at all times. @S913 */ subject s : Null; }
    requirement def R169 { doc /* The System Support Engineer shall provide round the clock on call coverage for production incidents affecting the Regional Flow Platform, Airport CDM Portal, Slot Allocation Engine, Departure Metering Service, Arrival Regulation Console, and Alert Distribution Hub. @S914 */ subject s : SystemSupportEngineer; }
    requirement def R170 { doc /* Standard service desk coverage for access requests, reporting questions, configuration inquiries, and minor usability issues shall be available during normal regional administrative hours on business days. @S915 */ subject s : Null; }
    requirement def R171 { doc /* During published peak traffic periods, Adverse Weather Mode, Capacity Reduction State, and Recovery Phase, the on call support posture shall be raised so that the System Support Engineer can join the Digital Briefing Room without delay. @S916 */ subject s : Null; }
    requirement def R172 { doc /* The Regional Flow Manager, Tower Supervisor, Ramp Control Lead, Airport Duty Manager, and Network Operations Liaison shall retain operational command authority during support activity. @S917 */ subject s : Null; }
    requirement def R173 { doc /* The System Support Engineer shall advise operational supervisors on technical status, known workarounds, data integrity concerns, and recovery options, but shall not issue traffic management instructions. @S918 */ subject s : SystemSupportEngineer; }
    requirement def R174 { doc /* Incidents shall be classified by operational effect, with the highest priority assigned to loss of common situational awareness, loss of slot computation, corruption of operational timing data, or failure of alert distribution during active traffic management. @S919 */ subject s : Null; }
    requirement def R175 { doc /* A critical incident shall be acknowledged within fifteen minutes and shall have continuous technical ownership until service is restored or an agreed operational workaround is in place. @S920 */ subject s : CriticalIncident; }
    requirement def R176 { doc /* A high priority incident that degrades a major function without stopping tactical coordination shall be acknowledged within thirty minutes and shall be reviewed with the affected operational supervisor at least hourly. @S921 */ subject s : HighPriorityIncident; }
    requirement def R177 { doc /* Medium and low priority incidents shall be handled through the service queue, with target updates provided at intervals appropriate to their operational impact and planned resolution path. @S922 */ subject s : Null; }
    requirement def R178 { doc /* The System Support Engineer shall maintain an incident record that captures the initial symptom, affected components, operational state, timeline, mitigation actions, data corrections, and supervisor decisions. @S923 */ subject s : SystemSupportEngineer; }
    requirement def R179 { doc /* Incident records shall reference the Audit Event Ledger where user actions, configuration changes, interface events, or automated decisions are relevant to the investigation. @S924 */ subject s : IncidentRecord; }
    requirement def R180 { doc /* The Collaborative Decision Log shall be used to preserve the operational context of major incidents when traffic management decisions are made while a technical degradation is present. @S925 */ subject s : CollaborativeDecisionLog; }
    requirement def R181 { doc /* The System Support Engineer shall verify that fallback tools, exported operational data, and restoration checkpoints are available before advising that normal technical service can resume. @S927 */ subject s : SystemSupportEngineer; }
    requirement def R182 { doc /* Post incident review shall be required for critical incidents, repeated high priority incidents, security related events, and failures that occur during capacity constrained operations. @S928 */ subject s : Null; }
    requirement def R183 { doc /* The review shall identify technical root cause, operational contributing factors, effectiveness of workarounds, user communication quality, and corrective actions assigned to named owners. @S929 */ subject s : Null; }
    requirement def R184 { doc /* Planned change windows shall normally be scheduled during low demand night periods and shall be coordinated with the Regional Flow Manager, Airport Duty Manager, Tower Supervisor, and affected Aircraft Operator Representative groups before approval. @S930 */ subject s : Null; }
    requirement def R185 { doc /* Changes that modify the Business Rules Registry, Identity Access Service, Time Synchronization Service, Flight Data Exchange, or operational metering behavior shall require additional validation in a representative test environment before production release. @S931 */ subject s : Null; }
    requirement def R186 { doc /* Emergency changes may be applied outside the standard window when needed to restore service, protect cyber security, or prevent material operational harm, but they shall be documented and retrospectively approved. @S932 */ subject s : Null; }
    requirement def R187 { doc /* Service level targets shall include monthly availability for critical production functions, incident response time, restoration time, data feed timeliness, and successful completion of scheduled operational reports. @S933 */ subject s : Null; }
    requirement def R188 { doc /* Availability targets shall exclude approved maintenance windows, customer network outages outside the managed boundary, and periods when operational supervisors have directed use of contingency procedures for nontechnical reasons. @S934 */ subject s : Null; }
    requirement def R189 { doc /* Performance against service targets shall be reviewed with the Regional Flow Manager and Data Governance Steward so that service quality, operational benefit, data quality, and user confidence are managed as a single operating obligation. @S935 */ subject s : Null; }
    requirement def R190 { doc /* Future enhancement of the Regional Flow Platform should be treated as an incremental extension of the operational service rather than as a replacement of the current concept. @S936 */ subject s : RegionalFlowPlatform; }
    requirement def R191 { doc /* Cross-border exchange should use standardized message structures where practical, but the Business Rules Registry should retain the local parameters needed for Meridian operations. @S939 */ subject s : Null; }
    requirement def R192 { doc /* The Flight Data Exchange should be enhanced to accept richer intent data, including improved route options, expected cruise profiles, and updated departure readiness information. @S940 */ subject s : FlightDataExchange; }
    requirement def R193 { doc /* The Demand Prediction Service should use this data to create more stable demand pictures across longer planning horizons while still preserving tactical responsiveness. @S941 */ subject s : DemandPredictionService; }
    requirement def R194 { doc /* Trajectory prediction should also make greater use of weather features, sector configuration, runway direction, and surface movement status when estimating flight progress. @S942 */ subject s : Null; }
    requirement def R195 { doc /* The Weather Ingest Gateway and Sector Load Monitor should provide the common inputs needed to connect airspace capacity and airport capacity in the same prediction cycle. @S943 */ subject s : Null; }
    requirement def R196 { doc /* The Capacity Assessment Module should evolve from a mainly rules-based assessment into a service that can compare planned capacity, observed throughput, and predicted constraint persistence. @S944 */ subject s : CapacityAssessmentModule; }
    requirement def R197 { doc /* Any use of learning models should be introduced with explainability requirements so that operational users can understand why a capacity or delay estimate has changed. @S945 */ subject s : Null; }
    requirement def R198 { doc /* Advanced turnaround prediction should combine aircraft state, handling milestones, stand occupancy, crew readiness, passenger processing, and ramp congestion signals. @S946 */ subject s : Null; }
    requirement def R199 { doc /* The Airport CDM Portal, Airline Interface Adapter, Handling Resource Planner, and Ramp Movement Board should provide the main operational inputs for this capability. @S947 */ subject s : Null; }
    requirement def R200 { doc /* Predicted changes to Target Off Block Time should be presented with confidence levels rather than as unconditional system corrections. @S948 */ subject s : TargetOffBlockTime; }
    requirement def R201 { doc /* The Slot Allocation Engine should use improved turnaround predictions to protect feasible Calculated Takeoff Time assignments and to reduce avoidable re-sequencing. @S949 */ subject s : SlotAllocationEngine; }
    requirement def R202 { doc /* The Tower Sequence Manager and Departure Metering Service should receive only the information needed for tactical sequencing, with detailed airline operational data controlled by policy. @S950 */ subject s : Null; }
    requirement def R203 { doc /* Machine-assisted recovery options should support the Recovery Phase by proposing coordinated actions that balance runway throughput, sector loading, stand availability, and airline priorities. @S951 */ subject s : Null; }
    requirement def R204 { doc /* These options should be generated by the Contingency Operations Console and reviewed through the Common Situation Display before any operational decision is applied. @S952 */ subject s : Null; }
    requirement def R205 { doc /* The system should not automatically impose a Ground Delay Program, change an Airport Acceptance Rate, or alter a tactical measure without authorized human confirmation. @S953 */ subject s : System; }
    requirement def R206 { doc /* Recovery recommendations should include the operational rationale, expected benefit, key assumptions, and possible secondary effects on connected flights and surface movements. @S954 */ subject s : Null; }
    requirement def R207 { doc /* The Collaborative Decision Log and Audit Event Ledger should record each proposed option, the user response, and the final decision so that performance can be reviewed after operations. @S955 */ subject s : Null; }
    requirement def R208 { doc /* Regional expansion should include a repeatable onboarding pattern for new airports, airspace sectors, airlines, and handling organizations. @S956 */ subject s : Null; }
    requirement def R209 { doc /* The Identity Access Service, Time Synchronization Service, and Performance Analytics Warehouse should be scaled early because they form shared foundations for a wider regional deployment. @S957 */ subject s : Null; }
    requirement def R210 { doc /* Data governance should remain under the Data Governance Steward, with clear rules for retention, consent, quality thresholds, and permitted operational use. @S958 */ subject s : DataGovernanceSteward; }
    requirement def R211 { doc /* Future releases should be validated in shadow mode before operational activation so that the Regional Flow Manager, Airline Operations Coordinator, Tower Supervisor, and Airport Duty Manager can compare recommendations with actual outcomes. @S959 */ subject s : Null; }
    requirement def R212 { doc /* Sustained regional ATFM and A-CDM operation requires each participating organization to treat the operating picture as a shared operational asset rather than a local advisory product. @S960 */ subject s : Null; }
    requirement def R213 { doc /* The Common Situation Display is the shared baseline for time-critical coordination and should be kept consistent with the Regional Flow Platform and Airport CDM Portal. @S974 */ subject s : CommonSituationDisplay; }
    requirement def R214 { doc /* Calculated Takeoff Time and Target Off Block Time commitments should be treated as executable operating constraints unless they are revised through the agreed coordination process. @S976 */ subject s : Null; }
    requirement def R215 { doc /* Ground Delay Program decisions, Tactical Regulation Proposal review, and Airport Acceptance Rate changes should be visible to affected participants before they are applied whenever operational time permits. @S977 */ subject s : Null; }
    requirement def R216 { doc /* The Flight Data Exchange, Airline Interface Adapter, Surface Surveillance Adapter, and Weather Ingest Gateway must be operated with monitored data quality thresholds and clear fallback procedures. @S979 */ subject s : Null; }
    requirement def R217 { doc /* The Slot Allocation Engine, Departure Metering Service, Arrival Regulation Console, Tower Sequence Manager, and Ramp Movement Board must use the approved rules recorded in the Business Rules Registry. @S980 */ subject s : Null; }
    requirement def R218 { doc /* The Identity Access Service and Audit Event Ledger must support traceability, least-privilege access, and after-action accountability for all operationally significant changes. @S981 */ subject s : Null; }
    requirement def R219 { doc /* The Performance Analytics Warehouse and Post Operations Report should be used to measure compliance, delay outcomes, capacity use, and the effectiveness of collaborative decisions. @S982 */ subject s : Null; }
    requirement def R220 { doc /* Governance should favor transparent decision making, timely challenge by affected parties, documented resolution of disputes, and continuous improvement through training, exercises, and post-operations review. @S983 */ subject s : Null; }
}
