package L2Model {
    item def AcceptedApronCongestionAdjustmentItem { doc /* @S466 */ }
    item def AcceptedConstraintsItem { doc /* @S135 */ }
    item def AcceptedFuelHoldAdjustmentItem { doc /* @S466 */ }
    item def AcceptedIntentDataItem { doc /* @S128 */ }
    item def AcceptedOrRejectedExemptionWithTheRuleAppliedTheApprovingRoleAndTheExpectedOperationalConsequenceItem { doc /* @S239 */ }
    item def AcceptedRunwayMeteringAdjustmentItem { doc /* @S466 */ }
    item def AcceptedSurfaceEquipmentAdjustmentItem { doc /* @S466 */ }
    item def AcknowledgementsItem { doc /* @S405 */ }
    item def ActiveRestrictionStatusItem { doc /* @S337,S338 */ }
    item def ActiveSpacingRulesItem { doc /* @S297 */ }
    item def ActiveSurfaceAdvisoriesItem { doc /* @S462,S463 */ }
    item def AerodromeInfrastructureEventsItem { doc /* @S695 */ }
    item def AffectedFlightItem { doc /* @S166 */ }
    item def AffectedFlightsItem { doc /* @S470 */ }
    item def AffectedResourceItem { doc /* @S704 */ }
    item def AffectedRunwayQueueItem { doc /* @S366 */ }
    item def AffectedStandsItem { doc /* @S462 */ }
    item def AgreedRecoveryTargetItem { doc /* @S506 */ }
    item def AircraftPositionItem { doc /* @S204 */ }
    item def AircraftSizeCompatibilityItem { doc /* @S470 */ }
    item def AirportAcceptanceRateItem { doc /* @S341 */ }
    item def AirspaceAlertsItem { doc /* @S331,S332 */ }
    item def ApprovedDutyCoordinationAlertsItem { doc /* @S193 */ }
    item def ApprovedOperationalResultItem { doc /* @S638 */ }
    item def ApronCongestionItem { doc /* @S218 */ }
    item def ApronCongestionAdvisoriesItem { doc /* @S461 */ }
    item def ArrivalPlanItem { doc /* @S405 */ }
    item def AssignmentsItem { doc /* @S812 */ }
    item def AuditRecordsItem { doc /* @S274 */ }
    item def AviationForecastsItem { doc /* @S108 */ }
    item def BaseMapItem { doc /* @S421 */ }
    item def BlockedLeadInLinesItem { doc /* @S458 */ }
    item def BlockingConditionsItem { doc /* @S204 */ }
    item def BorderAndCustomsStatusItem { doc /* @S572 */ }
    item def CalculatedTakeoffTimeItem { doc /* @S242,S685,S744 */ }
    item def CandidatePushbackSpacingItem { doc /* @S456 */ }
    item def CeilingAndVisibilityForecastsItem { doc /* @S108 */ }
    item def ChangesInStandOccupancySurfaceCongestionRecoveryDurationAndPassengerFacingDisruptionIndicatorsItem { doc /* @S860 */ }
    item def CivilRoutingOptionsItem { doc /* @S093 */ }
    item def CombinedTacticalViewItem { doc /* @S420 */ }
    item def CommonTimeBasisItem { doc /* @S824 */ }
    item def ConditionsThatMayAffectRunwayTaxiwayStandOrApronAvailabilityItem { doc /* @S175 */ }
    item def ConflictingPushbacksItem { doc /* @S458 */ }
    item def ConstraintsItem { doc /* @S225 */ }
    item def ControlledInterfaceItem { doc /* @S016 */ }
    item def CrewLegalityImpactsItem { doc /* @S627 */ }
    item def CurrentAgreedTargetSetItem { doc /* @S265 */ }
    item def CurrentBusinessRulesRegistryParametersItem { doc /* @S080 */ }
    item def CurrentDecisionStatusItem { doc /* @S704 */ }
    item def CurrentMovementAreaOccupancyItem { doc /* @S445 */ }
    item def CurrentOperatingBasisItem { doc /* @S734 */ }
    item def CurrentOperatingScheduleItem { doc /* @S103 */ }
    item def CurrentRegionalDemandAndConstraintContextItem { doc /* @S164 */ }
    item def DataIntegrityConcernsItem { doc /* @S918 */ }
    item def DelayItem { doc /* @S603 */ }
    item def DemandItem { doc /* @S225 */ }
    item def DemandForecastsItem { doc /* @S100,S101 */ }
    item def DemandSmoothingItem { doc /* @S079 */ }
    item def DepartureDemandProfileItem { doc /* @S351 */ }
    item def DispositionItem { doc /* @S833 */ }
    item def DiversionRationaleItem { doc /* @S506 */ }
    item def EastApronSensorIndicationsItem { doc /* @S205 */ }
    item def EquipmentStatusIndicatorsItem { doc /* @S445 */ }
    item def EvidenceItem { doc /* @S887 */ }
    item def ExceptionItem { doc /* @S671 */ }
    item def ExpectedOperationalEffectItem { doc /* @S337,S338 */ }
    item def ExpectedServiceCompletionTimesItem { doc /* @S302 */ }
    item def ExpiredTreatmentsItem { doc /* @S391 */ }
    item def ExternalCoordinationOutcomesItem { doc /* @S084 */ }
    item def FiledFlightInformationItem { doc /* @S103 */ }
    item def FlightIdentifiersItem { doc /* @S462 */ }
    item def FlightIntentMessageItem { doc /* @S126 */ }
    item def FlightListItem { doc /* @S421 */ }
    item def FluidShortagesItem { doc /* @S391 */ }
    item def FrozenOperationalTargetsItem { doc /* @S275 */ }
    item def GateConflictItem { doc /* @S470 */ }
    item def GateOrStandDecisionItem { doc /* @S475 */ }
    item def HandlingResourcePlannerConstraintsItem { doc /* @S213 */ }
    item def InappropriatePrivilegeUseItem { doc /* @S780 */ }
    item def InformationItem { doc /* @S063 */ }
    item def InsufficientRoomForSafeWingtipClearanceItem { doc /* @S458 */ }
    item def KnownWorkaroundsItem { doc /* @S918 */ }
    item def LatestFeasibleOffBlockTimeItem { doc /* @S470 */ }
    item def LightningAlertsItem { doc /* @S108 */ }
    item def MainOperationalInputsItem { doc /* @S947 */ }
    item def MandatoryOperationalAdvisoriesItem { doc /* @S731 */ }
    item def MaterialDeviationsItem { doc /* @S091 */ }
    item def MeasureStatusPanelsItem { doc /* @S421 */ }
    item def MorningPlanItem { doc /* @S073 */ }
    item def MorningWeatherOutlookItem { doc /* @S056,S057 */ }
    item def MovementIndicationsItem { doc /* @S179 */ }
    item def MovementUpdatesItem { doc /* @S222 */ }
    item def NormalTechnicalServiceCanResumeItem { doc /* @S927 */ }
    item def NormalizedScheduleItem { doc /* @S053 */ }
    item def NotificationsItem { doc /* @S529,S614 */ }
    item def OperationalBasisItem { doc /* @S400 */ }
    item def OperationalDecisionsItem { doc /* @S907 */ }
    item def OperationalSignificanceItem { doc /* @S447 */ }
    item def OperationalStatusItem { doc /* @S693,S703 */ }
    item def OperationalTradeOffsItem { doc /* @S862 */ }
    item def OutputsItem { doc /* @S095 */ }
    item def OverlappingOccupancyConditionItem { doc /* @S210 */ }
    item def OverloadFlagsItem { doc /* @S592,S593 */ }
    item def PadClosuresItem { doc /* @S391 */ }
    item def PassengerConnectionExposureItem { doc /* @S470 */ }
    item def PassengerDisruptionCuesItem { doc /* @S758 */ }
    item def PlannedRemoteStandOperatingPostureItem { doc /* @S544 */ }
    item def PositionUpdatesItem { doc /* @S179 */ }
    item def PossibleCredentialCompromiseItem { doc /* @S780 */ }
    item def PredictedOccupancyItem { doc /* @S592,S593 */ }
    item def PredictedReadinessItem { doc /* @S593 */ }
    item def PriorityClassificationItem { doc /* @S506 */ }
    item def ProbabilityValueItem { doc /* @S118 */ }
    item def ProposedDepartureOpportunitiesItem { doc /* @S242 */ }
    item def ProposedMitigationItem { doc /* @S531 */ }
    item def RadarDerivedPrecipitationFieldsItem { doc /* @S108 */ }
    item def RampBlockagesItem { doc /* @S391 */ }
    item def RationaleItem { doc /* @S760 */ }
    item def RecoveryOptionsItem { doc /* @S918 */ }
    item def ReferenceRecordItem { doc /* @S052 */ }
    item def RegionalBenefitsItem { doc /* @S862 */ }
    item def RelatedCoordinationNotesItem { doc /* @S337,S338 */ }
    item def RemoteStandStatusItem { doc /* @S560 */ }
    item def ResourceCommitmentItem { doc /* @S506 */ }
    item def ResourceDrivenFeasibilityStatusItem { doc /* @S312 */ }
    item def ReviewTimeItem { doc /* @S704 */ }
    item def RevisedInputsItem { doc /* @S699 */ }
    item def RoleSpecificAlertSummariesItem { doc /* @S505 */ }
    item def RunwayConditionWeatherInputsItem { doc /* @S108 */ }
    item def RunwayDeclarationItem { doc /* @S066 */ }
    item def RunwayDemandItem { doc /* @S283 */ }
    item def RunwayEntryQueuesItem { doc /* @S454 */ }
    item def RunwayMetersItem { doc /* @S462 */ }
    item def RunwaySpecificCapacityValuesItem { doc /* @S114 */ }
    item def SaturatedHoldingPointsItem { doc /* @S458 */ }
    item def ScheduledMovementsItem { doc /* @S593 */ }
    item def SharedViewOfDemandCapacityConstraintsAndActiveTrafficManagementMeasuresItem { doc /* @S020 */ }
    item def SlotComplianceEventsItem { doc /* @S789 */ }
    item def StakeholderRemarksItem { doc /* @S429 */ }
    item def StandOccupancyItem { doc /* @S204 */ }
    item def StandReadinessItem { doc /* @S250 */ }
    item def StartTimeItem { doc /* @S704 */ }
    item def SubscriptionRulesItem { doc /* @S332 */ }
    item def SupportingMovementEvidenceItem { doc /* @S474 */ }
    item def SurfaceEquipmentAdvisoriesItem { doc /* @S461 */ }
    item def SynchronizedTimestampsItem { doc /* @S098,S122 */ }
    item def TargetOffBlockTimeItem { doc /* @S429,S685 */ }
    item def TargetUpdatesItem { doc /* @S922 */ }
    item def TaxiSegmentsItem { doc /* @S462 */ }
    item def TechnicalStatusItem { doc /* @S918 */ }
    item def TheCapacityPictureMayChangeItem { doc /* @S121 */ }
    item def TimeItem { doc /* @S778 */ }
    item def TimeBucketedCountsItem { doc /* @S592,S593 */ }
    item def TimelineItem { doc /* @S421,S437 */ }
    item def TimingConstraintAndDecisionOwnershipInformationItem { doc /* @S505 */ }
    item def TowerReadinessChangesItem { doc /* @S293 */ }
    item def TraceFromIncomingForecastProductToCapacityValueItem { doc /* @S123 */ }
    item def TransactionItem { doc /* @S194 */ }
    item def TransitionToContingencyFallbackStateItem { doc /* @S926 */ }
    item def TugAvailabilityItem { doc /* @S677 */ }
    item def UnresolvedAssumptionsItem { doc /* @S071 */ }
    item def UseOfContingencyProceduresForNontechnicalReasonsItem { doc /* @S934 */ }
    item def WeatherImpactsItem { doc /* @S434 */ }
    item def WestApronSensorIndicationsItem { doc /* @S205 */ }
    item def WhetherTheOperatorCanAcceptALaterOffBlockTimeWithoutCausingCrewConnectionOrAircraftRotationImpactsItem { doc /* @S317 */ }
    item def WindForecastsItem { doc /* @S108 */ }
    part def AbnormalSystemIndications { doc /* @S498 */ }
    part def AcceptedAmendment { doc /* @S266 */ }
    part def AccessControl { doc /* @S786 */ }
    part def AccessLimitations { doc /* @S526 */ }
    part def AccessRoute { doc /* @S656 */ }
    part def AccessibleBoardingSupport { doc /* @S548 */ }
    part def AccessibleTransferTimes { doc /* @S563 */ }
    part def AccountableFlowRoles { doc /* @S099 */ }
    part def AccountableOperationalRole { doc /* @S518,S531 */ }
    part def AccountableParticipant { doc /* @S168 */ }
    part def AccountableParty { doc /* @S522 */ }
    part def ActivePadConfiguration { doc /* @S375 */ }
    part def ActiveSurfaceAdvisories { doc /* @S464 */ }
    part def ActorResponsibleForTheTurnaround { doc /* @S482 */ }
    part def ActualMovementMilestones { doc /* @S801 */ }
    part def ActualTakeoffOrOffBlockEvent { doc /* @S849 */ }
    part def AdditionalGroundHandlingResources { doc /* @S460 */ }
    part def AdvancedTurnaroundPrediction { doc /* @S946,S947 */ }
    part def AdverseWeatherMode { doc /* @S047 */ }
    part def Advisory { doc /* @S748 */ }
    part def AdvisoryUseOfPassengerDisruptionData { doc /* @S760 */ }
    part def AerodromeInfrastructureEvents { doc /* @S690,S698,S699,S706 */ }
    part def AffectedFlight { doc /* @S451,S518 */ }
    part def AffectedOperationalRoles { doc /* @S193 */ }
    part def AffectedResource { doc /* @S691,S713 */ }
    part def AffectedRoute { doc /* @S607 */ }
    part def AggregatedMetrics { doc /* @S805 */ }
    part def AgreedDepartureWindow { doc /* @S428 */ }
    part def AgreedOperationalWorkaround { doc /* @S920 */ }
    part def AirNavigationServiceParticipation { doc /* @S045 */ }
    part def AirTrafficControllers { doc /* @S865 */ }
    part def AirborneDelay { doc /* @S407 */ }
    part def Aircraft { doc /* @S236,S281,S299,S305,S320,S347,S348,S353,S360,S362,S364,S377,S387,S389,S476,S483,S521,S542,S558 */ }
    part def AircraftCondition { doc /* @S414 */ }
    part def AircraftOperatorRepresentative { doc /* @S011,S039,S055,S082,S291,S312,S316,S317,S363,S405,S437,S476,S620,S630,S666,S673,S725,S771,S797,S854,S868,S893,S965 */ }
    part def AircraftRegistration { doc /* @S127 */ }
    part def AircraftServiceability { doc /* @S449 */ }
    part def AircraftSwap { doc /* @S618 */ }
    part def AircraftTurnPerformance { doc /* @S065 */ }
    part def Airline { doc /* @S139,S754 */ }
    part def AirlineInterfaceAdapter { doc /* @S018,S033,S103,S126,S128,S135,S235,S452,S478,S618,S741,S829,S947,S979 */ }
    part def AirlineOperationsCentre { doc /* @S126 */ }
    part def AirlineOperationsCentreIntegration { doc /* @S124 */ }
    part def AirlineOperationsCentres { doc /* @S135,S146 */ }
    part def AirlineOperationsCoordinator { doc /* @S011,S039,S054,S081,S121,S129,S138,S157,S214,S237,S259,S260,S284,S312,S317,S338,S362,S385,S403,S437,S451,S472,S507,S521,S546,S554,S574,S604,S623,S630,S658,S667,S679,S725,S740,S766,S771,S795,S820,S854,S868,S893,S959,S965 */ }
    part def AirlineParticipants { doc /* @S372 */ }
    part def AirlineRecoveryActions { doc /* @S143 */ }
    part def AirlineRecoveryInformation { doc /* @S761 */ }
    part def AirlineRoles { doc /* @S560 */ }
    part def AirlineUsers { doc /* @S382 */ }
    part def Airlines { doc /* @S043 */ }
    part def Airport { doc /* @S890 */ }
    part def AirportAcceptanceRate { doc /* @S107 */ }
    part def AirportAcceptanceRateChanges { doc /* @S977 */ }
    part def AirportAcceptanceRateConstraints { doc /* @S046 */ }
    part def AirportAcceptanceRateValues { doc /* @S816 */ }
    part def AirportAndAirlineUsers { doc /* @S469 */ }
    part def AirportAuthority { doc /* @S188 */ }
    part def AirportCDMPortal { doc /* @S016,S031,S088,S150,S166,S170,S172,S179,S185,S195,S264,S270,S293,S312,S337,S338,S381,S405,S429,S447,S470,S485,S503,S527,S531,S544,S559,S572,S602,S648,S649,S668,S681,S695,S720,S812,S907,S947 */ }
    part def AirportCapacityDeclarations { doc /* @S816 */ }
    part def AirportCapacityPlan { doc /* @S872 */ }
    part def AirportCapacityPlanAssumptions { doc /* @S046 */ }
    part def AirportCapacityPlanRecords { doc /* @S816 */ }
    part def AirportCommunity { doc /* @S313 */ }
    part def AirportContinuity { doc /* @S784 */ }
    part def AirportDutyDesk { doc /* @S178 */ }
    part def AirportDutyManager { doc /* @S011,S040,S062,S088,S091,S116,S144,S162,S175,S177,S181,S183,S190,S196,S218,S345,S368,S435,S447,S471,S496,S544,S563,S568,S660,S678,S692,S713,S716,S734,S750,S809,S816,S860,S872,S893,S917,S959,S962 */ }
    part def AirportDutyManagerHandover { doc /* @S198 */ }
    part def AirportLevelConstraintProcess { doc /* @S591 */ }
    part def AirportMeasures { doc /* @S610 */ }
    part def AirportNetwork { doc /* @S003,S026 */ }
    part def AirportOnboarding { doc /* @S902 */ }
    part def AirportOperator { doc /* @S779 */ }
    part def AirportParticipant { doc /* @S167 */ }
    part def AirportParticipants { doc /* @S150,S372 */ }
    part def AirportRoles { doc /* @S560 */ }
    part def AirportServiceConstraints { doc /* @S062 */ }
    part def AirportStakeholders { doc /* @S016 */ }
    part def AirspaceAlerts { doc /* @S332 */ }
    part def AirspaceConstraints { doc /* @S967 */ }
    part def AirspacePlanningPersonnel { doc /* @S045 */ }
    part def AirspaceRestrictions { doc /* @S334,S344 */ }
    part def AirspaceSectorPlanner { doc /* @S041,S058,S079,S326,S345,S402,S432,S501,S608,S871 */ }
    part def AirspaceStructure { doc /* @S041 */ }
    part def AlertDistributionHub { doc /* @S033,S073,S121,S193,S331,S332,S366,S440,S461,S505,S529,S588,S614,S705,S731,S834 */ }
    part def Allocation { doc /* @S258 */ }
    part def ApprovalLatency { doc /* @S689 */ }
    part def ApprovedCompanyProcess { doc /* @S620 */ }
    part def ApprovedInterfaces { doc /* @S820 */ }
    part def ApprovedSources { doc /* @S108 */ }
    part def ApprovedSubstitution { doc /* @S684 */ }
    part def ApprovingAuthority { doc /* @S691 */ }
    part def ApronAvailabilityConstraints { doc /* @S678 */ }
    part def ApronCleaning { doc /* @S658 */ }
    part def ApronCongestion { doc /* @S218 */ }
    part def ApronContamination { doc /* @S660 */ }
    part def ApronDrivingSpeeds { doc /* @S319 */ }
    part def ApronPosition { doc /* @S474 */ }
    part def ApronSensing { doc /* @S588 */ }
    part def ApronSensingData { doc /* @S589 */ }
    part def ApronSensorEvents { doc /* @S585 */ }
    part def Arrival { doc /* @S618 */ }
    part def ArrivalOpportunity { doc /* @S227 */ }
    part def ArrivalRegulation { doc /* @S395,S573 */ }
    part def ArrivalRegulationConsole { doc /* @S017,S032,S070,S095,S241,S336,S407,S495,S535,S576,S596,S698,S729,S757,S980 */ }
    part def ArrivalWorkspace { doc /* @S155 */ }
    part def ArrivalsToTheMainHub { doc /* @S004 */ }
    part def AssignedAircraftRoute { doc /* @S545 */ }
    part def AssignedApronArea { doc /* @S647 */ }
    part def AssignedTeam { doc /* @S301 */ }
    part def AuditEventLedger { doc /* @S021,S034,S098,S123,S194,S222,S245,S271,S274,S289,S417,S442,S466,S488,S515,S537,S636,S664,S683,S710,S777,S789,S792,S833,S887,S890,S955,S981 */ }
    part def AuditOutputs { doc /* @S811 */ }
    part def AuditProcessing { doc /* @S788 */ }
    part def AuditRecords { doc /* @S778,S779 */ }
    part def AuditSequences { doc /* @S807 */ }
    part def AuditTrail { doc /* @S797 */ }
    part def AuthenticatedAirlineAndHandlingUsers { doc /* @S293 */ }
    part def Authority { doc /* @S717 */ }
    part def AuthorizedActor { doc /* @S708 */ }
    part def AuthorizedAirportAirlineAndFlowManagementUsers { doc /* @S695 */ }
    part def AuthorizedOperationalUsers { doc /* @S572 */ }
    part def AuthorizedUser { doc /* @S264 */ }
    part def AuthorizedUsers { doc /* @S020,S462,S627 */ }
    part def AutomatedSuggestions { doc /* @S623 */ }
    part def Automation { doc /* @S963 */ }
    part def AvailabilityTargets { doc /* @S934 */ }
    part def AverageQueueLength { doc /* @S846 */ }
    part def BaggageAndHandlerData { doc /* @S541 */ }
    part def BaggageOrHandlerException { doc /* @S530 */ }
    part def BaggageReconciliationData { doc /* @S452 */ }
    part def BasedCarriers { doc /* @S043 */ }
    part def BenefitSummaries { doc /* @S860 */ }
    part def Boarding { doc /* @S308 */ }
    part def BorderAndCustomsData { doc /* @S587 */ }
    part def BorderAndCustomsStates { doc /* @S586 */ }
    part def BorderProcessing { doc /* @S568 */ }
    part def BorderReleaseStatus { doc /* @S571,S589 */ }
    part def Bus { doc /* @S306 */ }
    part def BusLoading { doc /* @S563 */ }
    part def BusinessRulesRegistry { doc /* @S034,S055,S080,S297,S332,S436,S486,S539,S586,S631,S670,S706,S746,S768,S831,S890,S939 */ }
    part def BusinessRulesRegistryParameters { doc /* @S365 */ }
    part def BusinessRulesRegistryThreshold { doc /* @S534 */ }
    part def CalculatedTakeoffTime { doc /* @S269,S305,S625 */ }
    part def CalculatedTakeoffTimeCommitments { doc /* @S976 */ }
    part def CalculatedTakeoffTimeTolerances { doc /* @S815 */ }
    part def CalculatedTakeoffTimeValues { doc /* @S046 */ }
    part def CalculatedTimes { doc /* @S865 */ }
    part def CancellationAvoidance { doc /* @S852 */ }
    part def CandidateAirport { doc /* @S893 */ }
    part def Capacity { doc /* @S723 */ }
    part def CapacityAssessmentModule { doc /* @S014,S031,S057,S066,S094,S107,S114,S120,S132,S133,S192,S225,S252,S328,S341,S351,S373,S400,S431,S448,S494,S557,S584,S594,S600,S694,S697,S755,S825,S853,S900,S944,S973 */ }
    part def CapacityChanges { doc /* @S803 */ }
    part def CapacityOrDelayEstimate { doc /* @S945 */ }
    part def CapacityPicture { doc /* @S100,S121 */ }
    part def CapacityReductionState { doc /* @S047 */ }
    part def CapacityUpdate { doc /* @S269 */ }
    part def CapacityValues { doc /* @S120 */ }
    part def CargoAndGeneralAviationAerodromes { doc /* @S001 */ }
    part def CargoOperators { doc /* @S043 */ }
    part def Catering { doc /* @S385 */ }
    part def CertificationResults { doc /* @S901 */ }
    part def Change { doc /* @S797 */ }
    part def Changes { doc /* @S073,S800,S931 */ }
    part def CharterOperators { doc /* @S043 */ }
    part def CivilTrafficManagers { doc /* @S324 */ }
    part def ClearAlertPrioritization { doc /* @S884 */ }
    part def ClosedBays { doc /* @S375 */ }
    part def CoastalFog { doc /* @S005 */ }
    part def CodeSetChecks { doc /* @S826 */ }
    part def CollaborativeDecisionLog { doc /* @S021,S071,S084,S122,S169,S186,S221,S239,S267,S392,S405,S442,S466,S487,S506,S531,S589,S615,S637,S682,S709,S760,S794,S925,S955 */ }
    part def CollaborativeDecisionLogEntries { doc /* @S046 */ }
    part def CollaborativeTargetTimeManagement { doc /* @S249 */ }
    part def CommonServices { doc /* @S030 */ }
    part def CommonSituationDisplay { doc /* @S020,S072,S088,S095,S130,S165,S265,S337,S366,S391,S400,S421,S437,S462,S463,S527,S528,S560,S613,S627,S628,S685,S704,S758,S822,S974 */ }
    part def CommonSituationDisplayContent { doc /* @S046 */ }
    part def CommunicationSequencing { doc /* @S504 */ }
    part def CompetentController { doc /* @S188 */ }
    part def ComplianceAssessment { doc /* @S790 */ }
    part def ComplianceWithRevisedTimes { doc /* @S689 */ }
    part def Condition { doc /* @S446 */ }
    part def ConditionalAvailability { doc /* @S059 */ }
    part def ConditionalRouteAvailability { doc /* @S609 */ }
    part def Conditions { doc /* @S516,S517 */ }
    part def ConditionsThatMayAffectRunwayTaxiwayStandOrApronAvailability { doc /* @S175 */ }
    part def ConfidenceLevel { doc /* @S518,S691 */ }
    part def ConfidenceRecord { doc /* @S118,S119 */ }
    part def ConfidenceValue { doc /* @S607 */ }
    part def ConfirmationStepsForHighImpactActions { doc /* @S884 */ }
    part def Congestion { doc /* @S009 */ }
    part def ConnectedServices { doc /* @S165 */ }
    part def ConservativeIntents { doc /* @S146 */ }
    part def ConsistentTerminology { doc /* @S884 */ }
    part def ConstrainedPrimaryAirport { doc /* @S892 */ }
    part def ConstrainedRemoteStandAccess { doc /* @S007 */ }
    part def ConstraintRecords { doc /* @S607 */ }
    part def Contamination { doc /* @S383 */ }
    part def ContaminationReports { doc /* @S371 */ }
    part def ContingencyFallbackState { doc /* @S047 */ }
    part def ContingencyOperationsConsole { doc /* @S032,S195,S247,S719,S783,S908,S952 */ }
    part def ContractedHandlers { doc /* @S044 */ }
    part def ControlledSlotSwapProcess { doc /* @S666 */ }
    part def ConvectiveActivity { doc /* @S409 */ }
    part def ConvectiveAvoidance { doc /* @S858 */ }
    part def ConvectiveReroutes { doc /* @S005 */ }
    part def ConvergingArrivalFlows { doc /* @S408 */ }
    part def Conversion { doc /* @S611 */ }
    part def ConvertedMeasures { doc /* @S614 */ }
    part def CoordinatedActions { doc /* @S951 */ }
    part def CoreOperationalBaseline { doc /* @S890 */ }
    part def Countdowns { doc /* @S422 */ }
    part def Crew { doc /* @S385,S449 */ }
    part def CrewLegality { doc /* @S627 */ }
    part def CrewReadiness { doc /* @S127 */ }
    part def CrewTransportLateness { doc /* @S140 */ }
    part def Crews { doc /* @S308 */ }
    part def CriticalIncident { doc /* @S920 */ }
    part def CriticalSystemRecovery { doc /* @S784 */ }
    part def CrossBorderExchange { doc /* @S939 */ }
    part def Curfew { doc /* @S723 */ }
    part def CustomsHold { doc /* @S575,S588 */ }
    part def CustomsHoldIndicators { doc /* @S569 */ }
    part def CustomsHoldStatus { doc /* @S589 */ }
    part def CustomsStatus { doc /* @S681 */ }
    part def CustomsStatusEvents { doc /* @S585 */ }
    part def CutoverDecision { doc /* @S906 */ }
    part def DailyPlanningCycle { doc /* @S049 */ }
    part def DataDiscoveryWorkshops { doc /* @S902 */ }
    part def DataFeedTimeliness { doc /* @S933 */ }
    part def DataGovernance { doc /* @S812,S958 */ }
    part def DataGovernanceSteward { doc /* @S042,S098,S170,S240,S273,S490,S515,S541,S587,S711,S733,S742,S773,S780,S806,S813,S833,S861,S876,S910 */ }
    part def DataLatency { doc /* @S715 */ }
    part def DataQualityMeasures { doc /* @S836 */ }
    part def DecisionMakers { doc /* @S862 */ }
    part def DecisionSupportFunctions { doc /* @S025 */ }
    part def Declaration { doc /* @S717 */ }
    part def DeclaredCapacity { doc /* @S094 */ }
    part def DedicatedMilestoneView { doc /* @S156 */ }
    part def DefinedContingencyForBlockedApronMovement { doc /* @S545 */ }
    part def DefinedTechnicalBoundary { doc /* @S035,S037 */ }
    part def DegradedPerformance { doc /* @S498 */ }
    part def DegradedWeatherInputs { doc /* @S112 */ }
    part def DeicingConstraints { doc /* @S969 */ }
    part def DeicingCoordinator { doc /* @S040,S092,S294,S375,S390,S875,S969 */ }
    part def DeicingDemand { doc /* @S296 */ }
    part def DeicingInterfacePoint { doc /* @S295 */ }
    part def DeicingProviders { doc /* @S044 */ }
    part def DeicingResidue { doc /* @S661 */ }
    part def DelayAbsorption { doc /* @S573,S840 */ }
    part def DelayAndQueueForecasts { doc /* @S701 */ }
    part def DelayTransfers { doc /* @S857 */ }
    part def Demand { doc /* @S379 */ }
    part def DemandPredictionService { doc /* @S013,S031,S053,S100,S101,S103,S105,S131,S216,S225,S251,S350,S351,S395,S430,S493,S571,S593,S701,S743,S754,S825,S840,S900,S941,S973 */ }
    part def DemandSmoothing { doc /* @S079 */ }
    part def Departure { doc /* @S210 */ }
    part def DepartureFixConstraint { doc /* @S598 */ }
    part def DepartureMetering { doc /* @S597 */ }
    part def DepartureMeteringService { doc /* @S017,S032,S069,S095,S242,S278,S315,S335,S347,S348,S352,S379,S426,S456,S483,S534,S553,S626,S656,S686,S699,S728,S747,S825,S851,S950,S980 */ }
    part def DepartureQueue { doc /* @S453 */ }
    part def DepartureReadinessChecks { doc /* @S290 */ }
    part def Departures { doc /* @S502 */ }
    part def DeparturesFromNearbySecondaryAirports { doc /* @S004 */ }
    part def DeployedAirport { doc /* @S912 */ }
    part def DeploymentOfTheRegionalFlowPlatform { doc /* @S888 */ }
    part def Design { doc /* @S640 */ }
    part def DesignatedMilitaryCoordinationFunction { doc /* @S045 */ }
    part def DigitalBriefingRoom { doc /* @S031,S071,S345,S506,S734 */ }
    part def DiversionAndIrregularOperationsHandling { doc /* @S491 */ }
    part def DiversionChoices { doc /* @S512 */ }
    part def DiversionDecision { doc /* @S507 */ }
    part def DiversionRecovery { doc /* @S503 */ }
    part def DiversionRisk { doc /* @S413 */ }
    part def DiversionTraffic { doc /* @S501 */ }
    part def DownstreamServices { doc /* @S638 */ }
    part def Drivers { doc /* @S548 */ }
    part def DualControl { doc /* @S775 */ }
    part def EarlierValue { doc /* @S270 */ }
    part def EastApronSensor { doc /* @S019,S035,S063,S115,S179,S205,S282,S474,S578,S645,S845 */ }
    part def EffectiveTime { doc /* @S691 */ }
    part def EmergencyChanges { doc /* @S932 */ }
    part def EmergencyConditions { doc /* @S968 */ }
    part def EmergencyResponseActivity { doc /* @S096 */ }
    part def EmergencyResponseConditions { doc /* @S041 */ }
    part def EmergencyResponseCoordinator { doc /* @S041,S414,S499,S874,S968 */ }
    part def EmissionsMetrics { doc /* @S857 */ }
    part def EmissionsReduction { doc /* @S855 */ }
    part def EnRouteConstraints { doc /* @S608 */ }
    part def EndTime { doc /* @S607 */ }
    part def Engine { doc /* @S855 */ }
    part def EquipmentAvailability { doc /* @S211 */ }
    part def EquipmentFaults { doc /* @S383 */ }
    part def EquipmentUnserviceability { doc /* @S526 */ }
    part def EquityConcerns { doc /* @S689 */ }
    part def Escalation { doc /* @S096 */ }
    part def EstimatedRecoveryTime { doc /* @S518 */ }
    part def Event { doc /* @S643 */ }
    part def ExceptionProcessing { doc /* @S516 */ }
    part def ExceptionRecord { doc /* @S518 */ }
    part def ExcessHolding { doc /* @S406 */ }
    part def Exercise { doc /* @S881 */ }
    part def Exercises { doc /* @S882 */ }
    part def ExpansionBeyondThePilotAirports { doc /* @S909 */ }
    part def ExpectedBenefit { doc /* @S954 */ }
    part def ExpectedCapacity { doc /* @S607 */ }
    part def ExpectedCruiseProfiles { doc /* @S940 */ }
    part def ExpectedDuration { doc /* @S691 */ }
    part def Failures { doc /* @S928 */ }
    part def Findings { doc /* @S810 */ }
    part def FirstIncrement { doc /* @S889 */ }
    part def FlexibleUseAirspace { doc /* @S511 */ }
    part def Flight { doc /* @S265,S284,S295,S297,S570,S623,S632,S666,S744,S791,S849 */ }
    part def FlightDataExchange { doc /* @S018,S033,S052,S053,S103,S128,S278,S593,S638,S684,S827,S840,S940,S979 */ }
    part def FlightIntentMessage { doc /* @S127 */ }
    part def FlightIntentMessageStatus { doc /* @S046 */ }
    part def Flights { doc /* @S519 */ }
    part def FlowManagement { doc /* @S331 */ }
    part def FlowManagementMeasure { doc /* @S460 */ }
    part def FlowManagementPolicyData { doc /* @S814 */ }
    part def FlowMeasures { doc /* @S865 */ }
    part def FlowStaff { doc /* @S437 */ }
    part def FluidLimitations { doc /* @S375 */ }
    part def ForecastCapacity { doc /* @S070 */ }
    part def ForecastConfidence { doc /* @S121 */ }
    part def ForecastProduct { doc /* @S111 */ }
    part def ForeignObjectDebrisChecks { doc /* @S644 */ }
    part def FreezeHorizon { doc /* @S260 */ }
    part def FreezingPrecipitation { doc /* @S371 */ }
    part def FreshnessBreaches { doc /* @S836 */ }
    part def FreshnessIndicators { doc /* @S822,S823 */ }
    part def FuelHydrantPoint { doc /* @S446 */ }
    part def FuelLimitations { doc /* @S498 */ }
    part def FuelMargins { doc /* @S413 */ }
    part def FuelVehicleHolds { doc /* @S449 */ }
    part def FuelingConstraint { doc /* @S450 */ }
    part def FuelingProviders { doc /* @S044 */ }
    part def FullRegionalDeployment { doc /* @S911 */ }
    part def FutureReleases { doc /* @S959 */ }
    part def Gate { doc /* @S472 */ }
    part def GateBridge { doc /* @S446 */ }
    part def GateConflictDetector { doc /* @S019,S035,S210,S364,S386,S439,S459,S468,S509,S558,S582,S657,S900 */ }
    part def GateOrStandDecision { doc /* @S475 */ }
    part def GateRecoveryAction { doc /* @S479 */ }
    part def Governance { doc /* @S983 */ }
    part def GroundDelayProgram { doc /* @S067,S136,S227,S398,S424,S842 */ }
    part def GroundDelayProgramDecisions { doc /* @S977 */ }
    part def GroundDelayProgramParameters { doc /* @S814 */ }
    part def GroundEquipment { doc /* @S473 */ }
    part def GroundHandlingDispatcher { doc /* @S040,S064,S091,S140,S158,S261,S292,S302,S383,S438,S508,S519,S523,S550,S643,S653,S893,S966 */ }
    part def GroundHandlingPersonnel { doc /* @S869 */ }
    part def GroundMovement { doc /* @S657 */ }
    part def GroundPowerUnit { doc /* @S446 */ }
    part def GroundServiceProviders { doc /* @S044 */ }
    part def Groups { doc /* @S478 */ }
    part def HandlerDispatch { doc /* @S301 */ }
    part def HandlerException { doc /* @S535 */ }
    part def HandlerExceptions { doc /* @S526 */ }
    part def HandlingCoordinationCalls { doc /* @S063 */ }
    part def HandlingResourcePlanner { doc /* @S065,S141,S212,S213,S302,S303,S304,S318,S384,S460,S477,S522,S547,S830,S947 */ }
    part def HandlingResources { doc /* @S314 */ }
    part def HandlingStatus { doc /* @S158 */ }
    part def HarborEastAirport { doc /* @S026,S027 */ }
    part def HeldArrival { doc /* @S568 */ }
    part def HighFrequencyDomesticAirports { doc /* @S001 */ }
    part def HighPriorityIncident { doc /* @S921 */ }
    part def Hold { doc /* @S307 */ }
    part def HumanFactorsSafeguards { doc /* @S884 */ }
    part def IdentityAccessService { doc /* @S034,S126,S152,S194,S272,S515,S635,S650,S781,S783,S793,S890,S957,S981 */ }
    part def ImprovedRouteOptions { doc /* @S940 */ }
    part def InboundAircraft { doc /* @S416 */ }
    part def InboundDemand { doc /* @S395 */ }
    part def IncidentRecord { doc /* @S923,S924 */ }
    part def IncidentResponseTime { doc /* @S933 */ }
    part def Incidents { doc /* @S919 */ }
    part def InconsistentOperationalOutputs { doc /* @S715 */ }
    part def IndividualAircraftRotations { doc /* @S467 */ }
    part def InfeasibleRotation { doc /* @S623 */ }
    part def InformationServices { doc /* @S025 */ }
    part def InitialPilot { doc /* @S892 */ }
    part def InitialTraining { doc /* @S878 */ }
    part def IntegratedTacticalManagementPosition { doc /* @S420,S421,S429,S434,S435 */ }
    part def Interface { doc /* @S899 */ }
    part def InterfaceCertification { doc /* @S898 */ }
    part def InterfacesToExternalSystems { doc /* @S037 */ }
    part def IntersectingTaxiRoutes { doc /* @S007 */ }
    part def Investigations { doc /* @S778 */ }
    part def KeyAssumptions { doc /* @S954 */ }
    part def LakesideRegionalAirport { doc /* @S026,S027 */ }
    part def LandingRateStability { doc /* @S415 */ }
    part def LateAirportDrivenChanges { doc /* @S809 */ }
    part def LateAirspaceCapacityChanges { doc /* @S340 */ }
    part def LateOperationalChanges { doc /* @S799 */ }
    part def LaterComparisons { doc /* @S052 */ }
    part def LaterReview { doc /* @S537,S683,S792 */ }
    part def LatestSweepConfirmation { doc /* @S662 */ }
    part def LearningModels { doc /* @S945 */ }
    part def LegalityIndicators { doc /* @S618 */ }
    part def LessConstrainedRegionalAirport { doc /* @S892 */ }
    part def LifeSafety { doc /* @S784 */ }
    part def LightingPerformance { doc /* @S694 */ }
    part def LimitedGateBuffers { doc /* @S007 */ }
    part def LoadingPositions { doc /* @S548 */ }
    part def LocalBusinessDecisions { doc /* @S854 */ }
    part def LocalCapacity { doc /* @S938 */ }
    part def LocalCondition { doc /* @S178,S193 */ }
    part def LocalCoordinationAgreements { doc /* @S055 */ }
    part def LocalCoordinationDecision { doc /* @S186 */ }
    part def LocalDecisions { doc /* @S008 */ }
    part def LocalDutyCoordination { doc /* @S191 */ }
    part def LocalObservations { doc /* @S116 */ }
    part def LocalResequencing { doc /* @S286 */ }
    part def LocalSequencingConstraints { doc /* @S061 */ }
    part def LocalStakeholders { doc /* @S894 */ }
    part def LocalTool { doc /* @S903,S904 */ }
    part def LocalTools { doc /* @S905 */ }
    part def LocalTroubleshootingDetails { doc /* @S528 */ }
    part def LocalUsers { doc /* @S907 */ }
    part def Locations { doc /* @S891 */ }
    part def LowConfidenceWeatherForecasts { doc /* @S120 */ }
    part def LowSurfaceTemperatureForecasts { doc /* @S371 */ }
    part def MachineAssistedRecoveryOptions { doc /* @S951,S952 */ }
    part def MaintenanceRequirements { doc /* @S498 */ }
    part def MandatoryFieldChecks { doc /* @S826 */ }
    part def ManualCorrections { doc /* @S836 */ }
    part def ManualSlotProcedures { doc /* @S723 */ }
    part def MarkedTaxilane { doc /* @S446 */ }
    part def MarshallingStaff { doc /* @S473 */ }
    part def MaximumPermittedAge { doc /* @S823 */ }
    part def MaximumQueueLength { doc /* @S846 */ }
    part def MedicalPriorityAircraft { doc /* @S496 */ }
    part def MediumAndLowPriorityIncidents { doc /* @S922 */ }
    part def MeridianInternationalAirport { doc /* @S026,S027 */ }
    part def MeridianRegion { doc /* @S001 */ }
    part def MeridianRegionalCapability { doc /* @S022,S023,S025,S028,S031 */ }
    part def MeridianRegionalOperation { doc /* @S323 */ }
    part def MeteorologyBriefingOfficer { doc /* @S041,S056,S057,S085,S086,S087,S112,S119,S163,S372,S434,S512,S819,S858,S873 */ }
    part def MeteringAction { doc /* @S457 */ }
    part def MeteringAdjustment { doc /* @S739 */ }
    part def MeteringDecisions { doc /* @S361 */ }
    part def MeteringHorizon { doc /* @S368 */ }
    part def MeteringProcess { doc /* @S349 */ }
    part def MeteringRules { doc /* @S355 */ }
    part def MigrationPlan { doc /* @S903 */ }
    part def Milestone { doc /* @S166 */ }
    part def MilitaryAirspaceLiaison { doc /* @S041,S059,S093,S325,S345,S433,S511,S609 */ }
    part def MilitaryTrainingAreas { doc /* @S006 */ }
    part def MinorTimeBasedSequenceAdjustment { doc /* @S397 */ }
    part def MissingEquipment { doc /* @S524 */ }
    part def Model { doc /* @S619 */ }
    part def MonitoredRunwayLightingStatus { doc /* @S606 */ }
    part def MonthlyAvailability { doc /* @S933 */ }
    part def Movement { doc /* @S663 */ }
    part def NamedOperationalUser { doc /* @S764 */ }
    part def NetworkCoordination { doc /* @S607 */ }
    part def NetworkOperationsLiaison { doc /* @S039,S083,S084,S339,S413,S480,S510,S614,S674,S871,S917,S938 */ }
    part def NominalFleetOfEquipment { doc /* @S309 */ }
    part def NormalOperations { doc /* @S047 */ }
    part def NormalTechnicalService { doc /* @S927 */ }
    part def NorthRunwayMeter { doc /* @S019,S035,S114,S280,S359,S454,S845,S900 */ }
    part def NorthValleyAirport { doc /* @S026,S027 */ }
    part def Null { doc /* @S453,S458,S459,S464,S465,S466,S467,S468,S470,S471,S472,S473,S474,S475,S477,S480,S482,S483,S908,S911,S912,S913,S916,S919,S920,S921,S922,S925,S926,S927,S928,S929,S930,S932,S934 */ }
    part def OnCallSupportPosture { doc /* @S916 */ }
    part def OnboardingWave { doc /* @S910 */ }
    part def OpenBays { doc /* @S375 */ }
    part def OperationalApprovalPrivileges { doc /* @S772 */ }
    part def OperationalConcept { doc /* @S543 */ }
    part def OperationalConstraint { doc /* @S691,S696 */ }
    part def OperationalDecision { doc /* @S169 */ }
    part def OperationalDelay { doc /* @S659 */ }
    part def OperationalGroup { doc /* @S505 */ }
    part def OperationalNeed { doc /* @S782 */ }
    part def OperationalParticipants { doc /* @S265 */ }
    part def OperationalPlanningCycle { doc /* @S341 */ }
    part def OperationalPlausibilityChecks { doc /* @S826 */ }
    part def OperationalPositions { doc /* @S332 */ }
    part def OperationalProcesses { doc /* @S025 */ }
    part def OperationalRationale { doc /* @S954 */ }
    part def OperationalSafetyIssue { doc /* @S207 */ }
    part def OperationalSegregation { doc /* @S774 */ }
    part def OperationalServiceManagement { doc /* @S912 */ }
    part def OperationalStaff { doc /* @S704 */ }
    part def OperationalState { doc /* @S872 */ }
    part def OperationalSupervisors { doc /* @S918,S934 */ }
    part def OperationalUsers { doc /* @S490,S685,S945 */ }
    part def Operator { doc /* @S316,S363,S632 */ }
    part def OperatorCoordinationRoles { doc /* @S331 */ }
    part def OperatorProfileHelpText { doc /* @S423 */ }
    part def Operators { doc /* @S603 */ }
    part def Outputs { doc /* @S095 */ }
    part def OwnedDataElement { doc /* @S821 */ }
    part def PadDemand { doc /* @S294 */ }
    part def PadQueue { doc /* @S379 */ }
    part def PadQueueControls { doc /* @S376 */ }
    part def ParkedAircraft { doc /* @S208 */ }
    part def Participants { doc /* @S391,S720,S731,S758,S881 */ }
    part def ParticipatingAircraftOperators { doc /* @S779 */ }
    part def ParticipatingOperationalRoles { doc /* @S050 */ }
    part def ParticipatingOrganization { doc /* @S960 */ }
    part def ParticipatingRoles { doc /* @S073 */ }
    part def Party { doc /* @S687 */ }
    part def PassengerBoarding { doc /* @S306 */ }
    part def PassengerConnectionSensitivity { doc /* @S127 */ }
    part def PassengerDisruptionInformation { doc /* @S738 */ }
    part def PassengerStatus { doc /* @S385 */ }
    part def PassengerTransportProviders { doc /* @S044 */ }
    part def Passengers { doc /* @S449 */ }
    part def PerformanceAgainstServiceTargets { doc /* @S935 */ }
    part def PerformanceAnalyticsWarehouse { doc /* @S034,S074,S099,S123,S148,S173,S197,S274,S322,S346,S370,S394,S418,S489,S514,S538,S565,S566,S590,S616,S639,S665,S712,S737,S760,S761,S776,S804,S836,S839,S856,S887,S890,S957,S982 */ }
    part def PerformanceMeasurement { doc /* @S838 */ }
    part def PerformanceMeasures { doc /* @S861 */ }
    part def PhasedIncrements { doc /* @S888 */ }
    part def PilotAirportSelection { doc /* @S891 */ }
    part def PlannedArrival { doc /* @S210 */ }
    part def PlannedChangeWindows { doc /* @S930 */ }
    part def PlannedConnectionInterval { doc /* @S571 */ }
    part def PlannedRemoteStand { doc /* @S545 */ }
    part def PlannedStaffingLimitations { doc /* @S058 */ }
    part def Planners { doc /* @S069,S565 */ }
    part def PlanningComponents { doc /* @S447 */ }
    part def Positions { doc /* @S469,S471 */ }
    part def PossibleSecondaryEffectsOnConnectedFlightsAndSurfaceMovements { doc /* @S954 */ }
    part def PostEventAssessment { doc /* @S248 */ }
    part def PostEventReview { doc /* @S222,S289 */ }
    part def PostExerciseReviews { doc /* @S887 */ }
    part def PostIncidentReview { doc /* @S928,S929 */ }
    part def PostOperationsReport { doc /* @S074,S689,S862,S982 */ }
    part def PostOperationsReportOutputs { doc /* @S046 */ }
    part def PreTacticalCapacityReview { doc /* @S085 */ }
    part def Precipitation { doc /* @S661 */ }
    part def PredictedChangesToTargetOffBlockTime { doc /* @S948 */ }
    part def PredictedHoldingStacks { doc /* @S407 */ }
    part def PredictedQueue { doc /* @S366 */ }
    part def PreferenceFields { doc /* @S631 */ }
    part def PreferredRoute { doc /* @S127 */ }
    part def PrimaryCapacityConstraint { doc /* @S756 */ }
    part def PrimaryInternationalHub { doc /* @S001 */ }
    part def PrimaryWorkspace { doc /* @S153 */ }
    part def PrincipalDelayAbsorptionIndicator { doc /* @S841 */ }
    part def PriorityHandling { doc /* @S500 */ }
    part def ProductionIncidents { doc /* @S914 */ }
    part def ProjectedRecoveredDepartures { doc /* @S484 */ }
    part def Proposal { doc /* @S681 */ }
    part def ProposedDeparture { doc /* @S618 */ }
    part def ProposedTargetOffBlockTimeValues { doc /* @S251 */ }
    part def ProposingFunction { doc /* @S264 */ }
    part def ProtectionAgainstSilentModeChanges { doc /* @S884 */ }
    part def PushbackFlow { doc /* @S184 */ }
    part def PushbackPlanning { doc /* @S654 */ }
    part def PushbackSequence { doc /* @S213 */ }
    part def PushbackWindows { doc /* @S354 */ }
    part def QualifiedPersonnel { doc /* @S643 */ }
    part def QueueLengthPerformance { doc /* @S843 */ }
    part def QueueMetrics { doc /* @S846 */ }
    part def RampBuses { doc /* @S306 */ }
    part def RampControlLead { doc /* @S011,S040,S063,S090,S142,S159,S184,S200,S202,S204,S205,S206,S208,S210,S211,S213,S218,S219,S244,S262,S283,S357,S378,S387,S446,S473,S508,S545,S556,S614,S642,S647,S654,S677,S749,S766,S770,S818,S893,S917,S966 */ }
    part def RampMovementBoard { doc /* @S017,S032,S063,S216,S222,S250,S255,S311,S361,S377,S427,S445,S458,S469,S525,S551,S581,S646,S677,S703,S801,S844,S947,S980 */ }
    part def RampPersonnel { doc /* @S867 */ }
    part def RampRoles { doc /* @S560 */ }
    part def RampServiceOrganizations { doc /* @S044 */ }
    part def RampUsers { doc /* @S382 */ }
    part def RankedOptions { doc /* @S629 */ }
    part def ReadinessGate1 { doc /* @S894 */ }
    part def ReadinessGate2 { doc /* @S895 */ }
    part def ReadinessGate3 { doc /* @S896 */ }
    part def ReadinessGate4 { doc /* @S897 */ }
    part def ReadinessMilestone { doc /* @S518 */ }
    part def ReadinessValidityWindow { doc /* @S663 */ }
    part def RecordedConcurrences { doc /* @S687 */ }
    part def RecoveredGateAssignments { doc /* @S489 */ }
    part def RecoveryAction { doc /* @S674 */ }
    part def RecoveryPhase { doc /* @S047 */ }
    part def RecoveryPlan { doc /* @S754 */ }
    part def RecoveryRecommendations { doc /* @S954 */ }
    part def RecoveryTime { doc /* @S846 */ }
    part def RecurrentTraining { doc /* @S879 */ }
    part def RecurringOwnershipConflicts { doc /* @S836 */ }
    part def ReducedVisibility { doc /* @S464 */ }
    part def RegionalAuthority { doc /* @S779 */ }
    part def RegionalExpansion { doc /* @S956 */ }
    part def RegionalFlowManagementPersonnel { doc /* @S045 */ }
    part def RegionalFlowManager { doc /* @S010,S038,S050,S077,S078,S079,S093,S094,S117,S121,S137,S228,S286,S327,S343,S345,S367,S393,S396,S399,S410,S411,S416,S420,S463,S479,S492,S513,S532,S555,S573,S598,S614,S634,S675,S696,S721,S729,S739,S753,S766,S768,S800,S808,S814,S842,S864,S911,S917,S926,S938,S959,S961 */ }
    part def RegionalFlowPlatform { doc /* @S012,S030,S047,S051,S101,S109,S130,S147,S164,S191,S247,S250,S268,S302,S314,S333,S349,S371,S422,S444,S517,S540,S592,S593,S621,S691,S706,S708,S713,S714,S715,S716,S742,S775,S787,S789,S824,S905,S908,S926,S936 */ }
    part def RegionalFlowPlatformFunction { doc /* @S903 */ }
    part def RegionalFlowPlatformFunctions { doc /* @S097 */ }
    part def RegionalFlowProcess { doc /* @S275 */ }
    part def RegulatedFlight { doc /* @S533 */ }
    part def RegulatoryConstraints { doc /* @S723 */ }
    part def RejectionReasons { doc /* @S689 */ }
    part def ReleaseTiming { doc /* @S294 */ }
    part def RemoteStand { doc /* @S558,S564 */ }
    part def RemoteStandAreas { doc /* @S579 */ }
    part def RemoteStandDeparture { doc /* @S562 */ }
    part def RemoteStandUse { doc /* @S559 */ }
    part def RepeatableOnboardingPattern { doc /* @S956 */ }
    part def RepeatedSlips { doc /* @S315 */ }
    part def Replenishment { doc /* @S383 */ }
    part def Representation { doc /* @S624 */ }
    part def RequestedDepartureTiming { doc /* @S127 */ }
    part def Resequence { doc /* @S214 */ }
    part def ResourceConstraints { doc /* @S869 */ }
    part def ResponsibleActor { doc /* @S487 */ }
    part def ResponsibleOperationalOwner { doc /* @S904 */ }
    part def ResponsibleSweepTeam { doc /* @S647 */ }
    part def RestorationTime { doc /* @S933 */ }
    part def RestrictionHandlingProcess { doc /* @S346 */ }
    part def ResultingSequence { doc /* @S676 */ }
    part def RevisedOffBlockExpectation { doc /* @S215 */ }
    part def RevisedSequence { doc /* @S677 */ }
    part def RicherIntentData { doc /* @S940 */ }
    part def RoleAccountableForTheNextUpdate { doc /* @S166 */ }
    part def RoleProfiles { doc /* @S766,S767 */ }
    part def RunwayBalancing { doc /* @S280 */ }
    part def RunwayConditions { doc /* @S410 */ }
    part def RunwayConfiguration { doc /* @S431 */ }
    part def RunwayCrossingDemand { doc /* @S453 */ }
    part def RunwayEntryQueues { doc /* @S454 */ }
    part def RunwayLightingElements { doc /* @S693 */ }
    part def RunwayOccupancyTrend { doc /* @S453 */ }
    part def RunwayQueueManagement { doc /* @S287 */ }
    part def RunwaySequence { doc /* @S305 */ }
    part def SafeAccessRoutes { doc /* @S473 */ }
    part def SafePassengerTransferPath { doc /* @S545 */ }
    part def Safety { doc /* @S723 */ }
    part def SafetyEvent { doc /* @S096 */ }
    part def SafetySecurityOrServiceabilityIssue { doc /* @S965 */ }
    part def ScarceCapacity { doc /* @S675 */ }
    part def ScheduledPassengerOperators { doc /* @S043 */ }
    part def Schedules { doc /* @S700 */ }
    part def SchemaChecks { doc /* @S826 */ }
    part def SeasonalThunderstorms { doc /* @S005 */ }
    part def Section4 { doc /* @S075 */ }
    part def SectorConstraints { doc /* @S967 */ }
    part def SectorLoadMonitor { doc /* @S019,S035,S106,S329,S408,S484,S592,S593,S755,S900,S943,S973 */ }
    part def SectorLoadingConstraints { doc /* @S006 */ }
    part def SectorPlanning { doc /* @S331 */ }
    part def SectorWorkload { doc /* @S431 */ }
    part def Sectors { doc /* @S592,S594 */ }
    part def SecurityEvent { doc /* @S096 */ }
    part def SecurityMonitoring { doc /* @S780 */ }
    part def SelectedArrivals { doc /* @S398 */ }
    part def SensitivityOfSelectedDepartures { doc /* @S744 */ }
    part def SequencingChanges { doc /* @S865 */ }
    part def Service { doc /* @S920 */ }
    part def ServiceCompletionForecasts { doc /* @S261 */ }
    part def ServiceLevelTargets { doc /* @S933 */ }
    part def ServiceModel { doc /* @S913 */ }
    part def ServiceRoads { doc /* @S579 */ }
    part def ServiceSequencingConflicts { doc /* @S526 */ }
    part def ServiceUnavailability { doc /* @S715 */ }
    part def ServicingActivity { doc /* @S361 */ }
    part def ServicingProgress { doc /* @S211 */ }
    part def SharedAirTrafficFlowManagementAndAirportCollaborativeDecisionMakingCapability { doc /* @S009,S024 */ }
    part def SharedOperationalAccounts { doc /* @S765 */ }
    part def SharedOperationalPicture { doc /* @S046 */ }
    part def SharedWorkspace { doc /* @S164 */ }
    part def ShortDurationStandOccupancy { doc /* @S509 */ }
    part def ShuttleAvailability { doc /* @S548 */ }
    part def SimulationEvents { doc /* @S883 */ }
    part def SimulationExercises { doc /* @S880 */ }
    part def SimultaneousPushbacks { doc /* @S320 */ }
    part def SingleUser { doc /* @S774 */ }
    part def SlotAdherence { doc /* @S847 */ }
    part def SlotAllocationEngine { doc /* @S015,S031,S080,S134,S137,S225,S227,S234,S244,S253,S269,S342,S355,S374,S398,S428,S456,S533,S575,S603,S625,S659,S669,S671,S681,S699,S700,S745,S825,S840,S900,S949,S980 */ }
    part def SlotAllocationReferenceData { doc /* @S815 */ }
    part def SlotComplianceState { doc /* @S047,S247,S791,S850 */ }
    part def SlotComplianceStateDefinitions { doc /* @S815 */ }
    part def SlotCoordinator { doc /* @S011,S039,S068,S080,S136,S161,S229,S239,S258,S285,S356,S404,S457,S481,S502,S614,S633,S671,S672,S722,S724,S726,S736,S744,S766,S768,S798,S815,S848,S870 */ }
    part def SmallChangesInCapacity { doc /* @S069 */ }
    part def Source { doc /* @S118 */ }
    part def SourceData { doc /* @S859 */ }
    part def SouthRunwayMeter { doc /* @S019,S035,S114,S280,S359,S455,S845,S900 */ }
    part def SouthportAirport { doc /* @S026,S027 */ }
    part def SpecialUseAirspace { doc /* @S006,S041 */ }
    part def StabilizationPeriod { doc /* @S910 */ }
    part def StaffingAssumptions { doc /* @S431 */ }
    part def StaffingConstraints { doc /* @S211 */ }
    part def StaffingGaps { doc /* @S526 */ }
    part def StakeholderBenefitTracking { doc /* @S859 */ }
    part def StakeholderOrganization { doc /* @S048 */ }
    part def Stakeholders { doc /* @S023 */ }
    part def StaleData { doc /* @S822 */ }
    part def Stand { doc /* @S209,S386,S518,S646,S652,S656,S663 */ }
    part def StandAccess { doc /* @S184 */ }
    part def StandClosures { doc /* @S660 */ }
    part def StandCluster { doc /* @S309 */ }
    part def StandConflicts { doc /* @S439 */ }
    part def StandEquipmentShortages { doc /* @S308 */ }
    part def StandGateAndPassengerConnectionRecovery { doc /* @S467 */ }
    part def StandPlan { doc /* @S485 */ }
    part def StandReadinessIndication { doc /* @S655 */ }
    part def StandRestoration { doc /* @S658 */ }
    part def StandStatus { doc /* @S318 */ }
    part def StandardServiceDeskCoverage { doc /* @S915 */ }
    part def StartTime { doc /* @S607 */ }
    part def StewardshipReviews { doc /* @S837 */ }
    part def StrongCrosswinds { doc /* @S005 */ }
    part def SubscribedOperationalRole { doc /* @S529 */ }
    part def SubscribedOperationalRoles { doc /* @S461 */ }
    part def Substitution { doc /* @S680 */ }
    part def SubstitutionRecords { doc /* @S796 */ }
    part def SuccessfulCompletionOfScheduledOperationalReports { doc /* @S933 */ }
    part def SurfaceConstraints { doc /* @S007,S008,S443 */ }
    part def SurfaceHolds { doc /* @S465 */ }
    part def SurfaceMovementEvidence { doc /* @S802 */ }
    part def SurfaceSurveillance { doc /* @S454 */ }
    part def SurfaceSurveillanceAdapter { doc /* @S018,S033,S179,S204,S281,S360,S389,S445,S474,S580,S606,S802,S828,S979 */ }
    part def SurfaceSurveillanceAdapterInputs { doc /* @S204 */ }
    part def SurveillanceData { doc /* @S183 */ }
    part def SustainedSaturation { doc /* @S600 */ }
    part def Swap { doc /* @S671,S686 */ }
    part def SwapBetweenCompanyFlights { doc /* @S317 */ }
    part def SwapVolume { doc /* @S689 */ }
    part def Sweep { doc /* @S652 */ }
    part def System { doc /* @S104,S318,S320,S459,S465,S717,S727,S728,S735,S738,S739,S752,S953 */ }
    part def SystemSupportEngineer { doc /* @S042,S171,S688,S732,S772,S780,S807,S835,S877,S910,S914,S916,S918,S923,S927 */ }
    part def TacticalConstraints { doc /* @S323,S324 */ }
    part def TacticalPlan { doc /* @S463 */ }
    part def TacticalRegulationProposalReview { doc /* @S977 */ }
    part def TacticalRegulationProposalStatus { doc /* @S046 */ }
    part def TacticalRegulationProposalStatusValues { doc /* @S814 */ }
    part def TargetOffBlockTime { doc /* @S268,S314,S352,S376,S553 */ }
    part def TargetOffBlockTimeCommitments { doc /* @S976 */ }
    part def TargetOffBlockTimeValues { doc /* @S046 */ }
    part def TaxiQueues { doc /* @S367 */ }
    part def TechnicalConformanceDefects { doc /* @S898 */ }
    part def TechnicalPriorityCases { doc /* @S498 */ }
    part def TemporalSequenceChecks { doc /* @S826 */ }
    part def TemporaryAccess { doc /* @S782 */ }
    part def TemporaryRestrictedArea { doc /* @S327,S336 */ }
    part def TerminalAndEnRouteSectorLoads { doc /* @S402 */ }
    part def TerminalCurbSpace { doc /* @S548 */ }
    part def TimeAboveThreshold { doc /* @S846 */ }
    part def TimeOfLastAcceptedUpdate { doc /* @S823 */ }
    part def TimeSynchronizationService { doc /* @S034,S098,S110,S122,S149,S187,S256,S585,S651,S778,S792,S824,S890,S957 */ }
    part def Timestamps { doc /* @S422 */ }
    part def Tow { doc /* @S210 */ }
    part def TowbarAvailability { doc /* @S523 */ }
    part def TowerAndAirportDutyCoordination { doc /* @S174 */ }
    part def TowerCoordination { doc /* @S331 */ }
    part def TowerParticipants { doc /* @S372 */ }
    part def TowerPlanning { doc /* @S536 */ }
    part def TowerRoles { doc /* @S560 */ }
    part def TowerSequenceManager { doc /* @S017,S032,S089,S180,S217,S242,S254,S279,S283,S297,S334,S380,S411,S445,S450,S536,S552,S583,S693,S702,S703,S801,S844,S950,S980 */ }
    part def TowerSequenceWorkflow { doc /* @S298 */ }
    part def TowerSequencingFunction { doc /* @S275 */ }
    part def TowerSupervisor { doc /* @S011,S040,S060,S061,S066,S089,S121,S143,S160,S175,S176,S183,S189,S202,S218,S243,S263,S277,S280,S287,S296,S313,S345,S358,S368,S388,S401,S425,S475,S500,S605,S614,S655,S676,S693,S748,S766,S769,S817,S866,S893,S917,S959,S963 */ }
    part def TowerSupervisoryPersonnel { doc /* @S045 */ }
    part def TowerTeam { doc /* @S291 */ }
    part def TowerUsers { doc /* @S382 */ }
    part def TowingMovements { doc /* @S206 */ }
    part def TowingProviders { doc /* @S044 */ }
    part def TowingResources { doc /* @S212 */ }
    part def TrafficDemand { doc /* @S015 */ }
    part def TrainingAssessments { doc /* @S886 */ }
    part def TrainingForTheMeridianRegionalAirTrafficFlowManagementAndAirportCollaborativeDecisionMakingSystem { doc /* @S863 */ }
    part def TrajectoryPrediction { doc /* @S942 */ }
    part def TreatedAircraft { doc /* @S390 */ }
    part def Treatment { doc /* @S390 */ }
    part def TreatmentProgress { doc /* @S294 */ }
    part def TriggerConditions { doc /* @S087 */ }
    part def TugRouting { doc /* @S184 */ }
    part def TurnaroundEvent { doc /* @S156 */ }
    part def TurnaroundMilestone { doc /* @S571 */ }
    part def TurnaroundStatus { doc /* @S127 */ }
    part def UncontrolledParallelRecords { doc /* @S907 */ }
    part def UncontrolledPushback { doc /* @S453 */ }
    part def UncontrolledPushbackSurges { doc /* @S298 */ }
    part def UnevenAvailabilityOfGroundHandlingResources { doc /* @S007 */ }
    part def UnusualAccessPatterns { doc /* @S780 */ }
    part def UpdatedDepartureReadinessInformation { doc /* @S940 */ }
    part def UpstreamDelay { doc /* @S403 */ }
    part def UrgentDiscrepancies { doc /* @S834 */ }
    part def UseOfEmergencyAccess { doc /* @S785 */ }
    part def User { doc /* @S152,S781 */ }
    part def UserDecisions { doc /* @S793 */ }
    part def Users { doc /* @S120,S165,S272,S715,S883,S885,S886 */ }
    part def ValidationFailureRates { doc /* @S836 */ }
    part def ValidationRules { doc /* @S826 */ }
    part def ValidityIntervals { doc /* @S422 */ }
    part def VehicleAvailability { doc /* @S375 */ }
    part def Vehicles { doc /* @S548 */ }
    part def VisibilityReductions { doc /* @S409 */ }
    part def VisualConfirmation { doc /* @S645 */ }
    part def VisualState { doc /* @S823 */ }
    part def WalkingRoutes { doc /* @S563 */ }
    part def Waves { doc /* @S909 */ }
    part def Weather { doc /* @S041,S410 */ }
    part def WeatherCategory { doc /* @S431 */ }
    part def WeatherConstraints { doc /* @S967 */ }
    part def WeatherFeed { doc /* @S111 */ }
    part def WeatherIngestGateway { doc /* @S018,S033,S056,S057,S102,S108,S111,S182,S409,S434,S610,S819,S873,S943,S979 */ }
    part def WeatherRouting { doc /* @S858 */ }
    part def WestApronSensor { doc /* @S019,S035,S063,S115,S179,S205,S282,S474,S645,S845 */ }
    part def WetPavement { doc /* @S464 */ }
    part def Wind { doc /* @S661 */ }
    part def WindShifts { doc /* @S409 */ }
    part def WinterOperations { doc /* @S092 */ }
    part def Workflow { doc /* @S278 */ }
    part def WorkloadMonitoring { doc /* @S884 */ }
    part def WorkstationLayouts { doc /* @S885 */ }
    part system {
        part abnormalSystemIndications : AbnormalSystemIndications {
            perform action a0 { doc /* make continued flight or extended holding undesirable @S498 */ }
        }
        part acceptedAmendment : AcceptedAmendment {
            perform action a0 { doc /* replaces the prior value as the current shared plan @S266 */ }
        }
        part accessControl : AccessControl {
            perform action a0 { doc /* continue to enforce role separation @S786 */ }
        }
        part accessLimitations : AccessLimitations;
        part accessRoute : AccessRoute {
            exhibit state modes {
                state s0 { doc /* blocked @S656 */ }
            }
        }
        part accessibleBoardingSupport : AccessibleBoardingSupport;
        part accessibleTransferTimes : AccessibleTransferTimes {
            exhibit state modes {
                state s0 { doc /* less predictable @S563 */ }
            }
        }
        part accountableFlowRoles : AccountableFlowRoles {
            perform action a0 { doc /* confirm that decisions and unresolved issues are available to the Performance Analytics Warehouse for later inclusion in the Post Operations Report @S099 */ }
        }
        part accountableOperationalRole : AccountableOperationalRole {
            perform action a0 { doc /* record the proposed mitigation in the Collaborative Decision Log @S531 */ }
        }
        part accountableParticipant : AccountableParticipant {
            perform action a0 { doc /* enter a provisional value with an uncertainty flag @S168 */ }
            perform action a1 { doc /* leaving the milestone unchanged @S168 */ }
        }
        part accountableParty : AccountableParty {
            perform action a0 { doc /* is still working the same recovery action @S522 */ }
        }
        part activePadConfiguration : ActivePadConfiguration;
        part activeSurfaceAdvisories : ActiveSurfaceAdvisories {
            perform action a0 { doc /* carry higher planning weight @S464 */ }
        }
        part actorResponsibleForTheTurnaround : ActorResponsibleForTheTurnaround {
            perform action a0 { doc /* confirms that the boarding, servicing, and ramp movement assumptions are achievable @S482 */ }
        }
        part actualMovementMilestones : ActualMovementMilestones {
            perform action a0 { doc /* support independent verification of slot performance @S801 */ }
        }
        part actualTakeoffOrOffBlockEvent : ActualTakeoffOrOffBlockEvent {
            perform action a0 { doc /* occurs inside the operating window defined in the Business Rules Registry @S849 */ }
        }
        part additionalGroundHandlingResources : AdditionalGroundHandlingResources {
            perform action a0 { doc /* can remove the constraint @S460 */ }
        }
        part advancedTurnaroundPrediction : AdvancedTurnaroundPrediction {
            perform action a0 { doc /* combine aircraft state, handling milestones, stand occupancy, crew readiness, passenger processing, and ramp congestion signals @S946 */ }
        }
        part adverseWeatherMode : AdverseWeatherMode {
            perform action a0 { doc /* drive stakeholder participation and operating procedures @S047 */ }
        }
        part advisory : Advisory {
            perform action a0 { doc /* would impair safe separation, wake spacing, or local controller workload @S748 */ }
        }
        part advisoryUseOfPassengerDisruptionData : AdvisoryUseOfPassengerDisruptionData {
            perform action a0 { doc /* improved recovery performance @S760 */ }
        }
        part aerodromeInfrastructureEvents : AerodromeInfrastructureEvents {
            perform action a0 { doc /* affect runway availability, taxi route usability, stand access, lighting performance, or supporting navigation services @S690 */ }
            perform action a1 { doc /* reduces arrival throughput @S698 */ }
            perform action a2 { doc /* reduces departure throughput @S699 */ }
            perform action a3 { doc /* require approval @S706 */ }
            perform action a4 { doc /* automatically trigger a Capacity Reduction State @S706 */ }
        }
        part affectedFlight : AffectedFlight {
            perform action a0 { doc /* keep its Target Off Block Time @S451 */ }
            perform action a1 { doc /* request a new value @S451 */ }
            perform action a2 { doc /* accept a later Calculated Takeoff Time @S451 */ }
        }
        part affectedOperationalRoles : AffectedOperationalRoles;
        part affectedResource : AffectedResource {
            exhibit state modes {
                state s0 { doc /* Normal Operations @S713 */ }
                state s1 { doc /* Recovery Phase @S713 */ }
            }
        }
        part affectedRoute : AffectedRoute;
        part aggregatedMetrics : AggregatedMetrics {
            perform action a0 { doc /* support review of systemic lateness without exposing commercially sensitive detail beyond authorized roles @S805 */ }
            perform action a1 { doc /* exposing commercially sensitive detail beyond authorized roles @S805 */ }
        }
        part agreedDepartureWindow : AgreedDepartureWindow {
            exhibit state modes {
                state s0 { doc /* frozen @S428 */ }
            }
        }
        part agreedOperationalWorkaround : AgreedOperationalWorkaround {
            exhibit state modes {
                state s0 { doc /* in place @S920 */ }
            }
        }
        part airNavigationServiceParticipation : AirNavigationServiceParticipation;
        part airTrafficControllers : AirTrafficControllers {
            perform action a0 { doc /* understand how flow measures, sequencing changes, and calculated times affect sector workload, runway demand, and controller tactical flexibility @S865 */ }
        }
        part airborneDelay : AirborneDelay {
            perform action a0 { doc /* has already accumulated @S407 */ }
        }
        part aircraft : Aircraft {
            perform action a0 { doc /* cannot meet readiness criteria @S236 */ }
            perform action a1 { doc /* can use the opportunity @S236 */ }
            perform action a2 { doc /* entering the movement area @S281 */ }
            perform action a3 { doc /* holding short @S281 */ }
            perform action a4 { doc /* cannot meet a feasible off-block time unless the required people, vehicles, and stand equipment are available at the stand before boarding closure @S299 */ }
            perform action a5 { doc /* remain blocked on stand @S305 */ }
            perform action a6 { doc /* begin taxi @S347 */ }
            perform action a7 { doc /* enter the taxi stream @S348 */ }
            perform action a8 { doc /* can remain connected to normal operator processes @S353 */ }
            perform action a9 { doc /* holding at the gate @S353 */ }
            perform action a10 { doc /* waiting at runway holding points @S360 */ }
            perform action a11 { doc /* can absorb the assigned delay at stand @S362 */ }
            perform action a12 { doc /* compromising crew, passenger, or turnaround constraints @S362 */ }
            perform action a13 { doc /* continued stand holding @S364 */ }
            perform action a14 { doc /* taxi to pad @S377 */ }
            perform action a15 { doc /* awaiting release @S377 */ }
            perform action a16 { doc /* returning to stand @S377 */ }
            perform action a17 { doc /* leaves the treated area @S387 */ }
            perform action a18 { doc /* leaving the pad @S389 */ }
            perform action a19 { doc /* follow the assigned route @S389 */ }
            perform action a20 { doc /* do not block inbound traffic to the same treatment complex @S389 */ }
            perform action a21 { doc /* can accept a revised stand assignment @S476 */ }
            perform action a22 { doc /* disrupting maintenance release, fueling sequence, boarding control, or cabin readiness @S476 */ }
            perform action a23 { doc /* do not create a new surface queue at the runway holding points @S483 */ }
            perform action a24 { doc /* can remain on plan @S521 */ }
            perform action a25 { doc /* accept a short readiness deferral @S521 */ }
            perform action a26 { doc /* require a revised departure intent @S521 */ }
            perform action a27 { doc /* must wait clear of the terminal pier @S542 */ }
            perform action a28 { doc /* would cause less overall delay than a nominally available remote stand with inadequate passenger transfer capacity @S558 */ }
            exhibit state modes {
                state s0 { doc /* at stand @S281 */ }
                state s1 { doc /* awaiting release @S377 */ }
                state s2 { doc /* blocked on stand @S305 */ }
                state s3 { doc /* committed to the departure stream @S281 */ }
                state s4 { doc /* entering the movement area @S281 */ }
                state s5 { doc /* holding short @S281 */ }
                state s6 { doc /* in treatment @S377 */ }
                state s7 { doc /* pending push @S377 */ }
                state s8 { doc /* ready @S320 */ }
                state s9 { doc /* returning to stand @S377 */ }
                state s10 { doc /* taxi to pad @S377 */ }
            }
        }
        part aircraftCondition : AircraftCondition {
            perform action a0 { doc /* could affect rescue and firefighting readiness at Meridian or at an alternate airport @S414 */ }
        }
        part aircraftOperatorRepresentative : AircraftOperatorRepresentative {
            perform action a0 { doc /* require a common basis for decisions rather than separate local views of the same operational picture @S011 */ }
            perform action a1 { doc /* participate @S039 */ }
            perform action a2 { doc /* align airline intentions, schedule constraints, and slot management decisions with the shared plan @S039 */ }
            perform action a3 { doc /* validates that operator priorities are visible where they are allowed by the Business Rules Registry and local coordination agreements @S055 */ }
            perform action a4 { doc /* provides aircraft-specific constraints when requested @S082 */ }
            perform action a5 { doc /* ensuring that operator commitments entered in the Airport CDM Portal are operationally achievable @S082 */ }
            perform action a6 { doc /* keeping aircraft readiness information current enough for the tower team to trust the displayed status @S291 */ }
            perform action a7 { doc /* declare whether the operator can accept a later off-block time without causing crew, connection, or aircraft rotation impacts @S316 */ }
            perform action a8 { doc /* requests reconsideration through the Airport CDM Portal @S363 */ }
            perform action a9 { doc /* review proposed timing changes in the same timeline used by flow staff @S437 */ }
            perform action a10 { doc /* confirms whether the aircraft can accept a revised stand assignment without disrupting maintenance release, fueling sequence, boarding control, or cabin readiness @S476 */ }
            perform action a11 { doc /* sends the Crew Duty Extension Log @S620 */ }
            perform action a12 { doc /* identifies a flight that can exchange its assigned demand position without reducing declared capacity or creating an unfair priority change @S666 */ }
            perform action a13 { doc /* records concurrence in the Airport CDM Portal @S673 */ }
            perform action a14 { doc /* relying on a verbal agreement @S673 */ }
            perform action a15 { doc /* acknowledge manual slot assignments through recorded voice readback or an agreed written channel @S725 */ }
            perform action a16 { doc /* may view airline-relevant planning data @S771 */ }
            perform action a17 { doc /* submit coordination inputs @S771 */ }
            perform action a18 { doc /* without receiving administrative access to system configuration @S771 */ }
            perform action a19 { doc /* proposes a substitution @S797 */ }
            perform action a20 { doc /* be able to challenge cancellation avoidance results through the Collaborative Decision Log @S854 */ }
            perform action a21 { doc /* submit, review, and update Flight Intent Message data through approved interfaces @S868 */ }
            perform action a22 { doc /* assess the operational effect of Calculated Takeoff Time and Target Off Block Time changes @S868 */ }
            perform action a23 { doc /* have named accountable implementation contacts @S893 */ }
            perform action a24 { doc /* providing operationally realistic airline intentions @S965 */ }
            perform action a25 { doc /* honoring agreed times @S965 */ }
        }
        part aircraftRegistration : AircraftRegistration;
        part aircraftServiceability : AircraftServiceability {
            exhibit state modes {
                state s0 { doc /* complete @S449 */ }
            }
        }
        part aircraftSwap : AircraftSwap {
            exhibit state modes {
                state s0 { doc /* feasible @S618 */ }
            }
        }
        part aircraftTurnPerformance : AircraftTurnPerformance {
            perform action a0 { doc /* reduce stand availability @S065 */ }
        }
        part airline : Airline {
            perform action a0 { doc /* proposes a retime, cancellation, aircraft substitution, or route change @S139 */ }
            perform action a1 { doc /* submits an updated Flight Intent Message @S139 */ }
            perform action a2 { doc /* relying on manual annotations @S139 */ }
            perform action a3 { doc /* indicates a recovery plan that depends on unrealistic turnaround timing @S754 */ }
        }
        part airlineInterfaceAdapter : AirlineInterfaceAdapter {
            perform action a0 { doc /* provide the data feeds needed to maintain a current and consistent operational picture @S018 */ }
            perform action a1 { doc /* provide managed integration points with external systems @S033 */ }
            perform action a2 { doc /* held by the Airline Interface Adapter @S103 */ }
            perform action a3 { doc /* validates message structure @S128 */ }
            perform action a4 { doc /* maps carrier codes to the Business Rules Registry @S128 */ }
            perform action a5 { doc /* forwards accepted intent data to the Flight Data Exchange @S128 */ }
            perform action a6 { doc /* supplies operator preferences @S235 */ }
            perform action a7 { doc /* produces the Late Baggage Tag List @S452 */ }
            perform action a8 { doc /* maintains airline-provided connection exposure, including protected passengers, minimum connection time pressure, and groups that require assisted transfer @S478 */ }
            perform action a9 { doc /* accepts legality indicators that describe whether a proposed departure, arrival, or aircraft swap remains feasible within declared crew duty limits @S618 */ }
            perform action a10 { doc /* validates the timeliness, flight association, and airline ownership of connection-risk data @S741 */ }
            perform action a11 { doc /* apply carrier-specific format checks @S829 */ }
            perform action a12 { doc /* preserving the common operational meaning required by the Regional Flow Platform @S829 */ }
            perform action a13 { doc /* provide the main operational inputs for this capability @S947 */ }
        }
        part airlineOperationsCentre : AirlineOperationsCentre {
            perform action a0 { doc /* submits a Flight Intent Message through the Airline Interface Adapter using an authenticated system account managed by the Identity Access Service @S126 */ }
            perform action a1 { doc /* using an authenticated system account managed by the Identity Access Service @S126 */ }
        }
        part airlineOperationsCentreIntegration : AirlineOperationsCentreIntegration {
            perform action a0 { doc /* provides the operational bridge between carrier recovery planning and the Meridian Regional Air Traffic Flow Management and Airport Collaborative Decision-Making System @S124 */ }
        }
        part airlineOperationsCentres : AirlineOperationsCentres {
            perform action a0 { doc /* receive those constraints through the Airline Interface Adapter @S135 */ }
            perform action a1 { doc /* may also view them in the Airport CDM Portal @S135 */ }
            perform action a2 { doc /* submit conservative intents that distinguish firm operating plans from speculative recovery options @S146 */ }
        }
        part airlineOperationsCoordinator : AirlineOperationsCoordinator {
            perform action a0 { doc /* require a common basis for decisions rather than separate local views of the same operational picture @S011 */ }
            perform action a1 { doc /* participate @S039 */ }
            perform action a2 { doc /* align airline intentions, schedule constraints, and slot management decisions with the shared plan @S039 */ }
            perform action a3 { doc /* reviews material deviations from filed intent, including aircraft swaps, early cancellations, recovery flights, and known connection protection actions @S054 */ }
            perform action a4 { doc /* represents carrier operating priorities @S081 */ }
            perform action a5 { doc /* confirms that Flight Intent Message updates are complete, timely, and traceable @S081 */ }
            perform action a6 { doc /* can correct them without informal voice coordination @S129 */ }
            perform action a7 { doc /* evaluates each constraint against crew legality, aircraft rotation continuity, maintenance positioning, and passenger recovery commitments @S138 */ }
            perform action a8 { doc /* keeping the Flight Intent Message status, Target Off Block Time, passenger readiness indicator, and aircraft operational constraint notes current for each represented flight @S157 */ }
            perform action a9 { doc /* uses the delay slip @S237 */ }
            perform action a10 { doc /* requesting an exemption review for a crew connectivity constraint that is not already represented in the allocation data @S237 */ }
            perform action a11 { doc /* reviews the proposed Target Off Block Time against aircraft readiness, crew availability, passenger connection risk, and operator recovery priorities @S259 */ }
            perform action a12 { doc /* confirm any operator-requested Target Off Block Time revision in the Airport CDM Portal @S260 */ }
            perform action a13 { doc /* may request a sequence review @S284 */ }
            perform action a14 { doc /* uses the same information @S317 */ }
            perform action a15 { doc /* decide whether a swap between company flights is operationally meaningful or merely transfers a handling bottleneck to another stand @S317 */ }
            perform action a16 { doc /* uses the shared display @S338 */ }
            perform action a17 { doc /* identify flights that may need rerouting, delayed pushback planning, or revised operator intent @S338 */ }
            perform action a18 { doc /* confirms whether each affected aircraft can absorb the assigned delay at stand without compromising crew, passenger, or turnaround constraints @S362 */ }
            perform action a19 { doc /* reviews aircraft readiness @S385 */ }
            perform action a20 { doc /* may request a later pad entry @S385 */ }
            perform action a21 { doc /* reviews the proposed treatment for network impact @S403 */ }
            perform action a22 { doc /* identifies flights where upstream delay would create a disproportionate connection or aircraft rotation penalty @S403 */ }
            perform action a23 { doc /* review proposed timing changes in the same timeline used by flow staff @S437 */ }
            perform action a24 { doc /* confirming whether the affected flight should keep its Target Off Block Time, request a new value, or accept a later Calculated Takeoff Time @S451 */ }
            perform action a25 { doc /* uses the Gate Reopening Memo @S472 */ }
            perform action a26 { doc /* confirm when a previously unavailable gate can be planned again for arrival handling, boarding, and connection recovery @S472 */ }
            perform action a27 { doc /* supplies passenger, crew, maintenance, and aircraft rotation impacts @S507 */ }
            perform action a28 { doc /* confirms whether the aircraft can remain on plan, accept a short readiness deferral, or require a revised departure intent @S521 */ }
            perform action a29 { doc /* uses remote stands @S546 */ }
            perform action a30 { doc /* protect connection banks @S546 */ }
            perform action a31 { doc /* may request revision of the Target Off Block Time before the delay propagates to runway demand @S554 */ }
            perform action a32 { doc /* uses customs hold visibility to adjust connection protection, passenger messaging assumptions, and expected aircraft turnaround timing @S574 */ }
            perform action a33 { doc /* adjust connection protection, passenger messaging assumptions, and expected aircraft turnaround timing @S574 */ }
            perform action a34 { doc /* reviews the airport-level result @S604 */ }
            perform action a35 { doc /* determine whether flight swaps, cancellations, or recovery plans are needed inside the airline schedule @S604 */ }
            perform action a36 { doc /* may mark a flight as non-recoverable by delay after a specified time @S623 */ }
            perform action a37 { doc /* may propose a revised Target Off Block Time @S658 */ }
            perform action a38 { doc /* enters the proposed substitution in the Airport CDM Portal with the flight identifiers, operational reason, readiness basis, and requested effective time @S667 */ }
            perform action a39 { doc /* uses the release note @S679 */ }
            perform action a40 { doc /* confirm that a candidate substitution is eligible for customs release @S679 */ }
            perform action a41 { doc /* requesting a slot swap @S679 */ }
            perform action a42 { doc /* acknowledge manual slot assignments through recorded voice readback or an agreed written channel @S725 */ }
            perform action a43 { doc /* sends the Passenger Misconnect Count @S740 */ }
            perform action a44 { doc /* receive role profiles that reflect their normal operational responsibilities @S766 */ }
            perform action a45 { doc /* may view airline-relevant planning data @S771 */ }
            perform action a46 { doc /* submit coordination inputs @S771 */ }
            perform action a47 { doc /* without receiving administrative access to system configuration @S771 */ }
            perform action a48 { doc /* uses the permission email @S795 */ }
            perform action a49 { doc /* justify an approved slot substitution during post-operations review @S795 */ }
            perform action a50 { doc /* be accountable for airline-supplied schedule intent, readiness status, and Target Off Block Time updates submitted through approved interfaces @S820 */ }
            perform action a51 { doc /* be able to challenge cancellation avoidance results through the Collaborative Decision Log @S854 */ }
            perform action a52 { doc /* submit, review, and update Flight Intent Message data through approved interfaces @S868 */ }
            perform action a53 { doc /* assess the operational effect of Calculated Takeoff Time and Target Off Block Time changes @S868 */ }
            perform action a54 { doc /* have named accountable implementation contacts @S893 */ }
            perform action a55 { doc /* compare recommendations with actual outcomes @S959 */ }
            perform action a56 { doc /* providing operationally realistic airline intentions @S965 */ }
            perform action a57 { doc /* honoring agreed times @S965 */ }
        }
        part airlineParticipants : AirlineParticipants {
            perform action a0 { doc /* share one operational assumption @S372 */ }
        }
        part airlineRecoveryActions : AirlineRecoveryActions {
            perform action a0 { doc /* change the expected departure order @S143 */ }
        }
        part airlineRecoveryInformation : AirlineRecoveryInformation {
            perform action a0 { doc /* inform proportionate metering choices @S761 */ }
        }
        part airlineRoles : AirlineRoles {
            perform action a0 { doc /* share the same expectation for aircraft readiness @S560 */ }
        }
        part airlineUsers : AirlineUsers {
            perform action a0 { doc /* interpret treatment age consistently @S382 */ }
        }
        part airlines : Airlines {
            perform action a0 { doc /* participating in the initial operating concept @S043 */ }
        }
        part airport : Airport {
            perform action a0 { doc /* exchange operational data @S890 */ }
        }
        part airportAcceptanceRate : AirportAcceptanceRate {
            perform action a0 { doc /* remains feasible @S107 */ }
        }
        part airportAcceptanceRateChanges : AirportAcceptanceRateChanges;
        part airportAcceptanceRateConstraints : AirportAcceptanceRateConstraints;
        part airportAcceptanceRateValues : AirportAcceptanceRateValues;
        part airportAndAirlineUsers : AirportAndAirlineUsers {
            perform action a0 { doc /* used by airport and airline users @S469 */ }
        }
        part airportAuthority : AirportAuthority {
            perform action a0 { doc /* confirms the operational effect @S188 */ }
        }
        part airportCDMPortal : AirportCDMPortal {
            perform action a0 { doc /* provides airport stakeholders with a controlled interface for sharing operational readiness information and confirming decisions that affect the surface and terminal sequence @S016 */ }
            perform action a1 { doc /* support planning and collaborative assessment @S031 */ }
            perform action a2 { doc /* provides the shared operational workspace @S150 */ }
            perform action a3 { doc /* highlight the affected flight @S166 */ }
            perform action a4 { doc /* notify the role accountable for the next update through the Alert Distribution Hub @S166 */ }
            perform action a5 { doc /* used by the Airport CDM Portal @S170 */ }
            perform action a6 { doc /* preserve the last synchronized milestone set @S172 */ }
            perform action a7 { doc /* clearly mark any updates entered under degraded operating procedures @S172 */ }
            perform action a8 { doc /* records duty desk confirmations as operational annotations linked to the relevant runway, taxiway, apron, or stand area @S185 */ }
            perform action a9 { doc /* presents each proposed value with its confidence status, last update time, and the reason code assigned by the proposing function or authorized user @S264 */ }
            perform action a10 { doc /* requires a revised reason code @S270 */ }
            perform action a11 { doc /* marks the earlier value as superseded rather than deleted @S270 */ }
            perform action a12 { doc /* publish tower readiness changes to authenticated airline and handling users within the configured refresh interval @S293 */ }
            perform action a13 { doc /* presents the resource-driven feasibility status to the Airline Operations Coordinator and the Aircraft Operator Representative @S312 */ }
            perform action a14 { doc /* support early negotiation rather than last-minute rejection @S312 */ }
            perform action a15 { doc /* displays the active restriction status, expected operational effect, and any related coordination notes on the Common Situation Display @S337 */ }
            perform action a16 { doc /* records the selected fluid type, mixture ratio, treatment start time, treatment completion time, and expected holdover reference for each treated aircraft @S381 */ }
            perform action a17 { doc /* presents the resulting arrival plan to Aircraft Operator Representative users @S405 */ }
            perform action a18 { doc /* records acknowledgements in the Collaborative Decision Log @S405 */ }
            perform action a19 { doc /* exposes agreed Target Off Block Time values and stakeholder remarks to the tactical position in read-only mode unless the operator has an assigned coordination role @S429 */ }
            perform action a20 { doc /* presents each gate conflict with the affected flights, passenger connection exposure, aircraft size compatibility, and the latest feasible off-block time @S470 */ }
            perform action a21 { doc /* shows downstream departure-fix pressure as contextual information for gate recovery decisions @S485 */ }
            perform action a22 { doc /* without allowing the stand plan to override accepted airspace constraints @S485 */ }
            perform action a23 { doc /* uses the window token @S503 */ }
            perform action a24 { doc /* preserve the agreed pushback opportunity @S503 */ }
            perform action a25 { doc /* keeps detailed handler notes available to authorized users @S527 */ }
            perform action a26 { doc /* prompts the accountable role to record the proposed mitigation in the Collaborative Decision Log @S531 */ }
            perform action a27 { doc /* records the operational reason, affected flights, expected passenger transfer duration, and responsible control position @S559 */ }
            perform action a28 { doc /* displays border and customs status in a controlled view @S572 */ }
            perform action a29 { doc /* uses the shuttle count @S648 */ }
            perform action a30 { doc /* confirm that remote-stand passenger transfer demand is consistent with stand readiness timing @S648 */ }
            perform action a31 { doc /* records each stand readiness confirmation with the stand identifier, responsible organization, inspection time, readiness constraint, and confirming user identity @S649 */ }
            perform action a32 { doc /* validates the submitting user through the Identity Access Service @S668 */ }
            perform action a33 { doc /* blocks any proposal from a party without delegated operator authority @S668 */ }
            perform action a34 { doc /* keeps the proposal pending @S681 */ }
            perform action a35 { doc /* prevents the Slot Allocation Engine from publishing the revised slot assignment @S681 */ }
            perform action a36 { doc /* presents infrastructure events to authorized airport, airline, and flow management users as part of the shared operating picture @S695 */ }
            perform action a37 { doc /* becomes unavailable @S720 */ }
            perform action a38 { doc /* provide the main operational inputs for this capability @S947 */ }
            exhibit state modes {
                state s0 { doc /* read-only mode @S429 */ }
                state s1 { doc /* unavailable @S195 */ }
            }
        }
        part airportCapacityDeclarations : AirportCapacityDeclarations;
        part airportCapacityPlan : AirportCapacityPlan;
        part airportCapacityPlanAssumptions : AirportCapacityPlanAssumptions;
        part airportCapacityPlanRecords : AirportCapacityPlanRecords;
        part airportCommunity : AirportCommunity;
        part airportContinuity : AirportContinuity {
            perform action a0 { doc /* requires immediate action @S784 */ }
        }
        part airportDutyDesk : AirportDutyDesk {
            perform action a0 { doc /* reviews tower inputs, airport operations reports, and surveillance indications @S178 */ }
            perform action a1 { doc /* confirming whether a local condition should be reflected in the Airport Capacity Plan @S178 */ }
        }
        part airportDutyManager : AirportDutyManager {
            perform action a0 { doc /* require a common basis for decisions rather than separate local views of the same operational picture @S011 */ }
            perform action a1 { doc /* participate @S040 */ }
            perform action a2 { doc /* represent local airport, tower, ramp, handling, and winter operations considerations @S040 */ }
            perform action a3 { doc /* confirms terminal opening status, essential facility readiness, and airport service constraints that may affect the first operational waves @S062 */ }
            perform action a4 { doc /* confirms that airport-side constraints are reflected consistently across the Airport CDM Portal and the Common Situation Display @S088 */ }
            perform action a5 { doc /* may request a manual capacity review @S116 */ }
            perform action a6 { doc /* monitors the Common Situation Display @S144 */ }
            perform action a7 { doc /* ensure airline recovery decisions remain consistent with terminal capacity and passenger processing conditions @S144 */ }
            perform action a8 { doc /* maintaining the Airport Capacity Plan @S162 */ }
            perform action a9 { doc /* declaring local operating impacts @S162 */ }
            perform action a10 { doc /* confirming transitions between Normal Operations, Adverse Weather Mode, Capacity Reduction State, and Recovery Phase @S162 */ }
            perform action a11 { doc /* maintains the airport duty desk as the single operational point for airport status confirmation during Normal Operations, Adverse Weather Mode, Capacity Reduction State, and Recovery Phase @S177 */ }
            perform action a12 { doc /* uses the Runway Inspection Note @S181 */ }
            perform action a13 { doc /* confirm that the duty desk has a current record of pavement status @S181 */ }
            perform action a14 { doc /* endorsing any declared capacity change @S181 */ }
            perform action a15 { doc /* agree on the operational interpretation @S183 */ }
            perform action a16 { doc /* verifies that airfield operations checks have been completed @S190 */ }
            perform action a17 { doc /* requesting changes to Airport Acceptance Rate values or departure metering assumptions @S190 */ }
            perform action a18 { doc /* briefs open safety checks, unresolved surveillance discrepancies, and any tower coordination points that remain active @S196 */ }
            perform action a19 { doc /* confirm the active interpretation of the restriction @S345 */ }
            perform action a20 { doc /* agree whether the metering horizon should be extended so that delay is absorbed before pushback rather than near the runway @S368 */ }
            perform action a21 { doc /* can declare Normal Operations, Adverse Weather Mode, Capacity Reduction State, Recovery Phase, or Contingency Fallback State from the tactical header @S435 */ }
            perform action a22 { doc /* records the operational significance of the condition in the Airport CDM Portal @S447 */ }
            perform action a23 { doc /* sets the recovery priority for stands that can be reopened quickly @S471 */ }
            perform action a24 { doc /* giving preference to positions that remove multiple downstream conflicts rather than a single isolated delay @S471 */ }
            perform action a25 { doc /* sends the Medical Diversion Notice @S496 */ }
            perform action a26 { doc /* publishes the planned remote stand operating posture in the Airport CDM Portal before the first affected arrival bank @S544 */ }
            perform action a27 { doc /* may reduce planned remote stand use @S563 */ }
            perform action a28 { doc /* produces the Customs Hold Release Note when border processing confirms that a held arrival may proceed to normal turnaround handling @S568 */ }
            perform action a29 { doc /* can declare a localized Capacity Reduction State @S660 */ }
            perform action a30 { doc /* uses the Apron Sweep Completion Note @S678 */ }
            perform action a31 { doc /* confirm that apron availability constraints do not invalidate an approved substitution @S678 */ }
            perform action a32 { doc /* ensuring that declared service reductions are entered promptly and that the operational description is consistent with local aerodrome control procedures @S692 */ }
            perform action a33 { doc /* confirms closure in the Airport CDM Portal @S713 */ }
            perform action a34 { doc /* declaring the Contingency Fallback State after consultation with the Regional Flow Manager, Tower Supervisor, and System Support Engineer @S716 */ }
            perform action a35 { doc /* conducts fallback briefings at intervals appropriate to the traffic level @S734 */ }
            perform action a36 { doc /* publishes the current operating basis through the Digital Briefing Room @S734 */ }
            perform action a37 { doc /* uses the Airport CDM Portal @S750 */ }
            perform action a38 { doc /* see whether airline recovery actions are concentrated in one bank or distributed across the operating day @S750 */ }
            perform action a39 { doc /* review late airport-driven changes that affected multiple flights @S809 */ }
            perform action a40 { doc /* record whether the operational justification was valid @S809 */ }
            perform action a41 { doc /* own airport capacity declarations, including Airport Capacity Plan records and Airport Acceptance Rate values @S816 */ }
            perform action a42 { doc /* receive benefit summaries that show changes in stand occupancy, surface congestion, recovery duration, and passenger-facing disruption indicators @S860 */ }
            perform action a43 { doc /* recognize when an Airport Capacity Plan requires revision and when the operational state should move from Normal Operations to Adverse Weather Mode or Capacity Reduction State @S872 */ }
            perform action a44 { doc /* have named accountable implementation contacts @S893 */ }
            perform action a45 { doc /* retain operational command authority during support activity @S917 */ }
            perform action a46 { doc /* compare recommendations with actual outcomes @S959 */ }
            perform action a47 { doc /* confirm capacity assumptions used for airport-level coordination @S962 */ }
        }
        part airportDutyManagerHandover : AirportDutyManagerHandover {
            perform action a0 { doc /* has identified active surface constraints @S198 */ }
        }
        part airportLevelConstraintProcess : AirportLevelConstraintProcess {
            perform action a0 { doc /* starts by translating en-route demand indicators into rates, time windows, and advisories that can be understood by local operations teams @S591 */ }
            perform action a1 { doc /* translating en-route demand indicators into rates, time windows, and advisories @S591 */ }
        }
        part airportMeasures : AirportMeasures {
            perform action a0 { doc /* reflect both sector capacity and route availability @S610 */ }
        }
        part airportNetwork : AirportNetwork {
            perform action a0 { doc /* routinely operates near declared capacity during Normal Operations @S003 */ }
            perform action a1 { doc /* leaving limited margin for runway configuration changes, surface congestion, or short-notice airspace constraints @S003 */ }
            exhibit state modes {
                state s0 { doc /* Normal Operations @S003 */ }
            }
        }
        part airportOnboarding : AirportOnboarding {
            perform action a0 { doc /* shall start with data discovery workshops @S902 */ }
        }
        part airportOperator : AirportOperator {
            perform action a0 { doc /* agreed by the airport operator, regional authority, and participating aircraft operators @S779 */ }
        }
        part airportParticipant : AirportParticipant {
            perform action a0 { doc /* update a material change within two minutes of becoming aware of it during Normal Operations and within one minute during Adverse Weather Mode or Capacity Reduction State @S167 */ }
            perform action a1 { doc /* becoming aware of it @S167 */ }
        }
        part airportParticipants : AirportParticipants {
            perform action a0 { doc /* maintain a common view of departure readiness, arrival constraints, surface conditions, and slot impacts @S150 */ }
            perform action a1 { doc /* share one operational assumption @S372 */ }
        }
        part airportRoles : AirportRoles {
            perform action a0 { doc /* share the same expectation for aircraft readiness @S560 */ }
        }
        part airportServiceConstraints : AirportServiceConstraints {
            perform action a0 { doc /* may affect the first operational waves @S062 */ }
        }
        part airportStakeholders : AirportStakeholders {
            perform action a0 { doc /* sharing operational readiness information @S016 */ }
            perform action a1 { doc /* confirming decisions that affect the surface and terminal sequence @S016 */ }
        }
        part airspaceAlerts : AirspaceAlerts {
            perform action a0 { doc /* reaches the correct operational positions without requiring manual redistribution @S332 */ }
        }
        part airspaceConstraints : AirspaceConstraints {
            perform action a0 { doc /* may affect regional capacity @S967 */ }
        }
        part airspacePlanningPersonnel : AirspacePlanningPersonnel;
        part airspaceRestrictions : AirspaceRestrictions {
            perform action a0 { doc /* changes the usable departure routes or expected release spacing @S334 */ }
            perform action a1 { doc /* compounds an existing runway, sector, or surface constraint @S344 */ }
        }
        part airspaceSectorPlanner : AirspaceSectorPlanner {
            perform action a0 { doc /* participate @S041 */ }
            perform action a1 { doc /* declares expected sector constraints, route availability assumptions, and any planned staffing limitations that could influence arrival or departure metering @S058 */ }
            perform action a2 { doc /* supports the Regional Flow Manager @S079 */ }
            perform action a3 { doc /* validating sector constraints in the Sector Load Monitor @S079 */ }
            perform action a4 { doc /* advising whether demand smoothing is required before tactical execution @S079 */ }
            perform action a5 { doc /* converts confirmed restricted area information into sector availability assumptions @S326 */ }
            perform action a6 { doc /* checks whether existing flight plans require rerouting, metering, or ground delay action @S326 */ }
            perform action a7 { doc /* confirm the active interpretation of the restriction @S345 */ }
            perform action a8 { doc /* confirms whether terminal and en-route sector loads can absorb the regulated stream without generating unsafe compression @S402 */ }
            perform action a9 { doc /* monitors sector demand through the Sector Load Monitor @S432 */ }
            perform action a10 { doc /* confirms whether proposed measures are compatible with en route capacity @S432 */ }
            perform action a11 { doc /* protects sector margins @S501 */ }
            perform action a12 { doc /* may request a Tactical Regulation Proposal @S501 */ }
            perform action a13 { doc /* validates the operational meaning of each constraint @S608 */ }
            perform action a14 { doc /* coordinate regional constraints, sector load conditions, and network measures @S871 */ }
            perform action a15 { doc /* using the Sector Load Monitor and Common Situation Display @S871 */ }
        }
        part airspaceStructure : AirspaceStructure {
            perform action a0 { doc /* affect available capacity @S041 */ }
        }
        part alertDistributionHub : AlertDistributionHub {
            perform action a0 { doc /* provide managed integration points with external systems @S033 */ }
            perform action a1 { doc /* notifies participating roles that the morning plan is available and that changes must be entered through controlled Regional Flow Platform functions @S073 */ }
            perform action a2 { doc /* notifies the Regional Flow Manager, Tower Supervisor, and Airline Operations Coordinator that the capacity picture may change @S121 */ }
            perform action a3 { doc /* distributes approved duty coordination alerts to affected operational roles @S193 */ }
            perform action a4 { doc /* applies subscription rules from the Business Rules Registry @S332 */ }
            perform action a5 { doc /* highlights the affected runway queue on the Common Situation Display @S366 */ }
            perform action a6 { doc /* must distribute surface equipment and apron congestion advisories to subscribed operational roles within the latency target defined in the Business Rules Registry @S461 */ }
            perform action a7 { doc /* provides role-specific alert summaries @S505 */ }
            perform action a8 { doc /* routes notifications according to severity, time to milestone, and subscribed operational role @S529 */ }
            perform action a9 { doc /* broadcasting every exception to all users @S529 */ }
            perform action a10 { doc /* issues targeted alerts @S588 */ }
            perform action a11 { doc /* sends notifications to Regional Flow Manager, Tower Supervisor, Ramp Control Lead, Slot Coordinator, and Network Operations Liaison @S614 */ }
            perform action a12 { doc /* sends notifications @S705 */ }
            perform action a13 { doc /* cannot deliver mandatory operational advisories to the required participants within the agreed operational tolerance @S731 */ }
        }
        part allocationPart : Allocation {
            perform action a0 { doc /* would create avoidable delay or unfair sequencing @S258 */ }
        }
        part approvalLatency : ApprovalLatency;
        part approvedCompanyProcess : ApprovedCompanyProcess {
            perform action a0 { doc /* extends duty availability for a specific rotation @S620 */ }
        }
        part approvedInterfaces : ApprovedInterfaces;
        part approvedSources : ApprovedSources;
        part approvedSubstitution : ApprovedSubstitution {
            exhibit state modes {
                state s0 { doc /* final @S684 */ }
                state s1 { doc /* time synchronized @S684 */ }
            }
        }
        part approvingAuthority : ApprovingAuthority;
        part apronAvailabilityConstraints : ApronAvailabilityConstraints {
            perform action a0 { doc /* do not invalidate an approved substitution @S678 */ }
        }
        part apronCleaning : ApronCleaning {
            perform action a0 { doc /* delay the planned turnaround @S658 */ }
        }
        part apronCongestion : ApronCongestion {
            perform action a0 { doc /* begins to affect runway delivery @S218 */ }
        }
        part apronContamination : ApronContamination {
            perform action a0 { doc /* materially reduce usable gate capacity @S660 */ }
        }
        part apronDrivingSpeeds : ApronDrivingSpeeds {
            perform action a0 { doc /* fall @S319 */ }
        }
        part apronPosition : ApronPosition {
            exhibit state modes {
                state s0 { doc /* physically clear @S474 */ }
            }
        }
        part apronSensing : ApronSensing {
            perform action a0 { doc /* contradicts a declared off-block milestone @S588 */ }
        }
        part apronSensingData : ApronSensingData {
            perform action a0 { doc /* changes a sequencing or stand allocation decision @S589 */ }
        }
        part apronSensorEvents : ApronSensorEvents {
            perform action a0 { doc /* must align with Calculated Takeoff Time and Target Off Block Time decisions @S585 */ }
        }
        part arrival : Arrival {
            exhibit state modes {
                state s0 { doc /* feasible @S618 */ }
            }
        }
        part arrivalOpportunity : ArrivalOpportunity {
            perform action a0 { doc /* preserves the declared capacity envelope @S227 */ }
        }
        part arrivalRegulation : ArrivalRegulation {
            perform action a0 { doc /* begins @S395 */ }
        }
        part arrivalRegulationConsole : ArrivalRegulationConsole {
            perform action a0 { doc /* support the transition from regional planning decisions to executable airport and tower actions @S017 */ }
            perform action a1 { doc /* support tactical airport and regional coordination @S032 */ }
            perform action a2 { doc /* highlights inbound demand periods where holding, speed control, or upstream sequencing may be needed if the forecast capacity materializes @S070 */ }
            perform action a3 { doc /* presents proposed arrival opportunities with the capacity source, regulation start time, and expected delay for each affected flight @S241 */ }
            perform action a4 { doc /* applies airspace capacity reductions to inbound flows @S336 */ }
            perform action a5 { doc /* issues alerts @S407 */ }
            perform action a6 { doc /* presents diversion options with estimated holding exposure, likely gate or stand impact, and any expected effect on regulated arrivals already in the plan @S495 */ }
            perform action a7 { doc /* shall suppress handler-exception annotations for arriving flights unless the exception changes the Airport Acceptance Rate or a regulated arrival sequence @S535 */ }
            perform action a8 { doc /* uses the Medical Diversion Notice to protect arrival priority, stand assignment timing, and downstream border coordination in the active arrival plan @S576 */ }
            perform action a9 { doc /* protect arrival priority, stand assignment timing, and downstream border coordination in the active arrival plan @S576 */ }
            perform action a10 { doc /* applies the revised Airport Acceptance Rate after confirmation by the Regional Flow Manager @S698 */ }
            perform action a11 { doc /* may continue to display arrival demand @S729 */ }
            perform action a12 { doc /* may show inbound connection pressure as context for arrival rate discussions @S757 */ }
            perform action a13 { doc /* does not convert passenger handling needs into a separate arrival priority scheme @S757 */ }
            perform action a14 { doc /* must use the approved rules recorded in the Business Rules Registry @S980 */ }
        }
        part arrivalWorkspace : ArrivalWorkspace {
            perform action a0 { doc /* shows expected landing demand, stand allocation risk, inbound regulation effects, and handling readiness indicators needed to protect the Airport Acceptance Rate @S155 */ }
        }
        part arrivalsToTheMainHub : ArrivalsToTheMainHub {
            perform action a0 { doc /* use common fixes and adjacent climb corridors @S004 */ }
        }
        part assignedAircraftRoute : AssignedAircraftRoute;
        part assignedApronArea : AssignedApronArea {
            exhibit state modes {
                state s0 { doc /* clean @S647 */ }
                state s1 { doc /* free of observed foreign object debris @S647 */ }
                state s2 { doc /* safe @S647 */ }
            }
        }
        part assignedTeam : AssignedTeam {
            perform action a0 { doc /* is still servicing another aircraft @S301 */ }
            perform action a1 { doc /* crossing a congested apron @S301 */ }
            perform action a2 { doc /* waiting for security access to a remote stand @S301 */ }
        }
        part auditEventLedger : AuditEventLedger {
            perform action a0 { doc /* preserve the rationale, timing, and authorization of material operational decisions @S021 */ }
            perform action a1 { doc /* provide governance, security, traceability, and performance measurement capabilities @S034 */ }
            perform action a2 { doc /* retains the trace from incoming forecast product to capacity value @S123 */ }
            perform action a3 { doc /* retains movement updates from the Ramp Movement Board @S222 */ }
            perform action a4 { doc /* stores the previous value, new value, responsible user or automated function, timestamp, authority basis, and applicable operating state for every target time change @S271 */ }
            perform action a5 { doc /* preserves the sequence history @S289 */ }
            perform action a6 { doc /* preserves the same decision history for later traceability, including manual overrides, timestamp corrections, and identity of the approving role @S488 */ }
            perform action a7 { doc /* retain traceability of who viewed, changed, or approved diversion decisions @S515 */ }
            perform action a8 { doc /* records who raised, changed, acknowledged, or closed each escalated exception @S537 */ }
            perform action a9 { doc /* records who entered or changed a recovery choice, the effective time, the affected flight reference, and the reason category selected by the operator @S636 */ }
            perform action a10 { doc /* stores readiness changes, user acknowledgements, hazard closures, and release decisions @S664 */ }
            perform action a11 { doc /* support post-operation review and accountability @S664 */ }
            perform action a12 { doc /* records each approval, rejection, cancellation, and override @S683 */ }
            perform action a13 { doc /* preserves the technical record of submission, validation, publication, acknowledgement, and withdrawal for accountability and post-event review @S710 */ }
            perform action a14 { doc /* shall capture successful and failed authentication attempts, role changes, privilege elevations, operational approvals, configuration changes, data exports, and emergency access activations @S777 */ }
            perform action a15 { doc /* preserve the time source applied by the Time Synchronization Service @S792 */ }
            perform action a16 { doc /* record each proposed option, the user response, and the final decision @S955 */ }
            perform action a17 { doc /* must support traceability, least-privilege access, and after-action accountability for all operationally significant changes @S981 */ }
        }
        part auditOutputs : AuditOutputs;
        part auditProcessing : AuditProcessing {
            perform action a0 { doc /* treat reconciled contingency actions as part of the same operational record as actions taken during Normal Operations @S788 */ }
        }
        part auditRecords : AuditRecords {
            perform action a0 { doc /* shall use time derived from the Time Synchronization Service @S778 */ }
        }
        part auditSequences : AuditSequences {
            perform action a0 { doc /* show missing events, duplicate updates, or inconsistent timestamps @S807 */ }
        }
        part auditTrail : AuditTrail {
            perform action a0 { doc /* capture whether the change preserved the constraints of the active Ground Delay Program @S797 */ }
        }
        part authenticatedAirlineAndHandlingUsers : AuthenticatedAirlineAndHandlingUsers;
        part authority : Authority {
            perform action a0 { doc /* will approve restoration to Normal Operations or Recovery Phase @S717 */ }
        }
        part authorizedActor : AuthorizedActor {
            perform action a0 { doc /* closes @S708 */ }
            perform action a1 { doc /* supersedes it @S708 */ }
        }
        part authorizedAirportAirlineAndFlowManagementUsers : AuthorizedAirportAirlineAndFlowManagementUsers;
        part authorizedOperationalUsers : AuthorizedOperationalUsers {
            perform action a0 { doc /* see the clearance condition needed for coordination @S572 */ }
        }
        part authorizedUser : AuthorizedUser {
            perform action a0 { doc /* assigned by the proposing function or authorized user @S264 */ }
        }
        part authorizedUsers : AuthorizedUsers;
        part automatedSuggestions : AutomatedSuggestions {
            perform action a0 { doc /* would create an infeasible rotation @S623 */ }
        }
        part automation : Automation {
            perform action a0 { doc /* support judgment and workload management @S963 */ }
        }
        part availabilityTargets : AvailabilityTargets {
            perform action a0 { doc /* exclude approved maintenance windows, customer network outages outside the managed boundary, and periods when operational supervisors have directed use of contingency procedures for nontechnical reasons @S934 */ }
        }
        part averageQueueLength : AverageQueueLength;
        part baggageAndHandlerData : BaggageAndHandlerData {
            perform action a0 { doc /* does not disclose unnecessary passenger or workforce details @S541 */ }
        }
        part baggageOrHandlerException : BaggageOrHandlerException {
            perform action a0 { doc /* becomes a coordination issue @S530 */ }
            perform action a1 { doc /* threatens the Target Off Block Time, the Calculated Takeoff Time, or an agreed runway metering sequence @S530 */ }
            exhibit state modes {
                state s0 { doc /* coordination issue @S530 */ }
            }
        }
        part baggageReconciliationData : BaggageReconciliationData {
            perform action a0 { doc /* indicates that departure readiness may be overstated @S452 */ }
        }
        part basedCarriers : BasedCarriers {
            perform action a0 { doc /* require coordinated flow management at the participating airports @S043 */ }
        }
        part benefitSummaries : BenefitSummaries {
            perform action a0 { doc /* show changes in stand occupancy, surface congestion, recovery duration, and passenger-facing disruption indicators @S860 */ }
        }
        part boarding : Boarding {
            exhibit state modes {
                state s0 { doc /* complete @S308 */ }
            }
        }
        part borderAndCustomsData : BorderAndCustomsData {
            perform action a0 { doc /* can affect both operational outcomes and passenger privacy obligations @S587 */ }
        }
        part borderAndCustomsStates : BorderAndCustomsStates {
            perform action a0 { doc /* block sequencing @S586 */ }
            perform action a1 { doc /* require human confirmation @S586 */ }
        }
        part borderProcessing : BorderProcessing {
            perform action a0 { doc /* confirms that a held arrival may proceed to normal turnaround handling @S568 */ }
        }
        part borderReleaseStatus : BorderReleaseStatus {
            perform action a0 { doc /* changes a sequencing or stand allocation decision @S589 */ }
        }
        part bus : Bus {
            perform action a0 { doc /* has arrived @S306 */ }
            perform action a1 { doc /* unloaded @S306 */ }
            perform action a2 { doc /* cleared the stand area @S306 */ }
        }
        part busLoading : BusLoading {
            exhibit state modes {
                state s0 { doc /* less predictable @S563 */ }
            }
        }
        part businessRulesRegistry : BusinessRulesRegistry {
            perform action a0 { doc /* provide governance, security, traceability, and performance measurement capabilities @S034 */ }
            perform action a1 { doc /* are allowed by the Business Rules Registry and local coordination agreements @S055 */ }
            perform action a2 { doc /* supplies the applicable thresholds for alerting, approval routing, and measure publication @S436 */ }
            perform action a3 { doc /* holds the local rules for connection protection, gate compatibility, towing priority, stand reopening approval, and minimum turnaround recovery margins @S486 */ }
            perform action a4 { doc /* can tighten escalation thresholds for flights close to departure @S539 */ }
            perform action a5 { doc /* continuing to suppress low-impact local issues @S539 */ }
            perform action a6 { doc /* defines which border and customs states block sequencing, which states require human confirmation, and which states are informational only @S586 */ }
            perform action a7 { doc /* defines which preference fields are mandatory, optional, or hidden from other participants @S631 */ }
            perform action a8 { doc /* provides the governing parameters for precedence, equity, customs eligibility, minimum notification time, and prohibited trades @S670 */ }
            perform action a9 { doc /* defines which infrastructure events require approval, which events may be published as advisory information, and which events automatically trigger a Capacity Reduction State @S706 */ }
            perform action a10 { doc /* permits that use for the active operating state @S746 */ }
            perform action a11 { doc /* defined by the Business Rules Registry @S768 */ }
            perform action a12 { doc /* hold the current validation thresholds, allowable reason codes, and exception rules approved for Normal Operations, Adverse Weather Mode, Capacity Reduction State, Recovery Phase, and Contingency Fallback State @S831 */ }
            perform action a13 { doc /* retain the local parameters needed for Meridian operations @S939 */ }
        }
        part businessRulesRegistryParameters : BusinessRulesRegistryParameters {
            perform action a0 { doc /* define the maximum planned runway queue, the warning threshold, and the intervention threshold for each runway configuration @S365 */ }
        }
        part businessRulesRegistryThreshold : BusinessRulesRegistryThreshold {
            perform action a0 { doc /* confirms that the condition is operationally material @S534 */ }
        }
        part calculatedTakeoffTime : CalculatedTakeoffTime {
            perform action a0 { doc /* support departure @S305 */ }
            exhibit state modes {
                state s0 { doc /* frozen @S269 */ }
            }
        }
        part calculatedTakeoffTimeCommitments : CalculatedTakeoffTimeCommitments;
        part calculatedTakeoffTimeTolerances : CalculatedTakeoffTimeTolerances;
        part calculatedTakeoffTimeValues : CalculatedTakeoffTimeValues;
        part calculatedTimes : CalculatedTimes {
            perform action a0 { doc /* affect sector workload, runway demand, and controller tactical flexibility @S865 */ }
        }
        part cancellationAvoidance : CancellationAvoidance;
        part candidateAirport : CandidateAirport {
            perform action a0 { doc /* shall provide evidence that the Airport Duty Manager, Tower Supervisor, Ramp Control Lead, Airline Operations Coordinator, Ground Handling Dispatcher, and Aircraft Operator Representative have named accountable implementation contacts @S893 */ }
        }
        part capacity : Capacity {
            perform action a0 { doc /* require a new time @S723 */ }
        }
        part capacityAssessmentModule : CapacityAssessmentModule {
            perform action a0 { doc /* supports the assessment of declared and tactical capacity using weather, runway availability, sector loading, and airport resource conditions @S014 */ }
            perform action a1 { doc /* using weather, runway availability, sector loading, and airport resource conditions @S014 */ }
            perform action a2 { doc /* support planning and collaborative assessment @S031 */ }
            perform action a3 { doc /* combines the runway declaration, weather outlook, airspace constraints, stand readiness, and ground resource assumptions into a proposed Airport Acceptance Rate by period @S066 */ }
            perform action a4 { doc /* indicates that declared capacity no longer matches observed conditions @S094 */ }
            perform action a5 { doc /* combines demand projections with the Airport Capacity Plan @S107 */ }
            perform action a6 { doc /* determine whether a published Airport Acceptance Rate remains feasible @S107 */ }
            perform action a7 { doc /* applies the current wind, visibility, and precipitation assumptions @S114 */ }
            perform action a8 { doc /* flags the associated capacity values as provisional @S120 */ }
            perform action a9 { doc /* compares that demand with the Airport Capacity Plan and the current Airport Acceptance Rate @S132 */ }
            perform action a10 { doc /* recommending operating limits @S132 */ }
            perform action a11 { doc /* uses the Storm Cell Snapshot @S133 */ }
            perform action a12 { doc /* qualify capacity confidence during convective weather impacts @S133 */ }
            perform action a13 { doc /* may use the confirmed airport position @S192 */ }
            perform action a14 { doc /* recalculate available capacity @S192 */ }
            perform action a15 { doc /* does not originate local airfield safety judgments @S192 */ }
            perform action a16 { doc /* applies the active Airport Capacity Plan and Airport Acceptance Rate @S252 */ }
            perform action a17 { doc /* determine whether the proposed demand pattern remains operationally feasible @S252 */ }
            perform action a18 { doc /* treats a restriction as a time-bounded reduction in route, sector, or airport throughput, depending on the geometry and operational impact of the area @S328 */ }
            perform action a19 { doc /* recalculates the effective Airport Acceptance Rate @S341 */ }
            perform action a20 { doc /* passes the revised assumption into the operational planning cycle @S341 */ }
            perform action a21 { doc /* compares that demand with the active Airport Acceptance Rate, runway configuration, taxiway constraints, and sector limits @S351 */ }
            perform action a22 { doc /* reduces practical departure capacity @S373 */ }
            perform action a23 { doc /* account for deicing time, pad transit time, and slower ramp taxi speeds @S373 */ }
            perform action a24 { doc /* calculates candidate Airport Acceptance Rate values for each runway configuration @S400 */ }
            perform action a25 { doc /* exposes the operational basis for each value on the Common Situation Display @S400 */ }
            perform action a26 { doc /* recalculates available capacity @S431 */ }
            perform action a27 { doc /* converts persistent surface constraints into reduced stand throughput, extended turn buffers, or modified taxi-out assumptions @S448 */ }
            perform action a28 { doc /* evaluates runway availability, stand availability, sector load, handling capacity, and service constraints @S494 */ }
            perform action a29 { doc /* reflects persistent remote stand service limits as a reduction in practical gate throughput rather than only as a ramp movement issue @S557 */ }
            perform action a30 { doc /* applies persistent apron congestion as a local capacity factor @S584 */ }
            perform action a31 { doc /* estimating achievable departure throughput during Normal Operations and Adverse Weather Mode @S584 */ }
            perform action a32 { doc /* evaluates whether the affected traffic is dominated by departures, arrivals, or mixed flows @S594 */ }
            perform action a33 { doc /* applies Business Rules Registry thresholds @S600 */ }
            perform action a34 { doc /* distinguish a short tactical peak from sustained saturation requiring a Tactical Regulation Proposal @S600 */ }
            perform action a35 { doc /* converts the limit into a runway configuration constraint @S694 */ }
            perform action a36 { doc /* treating it as a general advisory @S694 */ }
            perform action a37 { doc /* calculates the operational effect @S697 */ }
            perform action a38 { doc /* comparing the affected resource with the current Airport Capacity Plan and the active weather state @S697 */ }
            perform action a39 { doc /* absorb discretionary changes @S755 */ }
            perform action a40 { doc /* reject data that lacks a trusted timestamp @S825 */ }
            perform action a41 { doc /* record the available Airport Acceptance Rate used in each baseline @S853 */ }
            perform action a42 { doc /* evolve from a mainly rules-based assessment into a service that can compare planned capacity, observed throughput, and predicted constraint persistence @S944 */ }
            perform action a43 { doc /* compare planned capacity, observed throughput, and predicted constraint persistence @S944 */ }
            perform action a44 { doc /* provide planning evidence @S973 */ }
        }
        part capacityChanges : CapacityChanges;
        part capacityOrDelayEstimate : CapacityOrDelayEstimate {
            perform action a0 { doc /* has changed @S945 */ }
        }
        part capacityPicture : CapacityPicture {
            perform action a0 { doc /* may change @S121 */ }
        }
        part capacityReductionState : CapacityReductionState {
            perform action a0 { doc /* drive stakeholder participation and operating procedures @S047 */ }
        }
        part capacityUpdate : CapacityUpdate {
            perform action a0 { doc /* changes the feasible departure allocation for the affected traffic set @S269 */ }
        }
        part capacityValues : CapacityValues {
            exhibit state modes {
                state s0 { doc /* provisional @S120 */ }
            }
        }
        part cargoAndGeneralAviationAerodromes : CargoAndGeneralAviationAerodromes {
            perform action a0 { doc /* operating within shared terminal airspace @S001 */ }
        }
        part cargoOperators : CargoOperators;
        part catering : Catering {
            perform action a0 { doc /* would cause holdover time to be wasted @S385 */ }
        }
        part certificationResults : CertificationResults {
            perform action a0 { doc /* affect operational procedures @S901 */ }
            perform action a1 { doc /* affect access, configuration, or transaction traceability @S901 */ }
        }
        part change : Change {
            perform action a0 { doc /* preserved the constraints of the active Ground Delay Program @S797 */ }
        }
        part changes : Changes {
            perform action a0 { doc /* require a reason code @S800 */ }
            perform action a1 { doc /* be visible to the Regional Flow Manager during post-operations review @S800 */ }
            perform action a2 { doc /* modify the Business Rules Registry, Identity Access Service, Time Synchronization Service, Flight Data Exchange, or operational metering behavior @S931 */ }
            perform action a3 { doc /* require additional validation in a representative test environment before production release @S931 */ }
        }
        part charterOperators : CharterOperators;
        part civilTrafficManagers : CivilTrafficManagers {
            perform action a0 { doc /* receive usable timing, altitude, and boundary information @S324 */ }
        }
        part clearAlertPrioritization : ClearAlertPrioritization;
        part closedBays : ClosedBays;
        part coastalFog : CoastalFog {
            perform action a0 { doc /* frequently reduce the effective Airport Acceptance Rate across the network @S005 */ }
        }
        part codeSetChecks : CodeSetChecks;
        part collaborativeDecisionLog : CollaborativeDecisionLog {
            perform action a0 { doc /* preserve the rationale, timing, and authorization of material operational decisions @S021 */ }
            perform action a1 { doc /* records who changed a value, when the change was made, whether the change was provisional or confirmed, and what operational decision relied on it @S169 */ }
            perform action a2 { doc /* captures the time, origin, and rationale for each local coordination decision that affects capacity or surface flow @S186 */ }
            perform action a3 { doc /* records each challenge, counterproposal, acceptance, rejection, and reason code associated with the Target Off Block Time and Calculated Takeoff Time @S267 */ }
            perform action a4 { doc /* captures winter-mode decisions, including capacity changes, pad flow restrictions, and agreed deviations from the normal departure order @S392 */ }
            perform action a5 { doc /* records each accepted conflict resolution with the chosen stand, rejected alternatives, affected passenger connections, and the rationale used by the responsible actor @S487 */ }
            perform action a6 { doc /* records the operational reason @S589 */ }
            perform action a7 { doc /* records the constraint, chosen conversion rule, responsible actor, and time of approval for traceability @S615 */ }
            perform action a8 { doc /* records any agreed operational outcome, including whether the decision was constrained by crew legality or by an operator preference @S637 */ }
            perform action a9 { doc /* captures the proposed flights, the reason code, the user confirmations, the governance outcome, and the final decision time @S682 */ }
            perform action a10 { doc /* records the time of publication, approving role, capacity effect, affected services, and any later amendment made during the operating period @S709 */ }
            perform action a11 { doc /* retain the stated reason, decision time, affected flight, and visible operational context for each material change to a slot or sequence @S794 */ }
            perform action a12 { doc /* record each proposed option, the user response, and the final decision @S955 */ }
        }
        part collaborativeDecisionLogEntries : CollaborativeDecisionLogEntries;
        part collaborativeTargetTimeManagement : CollaborativeTargetTimeManagement {
            perform action a0 { doc /* establishes a shared operating baseline for each departure @S249 */ }
            perform action a1 { doc /* linking the Target Off Block Time, the Calculated Takeoff Time, and the key surface milestone timestamps to the same flight record @S249 */ }
        }
        part commonServices : CommonServices {
            perform action a0 { doc /* support regional flow management and Airport Collaborative Decision-Making participation @S030 */ }
        }
        part commonSituationDisplay : CommonSituationDisplay {
            perform action a0 { doc /* give authorized users a shared view of demand, capacity, constraints, and active traffic management measures @S020 */ }
            perform action a1 { doc /* presents the approved pre-tactical baseline as the shared reference for Normal Operations, Adverse Weather Mode, Capacity Reduction State, and early Recovery Phase decisions @S072 */ }
            perform action a2 { doc /* distinguishes values supplied by connected services, values confirmed by users, and values that have exceeded the configured freshness threshold @S165 */ }
            perform action a3 { doc /* shows the current agreed target set @S265 */ }
            perform action a4 { doc /* highlights expired treatments, pad closures, fluid shortages, and ramp blockages @S391 */ }
            perform action a5 { doc /* provides the base map, timeline, flight list, and measure status panels used at the position @S421 */ }
            perform action a6 { doc /* highlights active surface advisories with the affected stands, taxi segments, runway meters, and flight identifiers visible to authorized users @S462 */ }
            perform action a7 { doc /* shows only the flight impact, severity, and expected recovery window @S527 */ }
            perform action a8 { doc /* prevents local troubleshooting details from crowding the regional view used by the Regional Flow Manager, Tower Supervisor, and Slot Coordinator @S528 */ }
            perform action a9 { doc /* presents remote stand status in time order @S560 */ }
            perform action a10 { doc /* shows crew legality impacts as coded operational states, such as feasible, time critical, infeasible, or operator review required @S627 */ }
            perform action a11 { doc /* without exposing the commercial reasoning behind an operator decision @S628 */ }
            perform action a12 { doc /* presents the updated Calculated Takeoff Time and Target Off Block Time @S685 */ }
            perform action a13 { doc /* shows the affected resource, start time, review time, and current decision status @S704 */ }
            perform action a14 { doc /* using language that can be understood by operational staff @S704 */ }
            perform action a15 { doc /* presents passenger disruption cues with clear labeling @S758 */ }
        }
        part commonSituationDisplayContent : CommonSituationDisplayContent;
        part communicationSequencing : CommunicationSequencing {
            perform action a0 { doc /* follows the principle that safety status is confirmed first, airspace and runway feasibility second, airport resource readiness third, and passenger or network recovery actions last @S504 */ }
        }
        part competentController : CompetentController {
            perform action a0 { doc /* confirms the operational effect @S188 */ }
        }
        part complianceAssessment : ComplianceAssessment {
            perform action a0 { doc /* compare the Calculated Takeoff Time, the Target Off Block Time, actual off-block time, and actual takeoff time against the tolerance defined in the Business Rules Registry @S790 */ }
        }
        part complianceWithRevisedTimes : ComplianceWithRevisedTimes;
        part condition : Condition {
            perform action a0 { doc /* blocks a single movement, a stand group, or a wider apron route @S446 */ }
        }
        part conditionalAvailability : ConditionalAvailability;
        part conditionalRouteAvailability : ConditionalRouteAvailability {
            perform action a0 { doc /* changes the effective capacity @S609 */ }
        }
        part conditions : Conditions {
            perform action a0 { doc /* can change the departure plan @S516 */ }
            perform action a1 { doc /* reach shared displays @S517 */ }
        }
        part conditionsThatMayAffectRunwayTaxiwayStandOrApronAvailability : ConditionsThatMayAffectRunwayTaxiwayStandOrApronAvailability {
            perform action a0 { doc /* may affect runway, taxiway, stand, or apron availability @S175 */ }
        }
        part confidenceLevel : ConfidenceLevel;
        part confidenceRecord : ConfidenceRecord {
            perform action a0 { doc /* also stores the originating feed, the processing time, the transformation version, and any manual override applied by the Meteorology Briefing Officer @S119 */ }
        }
        part confidenceValue : ConfidenceValue;
        part confirmationStepsForHighImpactActions : ConfirmationStepsForHighImpactActions;
        part congestion : Congestion {
            perform action a0 { doc /* becomes unstable @S009 */ }
        }
        part connectedServices : ConnectedServices {
            perform action a0 { doc /* supplied by connected services @S165 */ }
        }
        part conservativeIntents : ConservativeIntents {
            perform action a0 { doc /* distinguish firm operating plans from speculative recovery options @S146 */ }
        }
        part consistentTerminology : ConsistentTerminology;
        part constrainedPrimaryAirport : ConstrainedPrimaryAirport;
        part constrainedRemoteStandAccess : ConstrainedRemoteStandAccess;
        part constraintRecords : ConstraintRecords;
        part contamination : Contamination {
            perform action a0 { doc /* affect the planned treatment rate @S383 */ }
        }
        part contaminationReports : ContaminationReports {
            perform action a0 { doc /* make untreated ground movement unreliable @S371 */ }
        }
        part contingencyFallbackState : ContingencyFallbackState {
            perform action a0 { doc /* drive stakeholder participation and operating procedures @S047 */ }
        }
        part contingencyOperationsConsole : ContingencyOperationsConsole {
            perform action a0 { doc /* support tactical airport and regional coordination @S032 */ }
            perform action a1 { doc /* provides a degraded channel for recording tower and duty desk decisions @S195 */ }
            perform action a2 { doc /* preserves the last valid allocation @S247 */ }
            perform action a3 { doc /* supports manual amendments @S247 */ }
            perform action a4 { doc /* marks the resulting Slot Compliance State as provisional @S247 */ }
            perform action a5 { doc /* provides a protected operating position with independent access to the Flight Data Exchange, Alert Distribution Hub, Audit Event Ledger, and Digital Briefing Room @S719 */ }
            perform action a6 { doc /* accept emergency access activations @S783 */ }
            perform action a7 { doc /* be generated by the Contingency Operations Console @S952 */ }
        }
        part contractedHandlers : ContractedHandlers;
        part controlledSlotSwapProcess : ControlledSlotSwapProcess {
            perform action a0 { doc /* begins @S666 */ }
        }
        part convectiveActivity : ConvectiveActivity {
            perform action a0 { doc /* change achievable runway throughput @S409 */ }
        }
        part convectiveAvoidance : ConvectiveAvoidance {
            perform action a0 { doc /* dominated fuel performance @S858 */ }
        }
        part convectiveReroutes : ConvectiveReroutes {
            perform action a0 { doc /* frequently reduce the effective Airport Acceptance Rate across the network @S005 */ }
        }
        part convergingArrivalFlows : ConvergingArrivalFlows {
            perform action a0 { doc /* exceed terminal sector capacity under the current metering plan @S408 */ }
        }
        part conversion : Conversion {
            perform action a0 { doc /* may only produce monitoring alerts @S611 */ }
        }
        part convertedMeasures : ConvertedMeasures {
            perform action a0 { doc /* changes operational behavior @S614 */ }
        }
        part coordinatedActions : CoordinatedActions {
            perform action a0 { doc /* balance runway throughput, sector loading, stand availability, and airline priorities @S951 */ }
        }
        part coreOperationalBaseline : CoreOperationalBaseline {
            perform action a0 { doc /* shall include the Identity Access Service, Time Synchronization Service, Audit Event Ledger, Performance Analytics Warehouse, and Business Rules Registry @S890 */ }
        }
        part countdowns : Countdowns {
            perform action a0 { doc /* use the same operational clock @S422 */ }
        }
        part crew : Crew {
            perform action a0 { doc /* would cause holdover time to be wasted @S385 */ }
            exhibit state modes {
                state s0 { doc /* complete @S449 */ }
            }
        }
        part crewLegality : CrewLegality {
            exhibit state modes {
                state s0 { doc /* feasible @S627 */ }
                state s1 { doc /* infeasible @S627 */ }
                state s2 { doc /* operator review required @S627 */ }
                state s3 { doc /* time critical @S627 */ }
            }
        }
        part crewReadiness : CrewReadiness;
        part crewTransportLateness : CrewTransportLateness {
            perform action a0 { doc /* affects an aircraft turn @S140 */ }
        }
        part crews : Crews {
            exhibit state modes {
                state s0 { doc /* ready @S308 */ }
            }
        }
        part criticalIncident : CriticalIncident {
            perform action a0 { doc /* have continuous technical ownership until service is restored or an agreed operational workaround is in place @S920 */ }
        }
        part criticalSystemRecovery : CriticalSystemRecovery {
            perform action a0 { doc /* requires immediate action @S784 */ }
        }
        part crossBorderExchange : CrossBorderExchange {
            perform action a0 { doc /* use standardized message structures where practical @S939 */ }
        }
        part curfew : Curfew {
            perform action a0 { doc /* require a new time @S723 */ }
        }
        part customsHold : CustomsHold {
            perform action a0 { doc /* conflicts with an assigned stand plan @S588 */ }
            exhibit state modes {
                state s0 { doc /* unresolved @S575 */ }
            }
        }
        part customsHoldIndicators : CustomsHoldIndicators {
            perform action a0 { doc /* prevent premature stand release, passenger transfer assumptions, or departure readiness claims @S569 */ }
        }
        part customsHoldStatus : CustomsHoldStatus {
            perform action a0 { doc /* changes a sequencing or stand allocation decision @S589 */ }
        }
        part customsStatus : CustomsStatus {
            exhibit state modes {
                state s0 { doc /* incomplete @S681 */ }
            }
        }
        part customsStatusEvents : CustomsStatusEvents {
            perform action a0 { doc /* must align with Calculated Takeoff Time and Target Off Block Time decisions @S585 */ }
        }
        part cutoverDecision : CutoverDecision;
        part dailyPlanningCycle : DailyPlanningCycle {
            perform action a0 { doc /* begins with a pre-tactical baseline @S049 */ }
        }
        part dataDiscoveryWorkshops : DataDiscoveryWorkshops {
            perform action a0 { doc /* identify local tools, manual workarounds, unofficial spreadsheets, and locally maintained constraint registers @S902 */ }
        }
        part dataFeedTimeliness : DataFeedTimeliness;
        part dataGovernance : DataGovernance {
            perform action a0 { doc /* assign accountable owners to each operational data domain @S812 */ }
            perform action a1 { doc /* make those assignments visible in the Airport CDM Portal @S812 */ }
        }
        part dataGovernanceSteward : DataGovernanceSteward {
            perform action a0 { doc /* participate @S042 */ }
            perform action a1 { doc /* maintain data quality, access control, operational continuity, and controlled configuration of the Regional Flow Platform @S042 */ }
            perform action a2 { doc /* verifies that operational decisions, role acknowledgements, and exception handling are captured in the Audit Event Ledger with synchronized timestamps from the Time Synchronization Service @S098 */ }
            perform action a3 { doc /* defines the mandatory fields, permissible status values, retention rules, and data quality thresholds used by the Airport CDM Portal @S170 */ }
            perform action a4 { doc /* ensures that exemption categories, priority codes, and fairness metrics are versioned in the Business Rules Registry before they are used in live allocation @S240 */ }
            perform action a5 { doc /* reviews audit samples @S273 */ }
            perform action a6 { doc /* confirm that timestamps are complete, reason codes are valid, and manual changes can be traced to an operational justification @S273 */ }
            perform action a7 { doc /* ensures that passenger connection information used for prioritization is aggregated or role-restricted so that operational users see only the detail required for recovery decisions @S490 */ }
            perform action a8 { doc /* ensures that sensitive operational and passenger information remains role-restricted @S515 */ }
            perform action a9 { doc /* ensures that baggage and handler data exposed outside the local operation is limited to operational necessity and does not disclose unnecessary passenger or workforce details @S541 */ }
            perform action a10 { doc /* maintains the access rules and retention rules for border and customs data @S587 */ }
            perform action a11 { doc /* monitors data quality for infrastructure events, including duplicate reports, inconsistent effective times, and unclear service descriptions @S711 */ }
            perform action a12 { doc /* confirms which data sets may be trusted @S733 */ }
            perform action a13 { doc /* marks any later synchronization from fallback records for reconciliation review @S733 */ }
            perform action a14 { doc /* defines the acceptable aggregation level @S742 */ }
            perform action a15 { doc /* may manage data retention rules, reference data ownership, and audit review processes @S773 */ }
            perform action a16 { doc /* without being able to issue operational traffic flow instructions @S773 */ }
            perform action a17 { doc /* verify that audit fields required for slot performance reporting remain complete, immutable, and traceable to approved data definitions @S806 */ }
            perform action a18 { doc /* maintain the data ownership register @S813 */ }
            perform action a19 { doc /* coordinate updates through the Business Rules Registry @S813 */ }
            perform action a20 { doc /* coordinate discrepancy resolution with the responsible operational owner @S833 */ }
            perform action a21 { doc /* record the disposition in the Audit Event Ledger @S833 */ }
            perform action a22 { doc /* ensure that published performance measures identify data sources, calculation versions, confidence limits, and known exclusions @S861 */ }
            perform action a23 { doc /* train operational users on data quality responsibilities, privacy expectations, and the correct interpretation of audit records in the Audit Event Ledger @S876 */ }
            perform action a24 { doc /* monitor defect trends, data quality, access changes, and user adoption @S910 */ }
        }
        part dataLatency : DataLatency {
            perform action a0 { doc /* prevent users from relying on the normal decision support path without additional verification @S715 */ }
        }
        part dataQualityMeasures : DataQualityMeasures;
        part decisionMakers : DecisionMakers {
            perform action a0 { doc /* can see whether delay, queue, slot, cancellation, and emissions objectives were balanced in practice @S862 */ }
        }
        part decisionSupportFunctions : DecisionSupportFunctions;
        part declaration : Declaration {
            perform action a0 { doc /* identifies the affected functions, the operational area, the expected duration, and the authority that will approve restoration to Normal Operations or Recovery Phase @S717 */ }
        }
        part declaredCapacity : DeclaredCapacity {
            perform action a0 { doc /* no longer matches observed conditions @S094 */ }
        }
        part dedicatedMilestoneView : DedicatedMilestoneView {
            perform action a0 { doc /* records the planned, target, estimated, actual, and manually confirmed times for each turnaround event that affects a regulated departure or constrained arrival @S156 */ }
        }
        part definedContingencyForBlockedApronMovement : DefinedContingencyForBlockedApronMovement;
        part definedTechnicalBoundary : DefinedTechnicalBoundary;
        part degradedPerformance : DegradedPerformance {
            perform action a0 { doc /* make continued flight or extended holding undesirable @S498 */ }
        }
        part degradedWeatherInputs : DegradedWeatherInputs {
            perform action a0 { doc /* affect capacity assumptions for the next planning period @S112 */ }
        }
        part deicingConstraints : DeicingConstraints {
            perform action a0 { doc /* affect achievable departure throughput during winter operations @S969 */ }
        }
        part deicingCoordinator : DeicingCoordinator {
            perform action a0 { doc /* participate @S040 */ }
            perform action a1 { doc /* represent local airport, tower, ramp, handling, and winter operations considerations @S040 */ }
            perform action a2 { doc /* provides pre-tactical and tactical advice when winter operations affect departure readiness, metering stability, or achievable throughput @S092 */ }
            perform action a3 { doc /* sends the Deicing Pad Queue Card @S294 */ }
            perform action a4 { doc /* maintains the active pad configuration, including open bays, closed bays, fluid limitations, and vehicle availability @S375 */ }
            perform action a5 { doc /* marks the treatment as expired @S390 */ }
            perform action a6 { doc /* returns the aircraft to the appropriate queue state @S390 */ }
            perform action a7 { doc /* receive seasonal refresher training on how deicing capacity assumptions are represented in demand and departure metering tools @S875 */ }
            perform action a8 { doc /* confirm deicing constraints that affect achievable departure throughput during winter operations @S969 */ }
        }
        part deicingDemand : DeicingDemand {
            perform action a0 { doc /* increases @S296 */ }
        }
        part deicingInterfacePoint : DeicingInterfacePoint {
            perform action a0 { doc /* exposes whether a flight still requires treatment, is waiting for pad access, is under treatment, or has been released for taxi within the protected time assumption @S295 */ }
        }
        part deicingProviders : DeicingProviders;
        part deicingResidue : DeicingResidue {
            perform action a0 { doc /* can increase the probability of foreign object debris and surface contamination @S661 */ }
        }
        part delayAbsorption : DelayAbsorption {
            exhibit state modes {
                state s0 { doc /* local to the airport @S573 */ }
            }
        }
        part delayAndQueueForecasts : DelayAndQueueForecasts {
            perform action a0 { doc /* reflect the published limitation @S701 */ }
        }
        part delayTransfers : DelayTransfers {
            perform action a0 { doc /* only move fuel burn from one phase of flight to another @S857 */ }
        }
        part demand : Demand {
            perform action a0 { doc /* exceeds the safe holding capacity near the pad @S379 */ }
        }
        part demandPredictionService : DemandPredictionService {
            perform action a0 { doc /* estimates expected demand from scheduled operations, Flight Intent Message data, known airline recovery plans, and near-term operational changes @S013 */ }
            perform action a1 { doc /* support planning and collaborative assessment @S031 */ }
            perform action a2 { doc /* converts the normalized schedule into expected arrival and departure demand by time band, runway direction, terminal area, and major traffic flow @S053 */ }
            perform action a3 { doc /* generates the demand forecast used by the Regional Flow Platform @S101 */ }
            perform action a4 { doc /* receives filed flight information through the Flight Data Exchange @S103 */ }
            perform action a5 { doc /* compares it with the current operating schedule held by the Airline Interface Adapter @S103 */ }
            perform action a6 { doc /* uses recent conformance history, aircraft rotation timing, and known bank structures @S105 */ }
            perform action a7 { doc /* estimate arrival and departure loads by planning interval @S105 */ }
            perform action a8 { doc /* uses current airline intents @S131 */ }
            perform action a9 { doc /* refine departure demand, arrival demand, and recovery demand by time band @S131 */ }
            perform action a10 { doc /* shall refresh stand demand forecasts @S216 */ }
            perform action a11 { doc /* estimates demand pressure over the next planning horizon @S251 */ }
            perform action a12 { doc /* marks flights whose proposed Target Off Block Time values are likely to cause runway or sector imbalance @S251 */ }
            perform action a13 { doc /* estimates the departure demand profile by stand, apron area, runway, and departure fix @S350 */ }
            perform action a14 { doc /* shows that inbound demand will exceed the Airport Acceptance Rate within the planning horizon @S395 */ }
            perform action a15 { doc /* continuously updates short-term traffic forecasts using the Flight Intent Message stream and recent airport performance history @S430 */ }
            perform action a16 { doc /* using the Flight Intent Message stream and recent airport performance history @S430 */ }
            perform action a17 { doc /* compares amended Flight Intent Message data with the Airport Capacity Plan and the current Airport Acceptance Rate @S493 */ }
            perform action a18 { doc /* show whether a diversion can be absorbed without creating unsafe demand peaks @S493 */ }
            perform action a19 { doc /* treats the turnaround milestone as uncertain rather than assuming that the planned connection interval is valid @S571 */ }
            perform action a20 { doc /* assuming that the planned connection interval is valid @S571 */ }
            perform action a21 { doc /* recalculates short-term demand against the constrained capacity @S701 */ }
            perform action a22 { doc /* combines connection-risk indicators with aircraft readiness, scheduled bank structure, and forecast arrival variability @S743 */ }
            perform action a23 { doc /* estimate the sensitivity of selected departures @S743 */ }
            perform action a24 { doc /* discounts the associated connection benefit @S754 */ }
            perform action a25 { doc /* reject data that lacks a trusted timestamp @S825 */ }
            perform action a26 { doc /* use this data @S941 */ }
            perform action a27 { doc /* create more stable demand pictures across longer planning horizons @S941 */ }
            perform action a28 { doc /* preserving tactical responsiveness @S941 */ }
            perform action a29 { doc /* provide planning evidence @S973 */ }
        }
        part demandSmoothing : DemandSmoothing;
        part departure : Departure {
            perform action a0 { doc /* would create an overlapping occupancy condition at a stand or adjacent service lane @S210 */ }
        }
        part departureFixConstraint : DepartureFixConstraint;
        part departureMetering : DepartureMetering {
            perform action a0 { doc /* does not protect one sector by creating an unmanaged arrival queue @S597 */ }
            perform action a1 { doc /* creating an unmanaged arrival queue @S597 */ }
        }
        part departureMeteringService : DepartureMeteringService {
            perform action a0 { doc /* support the transition from regional planning decisions to executable airport and tower actions @S017 */ }
            perform action a1 { doc /* support tactical airport and regional coordination @S032 */ }
            perform action a2 { doc /* estimates provisional Target Off Block Time sensitivity @S069 */ }
            perform action a3 { doc /* presents proposed departure opportunities and associated Calculated Takeoff Time values for coordination with the Tower Sequence Manager @S242 */ }
            perform action a4 { doc /* aligns each Target Off Block Time with the applicable Calculated Takeoff Time @S278 */ }
            perform action a5 { doc /* absorb a small ground handling variation @S315 */ }
            perform action a6 { doc /* uses the current capacity assumptions @S335 */ }
            perform action a7 { doc /* adjust departure release guidance @S335 */ }
            perform action a8 { doc /* preserving previously coordinated Calculated Takeoff Time values where feasible @S335 */ }
            perform action a9 { doc /* extends the restriction handling process @S347 */ }
            perform action a10 { doc /* deciding where delay is best absorbed @S347 */ }
            perform action a11 { doc /* converts runway demand into controlled stand delay @S348 */ }
            perform action a12 { doc /* derives a feasible Target Off Block Time that protects the Calculated Takeoff Time without overloading the surface movement area @S352 */ }
            perform action a13 { doc /* overloading the surface movement area @S352 */ }
            perform action a14 { doc /* withholds further push clearances @S379 */ }
            perform action a15 { doc /* sends revised departure metering advisories @S426 */ }
            perform action a16 { doc /* translates runway metering limits into candidate pushback spacing for the Slot Allocation Engine @S456 */ }
            perform action a17 { doc /* sequences recovered departures @S483 */ }
            perform action a18 { doc /* applies exception status @S534 */ }
            perform action a19 { doc /* incorporates remote stand constraints when estimating whether a Target Off Block Time remains achievable @S553 */ }
            perform action a20 { doc /* estimating whether a Target Off Block Time remains achievable @S553 */ }
            perform action a21 { doc /* receives only the feasibility result and timing boundary needed for sequencing decisions @S626 */ }
            perform action a22 { doc /* suppresses release recommendations for flights whose assigned stand is not marked ready or whose access route is blocked by an unresolved apron condition @S656 */ }
            perform action a23 { doc /* recalculates metering advisories after approval @S686 */ }
            perform action a24 { doc /* prevents the swap from creating a new demand peak at a departure fix @S686 */ }
            perform action a25 { doc /* updates metering rates @S699 */ }
            perform action a26 { doc /* provides revised inputs to the Slot Allocation Engine @S699 */ }
            perform action a27 { doc /* may remain in monitoring mode while manual slot control is active @S728 */ }
            perform action a28 { doc /* must not automatically overwrite issued times @S728 */ }
            perform action a29 { doc /* can therefore recommend a minor hold, release, or resequencing action only when the change remains inside the available runway and surface movement envelope @S747 */ }
            perform action a30 { doc /* reject data that lacks a trusted timestamp @S825 */ }
            perform action a31 { doc /* uses the Passenger Misconnect Count @S851 */ }
            perform action a32 { doc /* weight departure sequencing decisions @S851 */ }
            perform action a33 { doc /* receive only the information needed for tactical sequencing @S950 */ }
            perform action a34 { doc /* must use the approved rules recorded in the Business Rules Registry @S980 */ }
            exhibit state modes {
                state s0 { doc /* monitoring mode @S728 */ }
            }
        }
        part departureQueue : DepartureQueue {
            perform action a0 { doc /* indicates that uncontrolled pushback would create an unstable surface queue @S453 */ }
        }
        part departureReadinessChecks : DepartureReadinessChecks {
            perform action a0 { doc /* combine aircraft operator status, ground handling status, cockpit readiness, route clearance availability, and surface position into a single tower-readable indicator @S290 */ }
        }
        part departures : Departures {
            exhibit state modes {
                state s0 { doc /* Slot Compliance State @S502 */ }
            }
        }
        part departuresFromNearbySecondaryAirports : DeparturesFromNearbySecondaryAirports {
            perform action a0 { doc /* use common fixes and adjacent climb corridors @S004 */ }
        }
        part deployedAirport : DeployedAirport {
            exhibit state modes {
                state s0 { doc /* steady state support @S912 */ }
            }
        }
        part deploymentOfTheRegionalFlowPlatform : DeploymentOfTheRegionalFlowPlatform {
            perform action a0 { doc /* shall proceed through phased increments @S888 */ }
        }
        part design : Design {
            perform action a0 { doc /* allows coordinated recovery during Normal Operations, Adverse Weather Mode, Capacity Reduction State, and Recovery Phase @S640 */ }
            perform action a1 { doc /* preserving the operator's commercially sensitive decision logic @S640 */ }
        }
        part designatedMilitaryCoordinationFunction : DesignatedMilitaryCoordinationFunction {
            perform action a0 { doc /* affects civil capacity planning @S045 */ }
        }
        part digitalBriefingRoom : DigitalBriefingRoom {
            perform action a0 { doc /* support planning and collaborative assessment @S031 */ }
            perform action a1 { doc /* displays the emerging Airport Capacity Plan @S071 */ }
            perform action a2 { doc /* records unresolved assumptions in the Collaborative Decision Log for confirmation during the morning coordination briefing @S071 */ }
            perform action a3 { doc /* provides a common venue for the Regional Flow Manager, Airspace Sector Planner, Military Airspace Liaison, Tower Supervisor, and Airport Duty Manager to confirm the active interpretation of the restriction @S345 */ }
            perform action a4 { doc /* records the diversion rationale, priority classification, resource commitment, and agreed recovery target in the Collaborative Decision Log @S506 */ }
        }
        part diversionAndIrregularOperationsHandling : DiversionAndIrregularOperationsHandling {
            perform action a0 { doc /* extends the operational concept beyond planned flow control @S491 */ }
            perform action a1 { doc /* supporting safe acceptance, prioritization, communication, and recovery during the Recovery Phase and the Contingency Fallback State @S491 */ }
        }
        part diversionChoices : DiversionChoices {
            perform action a0 { doc /* reflect changing ceiling, visibility, wind, and convective risk @S512 */ }
        }
        part diversionDecision : DiversionDecision {
            perform action a0 { doc /* accounts for both airport capacity and network recovery needs @S507 */ }
        }
        part diversionRecovery : DiversionRecovery {
            perform action a0 { doc /* requires a protected departure movement @S503 */ }
        }
        part diversionRisk : DiversionRisk {
            perform action a0 { doc /* becomes material @S413 */ }
        }
        part diversionTraffic : DiversionTraffic {
            perform action a0 { doc /* requires a broader arrival management action @S501 */ }
        }
        part downstreamServices : DownstreamServices {
            perform action a0 { doc /* need to update schedules, metering, or airport resource plans @S638 */ }
        }
        part drivers : Drivers;
        part dualControl : DualControl;
        part earlierValue : EarlierValue {
            exhibit state modes {
                state s0 { doc /* deleted @S270 */ }
                state s1 { doc /* superseded @S270 */ }
            }
        }
        part eastApronSensor : EastApronSensor {
            perform action a0 { doc /* provide additional indicators of emerging capacity loss and operational imbalance @S019 */ }
            perform action a1 { doc /* improve queue accuracy @S282 */ }
            perform action a2 { doc /* detecting aircraft movement @S282 */ }
            perform action a3 { doc /* provide supporting movement evidence for the reopened area @S474 */ }
            perform action a4 { doc /* reports stand occupancy transitions, pushback lane blockage durations, and sensor confidence values at a synchronized event time @S578 */ }
            perform action a5 { doc /* provide supporting surveillance cues @S645 */ }
            perform action a6 { doc /* support independent checks of queue length where surveillance coverage is available @S845 */ }
        }
        part effectiveTime : EffectiveTime;
        part emergencyChanges : EmergencyChanges;
        part emergencyConditions : EmergencyConditions {
            perform action a0 { doc /* affect airport or regional flow priorities @S968 */ }
        }
        part emergencyResponseActivity : EmergencyResponseActivity {
            perform action a0 { doc /* may affect airport acceptance, surface movement, or airspace availability @S096 */ }
        }
        part emergencyResponseConditions : EmergencyResponseConditions {
            perform action a0 { doc /* affect available capacity @S041 */ }
        }
        part emergencyResponseCoordinator : EmergencyResponseCoordinator {
            perform action a0 { doc /* participate @S041 */ }
            perform action a1 { doc /* confirms rescue, medical, and airport safety readiness with the Airport Duty Manager @S499 */ }
            perform action a2 { doc /* participate in recurrent training @S874 */ }
            perform action a3 { doc /* require protective operating measures when emergency conditions affect airport or regional flow priorities @S968 */ }
        }
        part emissionsMetrics : EmissionsMetrics {
            perform action a0 { doc /* distinguish between actual reductions and delay transfers that only move fuel burn from one phase of flight to another @S857 */ }
        }
        part emissionsReduction : EmissionsReduction;
        part enRouteConstraints : EnRouteConstraints {
            perform action a0 { doc /* influence airport rates @S608 */ }
        }
        part endTime : EndTime;
        part engine : Engine {
            perform action a0 { doc /* running in queues @S855 */ }
        }
        part equipmentAvailability : EquipmentAvailability {
            perform action a0 { doc /* can change the sequence @S211 */ }
        }
        part equipmentFaults : EquipmentFaults {
            perform action a0 { doc /* affect the planned treatment rate @S383 */ }
        }
        part equipmentUnserviceability : EquipmentUnserviceability;
        part equityConcerns : EquityConcerns;
        part escalation : Escalation;
        part estimatedRecoveryTime : EstimatedRecoveryTime;
        part eventPart : Event {
            perform action a0 { doc /* may introduce foreign object debris @S643 */ }
        }
        part exceptionProcessing : ExceptionProcessing {
            perform action a0 { doc /* preserve a usable common operating picture @S516 */ }
            perform action a1 { doc /* exposing conditions that can change the departure plan @S516 */ }
        }
        part exceptionRecord : ExceptionRecord {
            perform action a0 { doc /* carries the affected flight, stand, readiness milestone, estimated recovery time, confidence level, and accountable operational role @S518 */ }
        }
        part excessHolding : ExcessHolding {
            perform action a0 { doc /* increases fuel burn, controller workload, and the likelihood of unplanned diversion @S406 */ }
        }
        part exercise : Exercise {
            perform action a0 { doc /* shall include participants from tower, ramp, airline operations, handling, airport operations, network coordination, meteorology, data governance, and system support functions @S881 */ }
        }
        part exercises : Exercises {
            perform action a0 { doc /* shall cover transitions among Normal Operations, Adverse Weather Mode, Capacity Reduction State, Recovery Phase, Contingency Fallback State, and Slot Compliance State @S882 */ }
        }
        part expansionBeyondThePilotAirports : ExpansionBeyondThePilotAirports {
            perform action a0 { doc /* occur in waves that group airports by interface maturity, traffic dependency, stakeholder readiness, and available support capacity @S909 */ }
        }
        part expectedBenefit : ExpectedBenefit;
        part expectedCapacity : ExpectedCapacity;
        part expectedCruiseProfiles : ExpectedCruiseProfiles;
        part expectedDuration : ExpectedDuration;
        part failures : Failures {
            perform action a0 { doc /* occur during capacity constrained operations @S928 */ }
        }
        part findings : Findings {
            perform action a0 { doc /* feed adjustments to tolerance values, reason code definitions, and training material, subject to change control @S810 */ }
        }
        part firstIncrement : FirstIncrement {
            perform action a0 { doc /* shall establish the core operational baseline for the Regional Flow Manager, Network Operations Liaison, Data Governance Steward, and System Support Engineer in a controlled production environment @S889 */ }
        }
        part flexibleUseAirspace : FlexibleUseAirspace {
            perform action a0 { doc /* accommodate rerouting, holding relief, or shortened recovery paths @S511 */ }
        }
        part flight : Flight {
            perform action a0 { doc /* protect a connection, crew limit, or network rotation @S284 */ }
            perform action a1 { doc /* requires treatment @S295 */ }
            perform action a2 { doc /* is waiting for pad access @S295 */ }
            perform action a3 { doc /* miss their Calculated Takeoff Time @S297 */ }
            perform action a4 { doc /* can accept a later Calculated Takeoff Time @S632 */ }
            perform action a5 { doc /* can exchange its assigned demand position without reducing declared capacity or creating an unfair priority change @S666 */ }
            perform action a6 { doc /* reducing declared capacity @S666 */ }
            perform action a7 { doc /* creating an unfair priority change @S666 */ }
            perform action a8 { doc /* receive a favorable Calculated Takeoff Time @S744 */ }
            exhibit state modes {
                state s0 { doc /* Slot Compliance State @S791 */ }
                state s1 { doc /* cancelled @S791 */ }
                state s2 { doc /* compliant @S791 */ }
                state s3 { doc /* early @S791 */ }
                state s4 { doc /* exempted @S791 */ }
                state s5 { doc /* exempted from compliance monitoring @S265 */ }
                state s6 { doc /* frozen @S265 */ }
                state s7 { doc /* late @S791 */ }
                state s8 { doc /* non-recoverable by delay @S623 */ }
                state s9 { doc /* pending review @S791 */ }
                state s10 { doc /* physically parked @S570 */ }
                state s11 { doc /* proposed @S265 */ }
                state s12 { doc /* released for taxi @S295 */ }
                state s13 { doc /* substituted @S791 */ }
                state s14 { doc /* technically serviceable @S570 */ }
                state s15 { doc /* unavailable for normal passenger, baggage, or crew movement decisions @S570 */ }
                state s16 { doc /* under a customs hold @S570 */ }
                state s17 { doc /* under negotiation @S265 */ }
                state s18 { doc /* under treatment @S295 */ }
                state s19 { doc /* waiting for pad access @S295 */ }
            }
        }
        part flightDataExchange : FlightDataExchange {
            perform action a0 { doc /* provide the data feeds needed to maintain a current and consistent operational picture @S018 */ }
            perform action a1 { doc /* provide managed integration points with external systems @S033 */ }
            perform action a2 { doc /* normalizes flight identifiers, aircraft types, routing fields, and planned operating times @S052 */ }
            perform action a3 { doc /* provides current flight intent data @S278 */ }
            perform action a4 { doc /* distributes only the approved operational result to downstream services that need to update schedules, metering, or airport resource plans @S638 */ }
            perform action a5 { doc /* publishes revised Flight Intent Message content @S684 */ }
            perform action a6 { doc /* validate Flight Intent Message content @S827 */ }
            perform action a7 { doc /* accept richer intent data, including improved route options, expected cruise profiles, and updated departure readiness information @S940 */ }
        }
        part flightIntentMessage : FlightIntentMessage;
        part flightIntentMessageStatus : FlightIntentMessageStatus;
        part flights : Flights {
            perform action a0 { doc /* require baggage reconciliation @S519 */ }
        }
        part flowManagement : FlowManagement {
            perform action a0 { doc /* act @S331 */ }
        }
        part flowManagementMeasure : FlowManagementMeasure {
            perform action a0 { doc /* would absorb it @S460 */ }
        }
        part flowManagementPolicyData : FlowManagementPolicyData;
        part flowMeasures : FlowMeasures {
            perform action a0 { doc /* affect sector workload, runway demand, and controller tactical flexibility @S865 */ }
        }
        part flowStaff : FlowStaff;
        part fluidLimitations : FluidLimitations;
        part forecastCapacity : ForecastCapacity {
            perform action a0 { doc /* materializes @S070 */ }
        }
        part forecastConfidence : ForecastConfidence {
            perform action a0 { doc /* decreases below the configured threshold @S121 */ }
        }
        part forecastProduct : ForecastProduct {
            perform action a0 { doc /* arrives late @S111 */ }
            perform action a1 { doc /* fails validation @S111 */ }
        }
        part foreignObjectDebrisChecks : ForeignObjectDebrisChecks {
            perform action a0 { doc /* cover paved stand surfaces, jet bridge wheel paths, towbar storage locations, belt loader positions, fueling lanes, and adjacent drainage grates @S644 */ }
        }
        part freezeHorizon : FreezeHorizon {
            perform action a0 { doc /* expires @S260 */ }
        }
        part freezingPrecipitation : FreezingPrecipitation {
            perform action a0 { doc /* make untreated ground movement unreliable @S371 */ }
        }
        part freshnessBreaches : FreshnessBreaches;
        part freshnessIndicators : FreshnessIndicators {
            perform action a0 { doc /* include the time of last accepted update, the maximum permitted age, and a visual state that distinguishes current, aging, stale, and unavailable data @S823 */ }
            exhibit state modes {
                state s0 { doc /* aging @S823 */ }
                state s1 { doc /* current @S823 */ }
                state s2 { doc /* stale @S823 */ }
                state s3 { doc /* unavailable @S823 */ }
            }
        }
        part fuelHydrantPoint : FuelHydrantPoint {
            exhibit state modes {
                state s0 { doc /* unavailable @S446 */ }
            }
        }
        part fuelLimitations : FuelLimitations {
            perform action a0 { doc /* make continued flight or extended holding undesirable @S498 */ }
        }
        part fuelMargins : FuelMargins {
            perform action a0 { doc /* become critical @S413 */ }
        }
        part fuelVehicleHolds : FuelVehicleHolds {
            perform action a0 { doc /* affect the tactical plan @S449 */ }
            perform action a1 { doc /* delaying off-block readiness @S449 */ }
        }
        part fuelingConstraint : FuelingConstraint {
            exhibit state modes {
                state s0 { doc /* active @S450 */ }
            }
        }
        part fuelingProviders : FuelingProviders;
        part fullRegionalDeployment : FullRegionalDeployment;
        part futureReleases : FutureReleases {
            exhibit state modes {
                state s0 { doc /* shadow mode @S959 */ }
            }
        }
        part gate : Gate {
            exhibit state modes {
                state s0 { doc /* unavailable @S472 */ }
            }
        }
        part gateBridge : GateBridge {
            exhibit state modes {
                state s0 { doc /* unavailable @S446 */ }
            }
        }
        part gateConflictDetector : GateConflictDetector {
            perform action a0 { doc /* provide additional indicators of emerging capacity loss and operational imbalance @S019 */ }
            perform action a1 { doc /* alerts the Ramp Control Lead @S210 */ }
            perform action a2 { doc /* warns when continued stand holding would block an inbound allocation or create a conflict with a planned equipment move @S364 */ }
            perform action a3 { doc /* produces the Gate Reopening Memo @S386 */ }
            perform action a4 { doc /* highlights stand conflicts that would undermine a proposed departure recovery plan or compress arrival unloading capacity @S439 */ }
            perform action a5 { doc /* checks whether the congestion can be relieved by resequencing adjacent stands @S459 */ }
            perform action a6 { doc /* compares planned arrivals, planned departures, assigned gates, towing availability, and published stand status @S468 */ }
            perform action a7 { doc /* identify conflicts that would otherwise be hidden inside local spreadsheets @S468 */ }
            perform action a8 { doc /* flags conflicts between diversion parking requirements and planned turnarounds, including cases where a short-duration stand occupancy would still disrupt a critical departure bank @S509 */ }
            perform action a9 { doc /* identifies cases where an aircraft assigned to a contact gate would cause less overall delay than a nominally available remote stand with inadequate passenger transfer capacity @S558 */ }
            perform action a10 { doc /* uses border status and apron occupancy evidence @S582 */ }
            perform action a11 { doc /* distinguish a true gate conflict from a temporary clearance delay @S582 */ }
            perform action a12 { doc /* checks readiness status against aircraft allocation, towing activity, and adjacent stand occupancy @S657 */ }
            perform action a13 { doc /* identify conflicts @S657 */ }
        }
        part gateOrStandDecision : GateOrStandDecision {
            perform action a0 { doc /* changes runway sequence assumptions, expected taxi duration, or a departure metering commitment @S475 */ }
        }
        part gateRecoveryAction : GateRecoveryAction {
            perform action a0 { doc /* would improve one bank of departures @S479 */ }
            perform action a1 { doc /* consume scarce apron capacity @S479 */ }
        }
        part governance : Governance {
            perform action a0 { doc /* should favor transparent decision making, timely challenge by affected parties, documented resolution of disputes, and continuous improvement through training, exercises, and post-operations review @S983 */ }
        }
        part groundDelayProgram : GroundDelayProgram {
            perform action a0 { doc /* may become necessary @S067 */ }
            perform action a1 { doc /* meters selected arrivals @S398 */ }
            perform action a2 { doc /* reduced airborne holding @S842 */ }
            perform action a3 { doc /* creating excessive departure congestion at constrained airports @S842 */ }
            exhibit state modes {
                state s0 { doc /* active @S136,S227 */ }
                state s1 { doc /* in effect @S424 */ }
            }
        }
        part groundDelayProgramDecisions : GroundDelayProgramDecisions;
        part groundDelayProgramParameters : GroundDelayProgramParameters;
        part groundEquipment : GroundEquipment {
            exhibit state modes {
                state s0 { doc /* available @S473 */ }
            }
        }
        part groundHandlingDispatcher : GroundHandlingDispatcher {
            perform action a0 { doc /* participate @S040 */ }
            perform action a1 { doc /* represent local airport, tower, ramp, handling, and winter operations considerations @S040 */ }
            perform action a2 { doc /* confirms whether planned handling teams and equipment coverage are sufficient for the expected concentration of turns in each apron area @S064 */ }
            perform action a3 { doc /* confirms that handling resource assumptions are current in the Handling Resource Planner @S091 */ }
            perform action a4 { doc /* escalates material deviations through the Airport Duty Manager @S091 */ }
            perform action a5 { doc /* sends the Crew Bus Delay Slip @S140 */ }
            perform action a6 { doc /* updating servicing completion, baggage readiness, staffing limitation, and equipment availability milestones @S158 */ }
            perform action a7 { doc /* updates handling milestones @S261 */ }
            perform action a8 { doc /* updates boarding, loading, door closure, and tow readiness milestones through the operational interface @S292 */ }
            perform action a9 { doc /* updates the Handling Resource Planner with expected service completion times @S302 */ }
            perform action a10 { doc /* updates remaining fluid inventory and truck serviceability @S383 */ }
            perform action a11 { doc /* uses the Handling Resource Planner view @S438 */ }
            perform action a12 { doc /* compare planned off-block demand with available servicing capacity at affected stands @S438 */ }
            perform action a13 { doc /* confirm stand access, towing resources, refueling constraints, and unloading capacity through the Handling Resource Planner @S508 */ }
            perform action a14 { doc /* uses the tag list @S519 */ }
            perform action a15 { doc /* confirm which flights require baggage reconciliation @S519 */ }
            perform action a16 { doc /* sends the Towbar Shortage Report @S523 */ }
            perform action a17 { doc /* verifies that bus assignments do not conflict with baggage, catering, fueling, or crew transport movements on the same apron corridor @S550 */ }
            perform action a18 { doc /* assigns qualified personnel to perform apron sweeps during planned turnaround milestones and after any event that may introduce foreign object debris @S643 */ }
            perform action a19 { doc /* updates the Handling Resource Planner @S653 */ }
            perform action a20 { doc /* have named accountable implementation contacts @S893 */ }
            perform action a21 { doc /* maintaining accurate surface and handling status @S966 */ }
        }
        part groundHandlingPersonnel : GroundHandlingPersonnel {
            perform action a0 { doc /* confirming that resource constraints are represented accurately @S869 */ }
        }
        part groundMovement : GroundMovement {
            perform action a0 { doc /* begins @S657 */ }
        }
        part groundPowerUnit : GroundPowerUnit {
            exhibit state modes {
                state s0 { doc /* unavailable @S446 */ }
            }
        }
        part groundServiceProviders : GroundServiceProviders {
            perform action a0 { doc /* participating in the concept @S044 */ }
        }
        part groups : Groups {
            perform action a0 { doc /* require assisted transfer @S478 */ }
        }
        part handlerDispatch : HandlerDispatch {
            perform action a0 { doc /* affects feasibility @S301 */ }
        }
        part handlerException : HandlerException {
            perform action a0 { doc /* changes the Airport Acceptance Rate or a regulated arrival sequence @S535 */ }
        }
        part handlerExceptions : HandlerExceptions;
        part handlingCoordinationCalls : HandlingCoordinationCalls;
        part handlingResourcePlanner : HandlingResourcePlanner {
            perform action a0 { doc /* compares the demand curve with available ground resources @S065 */ }
            perform action a1 { doc /* flags time bands where aircraft turn performance is likely to reduce stand availability @S065 */ }
            perform action a2 { doc /* are correlated by the Handling Resource Planner with stand occupancy, baggage readiness, catering status, and boarding progress @S141 */ }
            perform action a3 { doc /* provides the shared planning basis for baggage, catering, cleaning, boarding support, and towing resources that affect apron readiness @S212 */ }
            perform action a4 { doc /* maintains the operational view of dispatch teams, tow teams, ramp buses, belt loaders, high loaders, stairs, ground power units, air start units, and potable water equipment @S303 */ }
            perform action a5 { doc /* uses the Stand Tow Request Form @S304 */ }
            perform action a6 { doc /* reserve towing capacity @S304 */ }
            perform action a7 { doc /* test whether the requested movement can be completed before the proposed Target Off Block Time @S304 */ }
            perform action a8 { doc /* reports a constraint @S318 */ }
            perform action a9 { doc /* compares fluid inventory with scheduled deicing demand @S384 */ }
            perform action a10 { doc /* warns when a planned bank cannot be supported without resequencing @S384 */ }
            perform action a11 { doc /* evaluates whether additional ground handling resources can remove the constraint faster than a flow management measure would absorb it @S460 */ }
            perform action a12 { doc /* estimates whether the proposed turnaround can be recovered using available loading teams, passenger stairs, boarding bridges, cleaning crews, and baggage transfer resources @S477 */ }
            perform action a13 { doc /* assigns a severity level to the handler exception @S522 */ }
            perform action a14 { doc /* suppresses duplicate updates @S522 */ }
            perform action a15 { doc /* produces the Remote Stand Shuttle Count at regular operating intervals @S547 */ }
            perform action a16 { doc /* represent available passenger transfer capacity for remote stand activity @S547 */ }
            perform action a17 { doc /* validate resource quantities, task timing, and allocation identifiers against active operational reference data @S830 */ }
            perform action a18 { doc /* provide the main operational inputs for this capability @S947 */ }
        }
        part handlingResources : HandlingResources {
            perform action a0 { doc /* arrive after the aircraft ready time @S314 */ }
        }
        part handlingStatus : HandlingStatus {
            perform action a0 { doc /* changes @S158 */ }
        }
        part harborEastAirport : HarborEastAirport {
            perform action a0 { doc /* remains responsible for its local safety management, aerodrome certification obligations, and operational command authority @S027 */ }
        }
        part heldArrival : HeldArrival {
            perform action a0 { doc /* may proceed to normal turnaround handling @S568 */ }
        }
        part highFrequencyDomesticAirports : HighFrequencyDomesticAirports {
            perform action a0 { doc /* operating within shared terminal airspace @S001 */ }
        }
        part highPriorityIncident : HighPriorityIncident {
            perform action a0 { doc /* degrades a major function without stopping tactical coordination @S921 */ }
            perform action a1 { doc /* stopping tactical coordination @S921 */ }
        }
        part hold : Hold {
            exhibit state modes {
                state s0 { doc /* closed @S307 */ }
            }
        }
        part humanFactorsSafeguards : HumanFactorsSafeguards {
            perform action a0 { doc /* shall include workload monitoring, clear alert prioritization, consistent terminology, confirmation steps for high impact actions, and protection against silent mode changes @S884 */ }
        }
        part identityAccessService : IdentityAccessService {
            perform action a0 { doc /* provide governance, security, traceability, and performance measurement capabilities @S034 */ }
            perform action a1 { doc /* managed by the Identity Access Service @S126 */ }
            perform action a2 { doc /* is controlled by the Identity Access Service @S152 */ }
            perform action a3 { doc /* restricts entry of duty desk confirmations to authorized airport operations staff @S194 */ }
            perform action a4 { doc /* records each transaction in the Audit Event Ledger @S194 */ }
            perform action a5 { doc /* ensures that only users with the assigned operational role can approve frozen-time changes, manual exemptions, or retrospective corrections @S272 */ }
            perform action a6 { doc /* retain traceability of who viewed, changed, or approved diversion decisions @S515 */ }
            perform action a7 { doc /* enforces these visibility rules for Airport CDM Portal, Digital Briefing Room, and application programming interfaces @S635 */ }
            perform action a8 { doc /* restricts readiness confirmation privileges to approved ramp, handling, and airport operations roles @S650 */ }
            perform action a9 { doc /* prevent unverified operational releases @S650 */ }
            perform action a10 { doc /* support rapid suspension of accounts @S781 */ }
            perform action a11 { doc /* records the authorizing incident reference and expiry time @S783 */ }
            perform action a12 { doc /* provided by the Identity Access Service @S793 */ }
            perform action a13 { doc /* must support traceability, least-privilege access, and after-action accountability for all operationally significant changes @S981 */ }
        }
        part improvedRouteOptions : ImprovedRouteOptions;
        part inboundAircraft : InboundAircraft {
            perform action a0 { doc /* occupying gates needed for recovery flights @S416 */ }
        }
        part inboundDemand : InboundDemand {
            perform action a0 { doc /* will exceed the Airport Acceptance Rate within the planning horizon @S395 */ }
        }
        part incidentRecord : IncidentRecord {
            perform action a0 { doc /* captures the initial symptom, affected components, operational state, timeline, mitigation actions, data corrections, and supervisor decisions @S923 */ }
            perform action a1 { doc /* reference the Audit Event Ledger where user actions, configuration changes, interface events, or automated decisions are relevant to the investigation @S924 */ }
        }
        part incidentResponseTime : IncidentResponseTime;
        part incidents : Incidents;
        part inconsistentOperationalOutputs : InconsistentOperationalOutputs {
            perform action a0 { doc /* prevent users from relying on the normal decision support path without additional verification @S715 */ }
        }
        part individualAircraftRotations : IndividualAircraftRotations {
            perform action a0 { doc /* become the controlling problem @S467 */ }
        }
        part infeasibleRotation : InfeasibleRotation {
            exhibit state modes {
                state s0 { doc /* infeasible @S623 */ }
            }
        }
        part informationServices : InformationServices;
        part initialPilot : InitialPilot {
            perform action a0 { doc /* shall include one constrained primary airport and one less constrained regional airport @S892 */ }
        }
        part initialTraining : InitialTraining {
            perform action a0 { doc /* include classroom instruction, supervised workstation practice, scenario walkthroughs in the Digital Briefing Room, and observed operational shadowing @S878 */ }
        }
        part integratedTacticalManagementPosition : IntegratedTacticalManagementPosition {
            perform action a0 { doc /* presents a combined tactical view @S420 */ }
            perform action a1 { doc /* applies weather-driven capacity values @S434 */ }
            exhibit state modes {
                state s0 { doc /* Adverse Weather Mode @S435 */ }
                state s1 { doc /* Capacity Reduction State @S435 */ }
                state s2 { doc /* Contingency Fallback State @S435 */ }
                state s3 { doc /* Normal Operations @S435 */ }
                state s4 { doc /* Recovery Phase @S435 */ }
            }
        }
        part interfacePart : Interface;
        part interfaceCertification : InterfaceCertification;
        part interfacesToExternalSystems : InterfacesToExternalSystems {
            perform action a0 { doc /* validate identity @S037 */ }
            perform action a1 { doc /* receive authorized operational data @S037 */ }
            perform action a2 { doc /* publish approved coordination information @S037 */ }
            perform action a3 { doc /* maintain auditable records @S037 */ }
        }
        part intersectingTaxiRoutes : IntersectingTaxiRoutes;
        part investigations : Investigations {
            perform action a0 { doc /* can reconstruct event order across the Airport CDM Portal, Slot Allocation Engine, and Alert Distribution Hub @S778 */ }
        }
        part keyAssumptions : KeyAssumptions;
        part lakesideRegionalAirport : LakesideRegionalAirport {
            perform action a0 { doc /* remains responsible for its local safety management, aerodrome certification obligations, and operational command authority @S027 */ }
        }
        part landingRateStability : LandingRateStability {
            perform action a0 { doc /* may depend on short-lived runway configuration and approach spacing opportunities @S415 */ }
        }
        part lateAirportDrivenChanges : LateAirportDrivenChanges {
            perform action a0 { doc /* affected multiple flights @S809 */ }
        }
        part lateAirspaceCapacityChanges : LateAirspaceCapacityChanges {
            perform action a0 { doc /* can invalidate demand forecasts, slot allocations, and airport acceptance assumptions already in use @S340 */ }
        }
        part lateOperationalChanges : LateOperationalChanges;
        part laterComparisons : LaterComparisons {
            perform action a0 { doc /* use a single reference record @S052 */ }
        }
        part laterReview : LaterReview {
            perform action a0 { doc /* can distinguish data noise from operational decisions @S537 */ }
            perform action a1 { doc /* can distinguish operational judgment from system enforcement @S683 */ }
            perform action a2 { doc /* distinguish operational delay from data latency @S792 */ }
        }
        part latestSweepConfirmation : LatestSweepConfirmation {
            perform action a0 { doc /* remains valid through passenger boarding completion, equipment removal, door closure, and pushback coordination @S662 */ }
            exhibit state modes {
                state s0 { doc /* valid @S662 */ }
            }
        }
        part learningModels : LearningModels;
        part legalityIndicators : LegalityIndicators {
            perform action a0 { doc /* describe whether a proposed departure, arrival, or aircraft swap remains feasible within declared crew duty limits @S618 */ }
        }
        part lessConstrainedRegionalAirport : LessConstrainedRegionalAirport;
        part lifeSafety : LifeSafety {
            perform action a0 { doc /* requires immediate action @S784 */ }
        }
        part lightingPerformance : LightingPerformance {
            perform action a0 { doc /* limits night or low-visibility operations @S694 */ }
        }
        part limitedGateBuffers : LimitedGateBuffers;
        part loadingPositions : LoadingPositions;
        part localBusinessDecisions : LocalBusinessDecisions {
            perform action a0 { doc /* affected the outcome @S854 */ }
        }
        part localCapacity : LocalCapacity {
            exhibit state modes {
                state s0 { doc /* saturated @S938 */ }
            }
        }
        part localCondition : LocalCondition {
            perform action a0 { doc /* changes runway availability, taxi routing, or apron access @S193 */ }
        }
        part localCoordinationAgreements : LocalCoordinationAgreements {
            perform action a0 { doc /* are allowed by the Business Rules Registry and local coordination agreements @S055 */ }
        }
        part localCoordinationDecision : LocalCoordinationDecision {
            perform action a0 { doc /* affects capacity or surface flow @S186 */ }
        }
        part localDecisions : LocalDecisions {
            perform action a0 { doc /* can quickly create airborne holding, missed departure opportunities, and uneven delay distribution across the Meridian region @S008 */ }
        }
        part localDutyCoordination : LocalDutyCoordination {
            perform action a0 { doc /* has established the airport position @S191 */ }
        }
        part localObservations : LocalObservations {
            perform action a0 { doc /* differ materially from the automated weather interpretation @S116 */ }
        }
        part localResequencing : LocalResequencing {
            perform action a0 { doc /* threatens to erode the planned departure rate in the Airport Capacity Plan @S286 */ }
        }
        part localSequencingConstraints : LocalSequencingConstraints {
            perform action a0 { doc /* affect the North Runway Meter and South Runway Meter @S061 */ }
        }
        part localStakeholders : LocalStakeholders {
            perform action a0 { doc /* accepted by local stakeholders @S894 */ }
        }
        part localTool : LocalTool {
            exhibit state modes {
                state s0 { doc /* integrated through an approved interface @S903 */ }
                state s1 { doc /* replaced by a Regional Flow Platform function @S903 */ }
                state s2 { doc /* retained for read-only reference @S903 */ }
                state s3 { doc /* retired @S903 */ }
            }
        }
        part localTools : LocalTools {
            perform action a0 { doc /* shall remain the authoritative source @S905 */ }
        }
        part localTroubleshootingDetails : LocalTroubleshootingDetails {
            perform action a0 { doc /* crowding the regional view @S528 */ }
        }
        part localUsers : LocalUsers {
            perform action a0 { doc /* enter operational decisions through the Airport CDM Portal @S907 */ }
            perform action a1 { doc /* avoid reintroducing uncontrolled parallel records that undermine common situational awareness @S907 */ }
            perform action a2 { doc /* reintroducing uncontrolled parallel records that undermine common situational awareness @S907 */ }
        }
        part locations : Locations {
            perform action a0 { doc /* participate in joint procedure development @S891 */ }
        }
        part lowConfidenceWeatherForecasts : LowConfidenceWeatherForecasts {
            perform action a0 { doc /* remain visible to users @S120 */ }
        }
        part lowSurfaceTemperatureForecasts : LowSurfaceTemperatureForecasts {
            perform action a0 { doc /* make untreated ground movement unreliable @S371 */ }
        }
        part machineAssistedRecoveryOptions : MachineAssistedRecoveryOptions {
            perform action a0 { doc /* support the Recovery Phase @S951 */ }
            perform action a1 { doc /* proposing coordinated actions that balance runway throughput, sector loading, stand availability, and airline priorities @S951 */ }
        }
        part maintenanceRequirements : MaintenanceRequirements {
            perform action a0 { doc /* make continued flight or extended holding undesirable @S498 */ }
        }
        part mandatoryFieldChecks : MandatoryFieldChecks;
        part manualCorrections : ManualCorrections;
        part manualSlotProcedures : ManualSlotProcedures {
            perform action a0 { doc /* preserve the most recent valid Calculated Takeoff Time @S723 */ }
        }
        part markedTaxilane : MarkedTaxilane {
            exhibit state modes {
                state s0 { doc /* unavailable @S446 */ }
            }
        }
        part marshallingStaff : MarshallingStaff {
            exhibit state modes {
                state s0 { doc /* available @S473 */ }
            }
        }
        part maximumPermittedAge : MaximumPermittedAge;
        part maximumQueueLength : MaximumQueueLength;
        part medicalPriorityAircraft : MedicalPriorityAircraft {
            perform action a0 { doc /* requires airport-level coordination before landing @S496 */ }
            perform action a1 { doc /* landing @S496 */ }
        }
        part mediumAndLowPriorityIncidents : MediumAndLowPriorityIncidents;
        part meridianInternationalAirport : MeridianInternationalAirport {
            perform action a0 { doc /* remains responsible for its local safety management, aerodrome certification obligations, and operational command authority @S027 */ }
        }
        part meridianRegion : MeridianRegion;
        part meridianRegionalCapability : MeridianRegionalCapability {
            perform action a0 { doc /* must support rapid development of a Tactical Regulation Proposal and consistent communication of the resulting Ground Delay Program @S022 */ }
            perform action a1 { doc /* must help stakeholders restore scheduled flow @S023 */ }
            perform action a2 { doc /* monitoring Target Off Block Time, Calculated Takeoff Time, and Slot Compliance State performance @S023 */ }
            perform action a3 { doc /* provides a shared coordination layer @S028 */ }
            perform action a4 { doc /* does not replace statutory air traffic control, airport operator control rooms, airline operational control centers, or ground handling dispatch systems @S028 */ }
            exhibit state modes {
                state s0 { doc /* Adverse Weather Mode @S022 */ }
                state s1 { doc /* Capacity Reduction State @S022 */ }
                state s2 { doc /* Recovery Phase @S023 */ }
            }
        }
        part meridianRegionalOperation : MeridianRegionalOperation {
            perform action a0 { doc /* used by the Meridian regional operation @S323 */ }
        }
        part meteorologyBriefingOfficer : MeteorologyBriefingOfficer {
            perform action a0 { doc /* participate @S041 */ }
            perform action a1 { doc /* provides the morning weather outlook with emphasis on wind trend, ceiling, visibility, convective risk, temperature limits, and confidence over the planning horizon @S056 */ }
            perform action a2 { doc /* produces the Storm Cell Snapshot @S085 */ }
            perform action a3 { doc /* briefs forecast confidence, timing risk, and expected operational impact in the Digital Briefing Room using data supplied through the Weather Ingest Gateway @S086 */ }
            perform action a4 { doc /* using data supplied through the Weather Ingest Gateway @S086 */ }
            perform action a5 { doc /* states the trigger conditions that would justify moving from Normal Operations to Adverse Weather Mode @S087 */ }
            perform action a6 { doc /* reviews degraded weather inputs @S112 */ }
            perform action a7 { doc /* applied by the Meteorology Briefing Officer @S119 */ }
            perform action a8 { doc /* uses the portal workspace @S163 */ }
            perform action a9 { doc /* attach weather interpretation, forecast confidence, and expected timing of operational impacts @S163 */ }
            perform action a10 { doc /* without replacing the authoritative weather source @S163 */ }
            perform action a11 { doc /* confirms the trigger conditions in the Digital Briefing Room @S372 */ }
            perform action a12 { doc /* verifies weather impacts shown from the Weather Ingest Gateway @S434 */ }
            perform action a13 { doc /* maintains rapidly updated forecast information @S512 */ }
            perform action a14 { doc /* own operational weather classification inputs accepted by the Weather Ingest Gateway @S819 */ }
            perform action a15 { doc /* support interpretation of emissions results by identifying periods when weather routing or convective avoidance dominated fuel performance @S858 */ }
            perform action a16 { doc /* identifying periods when weather routing or convective avoidance dominated fuel performance @S858 */ }
            perform action a17 { doc /* explain weather uncertainty in operational terms @S873 */ }
            perform action a18 { doc /* verify that the Weather Ingest Gateway supports the assumptions used during briefings @S873 */ }
        }
        part meteringAction : MeteringAction {
            perform action a0 { doc /* affects a regulated flight @S457 */ }
        }
        part meteringAdjustment : MeteringAdjustment {
            perform action a0 { doc /* may reduce downstream disruption @S739 */ }
            perform action a1 { doc /* degrading the Airport Capacity Plan @S739 */ }
        }
        part meteringDecisions : MeteringDecisions {
            perform action a0 { doc /* require servicing activity to remain clear of an aircraft that is being held at stand @S361 */ }
        }
        part meteringHorizon : MeteringHorizon;
        part meteringProcess : MeteringProcess {
            perform action a0 { doc /* starts @S349 */ }
        }
        part meteringRules : MeteringRules {
            perform action a0 { doc /* require additional stand absorption @S355 */ }
        }
        part migrationPlan : MigrationPlan {
            perform action a0 { doc /* shall classify each local tool as retired, retained for read-only reference, integrated through an approved interface, or replaced by a Regional Flow Platform function @S903 */ }
        }
        part milestone : Milestone {
            perform action a0 { doc /* becomes stale @S166 */ }
            exhibit state modes {
                state s0 { doc /* stale @S166 */ }
            }
        }
        part militaryAirspaceLiaison : MilitaryAirspaceLiaison {
            perform action a0 { doc /* participate @S041 */ }
            perform action a1 { doc /* confirms whether shared airspace assumptions remain valid for the morning @S059 */ }
            perform action a2 { doc /* identifies any conditional availability that must be treated as uncertain @S059 */ }
            perform action a3 { doc /* confirms military airspace availability assumptions @S093 */ }
            perform action a4 { doc /* alerts the Regional Flow Manager when civil routing options may be constrained @S093 */ }
            perform action a5 { doc /* sends the Temporary Restriction Notice @S325 */ }
            perform action a6 { doc /* confirming the activation window, affected volume, controlling authority, and any published contingency conditions @S325 */ }
            perform action a7 { doc /* confirm the active interpretation of the restriction @S345 */ }
            perform action a8 { doc /* can mark an airspace release or closure assumption for review @S433 */ }
            perform action a9 { doc /* states whether flexible use airspace can be adjusted to accommodate rerouting, holding relief, or shortened recovery paths @S511 */ }
            perform action a10 { doc /* confirms whether conditional route availability changes the effective capacity @S609 */ }
        }
        part militaryTrainingAreas : MilitaryTrainingAreas {
            perform action a0 { doc /* also create recurring sector loading constraints @S006 */ }
        }
        part minorTimeBasedSequenceAdjustment : MinorTimeBasedSequenceAdjustment {
            perform action a0 { doc /* moves delay to upstream departure points rather than to airborne holding near Meridian @S397 */ }
        }
        part missingEquipment : MissingEquipment {
            perform action a0 { doc /* affects a flight inside the active departure planning horizon @S524 */ }
            perform action a1 { doc /* blocks a higher-priority aircraft movement @S524 */ }
        }
        part model : Model {
            perform action a0 { doc /* uses time thresholds, qualification flags, and pairing feasibility status @S619 */ }
            perform action a1 { doc /* does not require names, pay rules, hotel arrangements, or internal crew roster details @S619 */ }
        }
        part monitoredRunwayLightingStatus : MonitoredRunwayLightingStatus {
            perform action a0 { doc /* affects a declared operating configuration @S606 */ }
        }
        part monthlyAvailability : MonthlyAvailability;
        part movement : Movement {
            perform action a0 { doc /* begins @S663 */ }
        }
        part namedOperationalUser : NamedOperationalUser {
            perform action a0 { doc /* shall authenticate with an individually assigned identity @S764 */ }
            perform action a1 { doc /* accessing the Airport CDM Portal, Digital Briefing Room, or any operational console @S764 */ }
        }
        part networkCoordination : NetworkCoordination;
        part networkOperationsLiaison : NetworkOperationsLiaison {
            perform action a0 { doc /* participate @S039 */ }
            perform action a1 { doc /* align airline intentions, schedule constraints, and slot management decisions with the shared plan @S039 */ }
            perform action a2 { doc /* coordinates with adjacent network units @S083 */ }
            perform action a3 { doc /* confirms that regional measures remain compatible with upstream and downstream flow constraints @S083 */ }
            perform action a4 { doc /* records external coordination outcomes in the Collaborative Decision Log @S084 */ }
            perform action a5 { doc /* coordinates with external network positions @S339 */ }
            perform action a6 { doc /* coordinates with affected airline control centers @S413 */ }
            perform action a7 { doc /* reviews whether protecting a connecting passenger group supports wider network recovery or only transfers delay to a later sector @S480 */ }
            perform action a8 { doc /* coordinates downstream network effects, including alternate airport choices, aircraft swaps, crew legality risk, and rebooking pressure @S510 */ }
            perform action a9 { doc /* monitors aggregate displacement from approved substitutions @S674 */ }
            perform action a10 { doc /* ensure that one carrier's recovery action does not destabilize the wider network plan @S674 */ }
            perform action a11 { doc /* coordinate regional constraints, sector load conditions, and network measures @S871 */ }
            perform action a12 { doc /* using the Sector Load Monitor and Common Situation Display @S871 */ }
            perform action a13 { doc /* retain operational command authority during support activity @S917 */ }
            perform action a14 { doc /* see upstream demand pressure earlier @S938 */ }
            perform action a15 { doc /* negotiate measures before local capacity is saturated @S938 */ }
        }
        part nominalFleetOfEquipment : NominalFleetOfEquipment {
            perform action a0 { doc /* support one stand cluster @S309 */ }
            perform action a1 { doc /* leaving another cluster unable to dispatch departures at the planned rate @S309 */ }
        }
        part normalOperations : NormalOperations {
            perform action a0 { doc /* drive stakeholder participation and operating procedures @S047 */ }
        }
        part normalTechnicalService : NormalTechnicalService {
            perform action a0 { doc /* resume @S927 */ }
        }
        part northRunwayMeter : NorthRunwayMeter {
            perform action a0 { doc /* provide additional indicators of emerging capacity loss and operational imbalance @S019 */ }
            perform action a1 { doc /* receive runway-specific capacity values @S114 */ }
            perform action a2 { doc /* maintain separate queues @S280 */ }
            perform action a3 { doc /* maintain independent queue counts @S359 */ }
            perform action a4 { doc /* reduces the departure release rate @S454 */ }
            perform action a5 { doc /* support independent checks of queue length where surveillance coverage is available @S845 */ }
        }
        part northValleyAirport : NorthValleyAirport {
            perform action a0 { doc /* remains responsible for its local safety management, aerodrome certification obligations, and operational command authority @S027 */ }
        }
        part nullPart : Null {
            perform action a0 { doc /* are applied @S453 */ }
            perform action a1 { doc /* are generated @S458 */ }
            perform action a2 { doc /* can be relieved by resequencing adjacent stands @S459 */ }
            perform action a3 { doc /* resequencing adjacent stands @S459 */ }
            perform action a4 { doc /* is written to the Collaborative Decision Log and the Audit Event Ledger with the actor, timestamp, affected flight, and planning rationale @S466 */ }
            perform action a5 { doc /* have been reduced enough for individual aircraft rotations to become the controlling problem @S467 */ }
            perform action a6 { doc /* would otherwise be hidden inside local spreadsheets @S468 */ }
            perform action a7 { doc /* can be reopened quickly @S471 */ }
            perform action a8 { doc /* can be planned again for arrival handling, boarding, and connection recovery @S472 */ }
            perform action a9 { doc /* is reassigned @S473 */ }
            perform action a10 { doc /* is advised only when the gate or stand decision changes runway sequence assumptions, expected taxi duration, or a departure metering commitment @S475 */ }
            perform action a11 { doc /* can be recovered using available loading teams, passenger stairs, boarding bridges, cleaning crews, and baggage transfer resources @S477 */ }
            perform action a12 { doc /* using available loading teams, passenger stairs, boarding bridges, cleaning crews, and baggage transfer resources @S477 */ }
            perform action a13 { doc /* protecting a connecting passenger group @S480 */ }
            perform action a14 { doc /* supports wider network recovery @S480 */ }
            perform action a15 { doc /* only transfers delay to a later sector @S480 */ }
            perform action a16 { doc /* is revised only when the actor responsible for the turnaround confirms that the boarding, servicing, and ramp movement assumptions are achievable @S482 */ }
            perform action a17 { doc /* released from delayed turnarounds @S483 */ }
            perform action a18 { doc /* is declared for Normal Operations, Adverse Weather Mode, Capacity Reduction State, Recovery Phase, or Contingency Fallback State @S908 */ }
            perform action a19 { doc /* be declared only after the Regional Flow Manager confirms that operational benefits, safety constraints, cyber controls, and stakeholder obligations remain stable across multiple airports and traffic conditions @S911 */ }
            perform action a20 { doc /* is accepted into steady state support after the regional stabilization period @S912 */ }
            perform action a21 { doc /* remain protected at all times @S913 */ }
            perform action a22 { doc /* be raised so that the System Support Engineer can join the Digital Briefing Room without delay @S916 */ }
            perform action a23 { doc /* be classified by operational effect @S919 */ }
            perform action a24 { doc /* assigned to loss of common situational awareness, loss of slot computation, corruption of operational timing data, or failure of alert distribution during active traffic management @S919 */ }
            perform action a25 { doc /* be acknowledged within fifteen minutes @S920 */ }
            perform action a26 { doc /* is restored @S920 */ }
            perform action a27 { doc /* be acknowledged within thirty minutes @S921 */ }
            perform action a28 { doc /* be reviewed with the affected operational supervisor at least hourly @S921 */ }
            perform action a29 { doc /* be handled through the service queue @S922 */ }
            perform action a30 { doc /* provided at intervals appropriate to their operational impact and planned resolution path @S922 */ }
            perform action a31 { doc /* be used to preserve the operational context of major incidents when traffic management decisions are made while a technical degradation is present @S925 */ }
            perform action a32 { doc /* preserve the operational context of major incidents @S925 */ }
            perform action a33 { doc /* are made while a technical degradation is present @S925 */ }
            perform action a34 { doc /* be required for critical incidents, repeated high priority incidents, security related events, and failures that occur during capacity constrained operations @S928 */ }
            perform action a35 { doc /* assigned to named owners @S929 */ }
            perform action a36 { doc /* normally be scheduled during low demand night periods @S930 */ }
            perform action a37 { doc /* be coordinated with the Regional Flow Manager, Airport Duty Manager, Tower Supervisor, and affected Aircraft Operator Representative groups before approval @S930 */ }
            perform action a38 { doc /* be applied outside the standard window when needed to restore service, protect cyber security, or prevent material operational harm @S932 */ }
            perform action a39 { doc /* restore service @S932 */ }
            perform action a40 { doc /* protect cyber security @S932 */ }
            perform action a41 { doc /* prevent material operational harm @S932 */ }
            perform action a42 { doc /* be documented @S932 */ }
            perform action a43 { doc /* retrospectively approved @S932 */ }
            exhibit state modes {
                state s0 { doc /* Adverse Weather Mode @S464 */ }
                state s1 { doc /* Recovery Phase @S465 */ }
            }
        }
        part onCallSupportPosture : OnCallSupportPosture;
        part onboardingWave : OnboardingWave;
        part openBays : OpenBays;
        part operationalApprovalPrivileges : OperationalApprovalPrivileges;
        part operationalConcept : OperationalConcept {
            perform action a0 { doc /* treats each remote stand as an airside resource with a landside service dependency, not as an isolated parking position @S543 */ }
        }
        part operationalConstraint : OperationalConstraint {
            perform action a0 { doc /* changes the usable runway rate, taxi-out predictability, or the feasibility of the active demand plan @S696 */ }
        }
        part operationalDecision : OperationalDecision {
            perform action a0 { doc /* relied on it @S169 */ }
        }
        part operationalDelay : OperationalDelay {
            perform action a0 { doc /* exceeds the tolerance defined in the Business Rules Registry @S659 */ }
        }
        part operationalGroup : OperationalGroup {
            perform action a0 { doc /* receives the timing, constraint, and decision ownership information needed for its task @S505 */ }
        }
        part operationalNeed : OperationalNeed {
            perform action a0 { doc /* has ended @S782 */ }
        }
        part operationalParticipants : OperationalParticipants {
            perform action a0 { doc /* can see whether a flight is proposed, under negotiation, frozen, or exempted from compliance monitoring @S265 */ }
        }
        part operationalPlanningCycle : OperationalPlanningCycle;
        part operationalPlausibilityChecks : OperationalPlausibilityChecks;
        part operationalPositions : OperationalPositions;
        part operationalProcesses : OperationalProcesses;
        part operationalRationale : OperationalRationale;
        part operationalSafetyIssue : OperationalSafetyIssue {
            perform action a0 { doc /* requires earlier action @S207 */ }
        }
        part operationalSegregation : OperationalSegregation {
            perform action a0 { doc /* shall prevent a single user from creating, approving, and technically concealing a material change to a Ground Delay Program, Airport Acceptance Rate, or Tactical Regulation Proposal @S774 */ }
        }
        part operationalServiceManagement : OperationalServiceManagement {
            perform action a0 { doc /* begin when a deployed airport is accepted into steady state support after the regional stabilization period @S912 */ }
        }
        part operationalStaff : OperationalStaff;
        part operationalState : OperationalState {
            perform action a0 { doc /* move from Normal Operations to Adverse Weather Mode or Capacity Reduction State @S872 */ }
        }
        part operationalSupervisors : OperationalSupervisors {
            perform action a0 { doc /* have directed use of contingency procedures for nontechnical reasons @S934 */ }
        }
        part operationalUsers : OperationalUsers {
            perform action a0 { doc /* see only the detail required for recovery decisions @S490 */ }
            perform action a1 { doc /* share the same view of the accepted change @S685 */ }
            perform action a2 { doc /* understand why a capacity or delay estimate has changed @S945 */ }
        }
        part operator : Operator {
            perform action a0 { doc /* accept a later off-block time without causing crew, connection, or aircraft rotation impacts @S316 */ }
            perform action a1 { doc /* causing crew, connection, or aircraft rotation impacts @S316 */ }
            perform action a2 { doc /* cannot accept the proposed stand delay @S363 */ }
            perform action a3 { doc /* may disclose that a flight can accept a later Calculated Takeoff Time @S632 */ }
            perform action a4 { doc /* withhold the passenger revenue, maintenance cost, or network protection reason @S632 */ }
        }
        part operatorCoordinationRoles : OperatorCoordinationRoles {
            perform action a0 { doc /* act @S331 */ }
        }
        part operatorProfileHelpText : OperatorProfileHelpText;
        part operators : Operators;
        part outputs : Outputs {
            perform action a0 { doc /* must remain visible on the Common Situation Display @S095 */ }
        }
        part ownedDataElement : OwnedDataElement {
            perform action a0 { doc /* have a defined business meaning, allowed value range, update authority, retention class, and escalation contact @S821 */ }
        }
        part padDemand : PadDemand {
            perform action a0 { doc /* changes @S294 */ }
        }
        part padQueue : PadQueue {
            perform action a0 { doc /* falls below the configured threshold @S379 */ }
        }
        part padQueueControls : PadQueueControls {
            perform action a0 { doc /* assign aircraft to a deicing lane @S376 */ }
        }
        part parkedAircraft : ParkedAircraft;
        part participants : Participants {
            perform action a0 { doc /* can resolve conflicts without separate status calls @S391 */ }
            perform action a1 { doc /* continue coordination through the Digital Briefing Room @S720 */ }
            perform action a2 { doc /* record decisions in the Collaborative Decision Log @S720 */ }
            perform action a3 { doc /* understand they are decision-support indicators, not commands @S758 */ }
        }
        part participatingAircraftOperators : ParticipatingAircraftOperators {
            perform action a0 { doc /* agreed by the airport operator, regional authority, and participating aircraft operators @S779 */ }
        }
        part participatingOperationalRoles : ParticipatingOperationalRoles {
            perform action a0 { doc /* are understood by the participating operational roles @S050 */ }
        }
        part participatingOrganization : ParticipatingOrganization {
            perform action a0 { doc /* treat the operating picture as a shared operational asset rather than a local advisory product @S960 */ }
        }
        part participatingRoles : ParticipatingRoles;
        part party : Party {
            perform action a0 { doc /* alleges that governance rules were bypassed @S687 */ }
        }
        part passengerBoarding : PassengerBoarding {
            perform action a0 { doc /* cannot close until the last bus has arrived, unloaded, and cleared the stand area @S306 */ }
        }
        part passengerConnectionSensitivity : PassengerConnectionSensitivity;
        part passengerDisruptionInformation : PassengerDisruptionInformation {
            perform action a0 { doc /* can refine, but not replace, capacity and safety constraints in traffic flow decisions @S738 */ }
        }
        part passengerStatus : PassengerStatus {
            perform action a0 { doc /* would cause holdover time to be wasted @S385 */ }
        }
        part passengerTransportProviders : PassengerTransportProviders;
        part passengers : Passengers {
            exhibit state modes {
                state s0 { doc /* complete @S449 */ }
            }
        }
        part performanceAgainstServiceTargets : PerformanceAgainstServiceTargets;
        part performanceAnalyticsWarehouse : PerformanceAnalyticsWarehouse {
            perform action a0 { doc /* provide governance, security, traceability, and performance measurement capabilities @S034 */ }
            perform action a1 { doc /* retains the baseline inputs, capacity declarations, and approval timestamps @S074 */ }
            perform action a2 { doc /* can reconstruct the decision basis after operations @S123 */ }
            perform action a3 { doc /* compares submitted intents, issued constraints, actual off-block times, and achieved arrival outcomes @S148 */ }
            perform action a4 { doc /* improve recovery playbooks @S148 */ }
            perform action a5 { doc /* uses the recorded milestones and decision history @S173 */ }
            perform action a6 { doc /* compare planned outcomes with actual off-block, takeoff, landing, and stand events @S173 */ }
            perform action a7 { doc /* compares recorded duty coordination events with actual movement data @S197 */ }
            perform action a8 { doc /* identify delays, missed checks, and opportunities to improve local decision quality @S197 */ }
            perform action a9 { doc /* uses frozen targets, actual milestone timestamps, and audit records @S274 */ }
            perform action a10 { doc /* measure compliance, delay attribution, negotiation effectiveness, and rule quality after operations @S274 */ }
            perform action a11 { doc /* compares predicted and actual handling constraints @S322 */ }
            perform action a12 { doc /* improve standard service times @S322 */ }
            perform action a13 { doc /* identify chronic equipment shortages by stand group @S322 */ }
            perform action a14 { doc /* compares planned capacity, issued alerts, operator acknowledgements, and realized delay @S346 */ }
            perform action a15 { doc /* determine whether the restriction handling process supported timely and consistent decisions @S346 */ }
            perform action a16 { doc /* compares planned stand absorption, actual off block performance, and runway queue length @S370 */ }
            perform action a17 { doc /* verify that the agreed thresholds were not exceeded @S370 */ }
            perform action a18 { doc /* compares planned treatment throughput, actual pad occupancy, and departure compliance @S394 */ }
            perform action a19 { doc /* improve winter capacity assumptions for future events @S394 */ }
            perform action a20 { doc /* uses the recorded regulation history @S418 */ }
            perform action a21 { doc /* compare predicted holding, actual airborne delay, diversion outcomes, and achieved landing rates for continuous improvement of Meridian arrival management @S418 */ }
            perform action a22 { doc /* measures whether recovered gate assignments reduced missed connections, reduced secondary stand conflicts, and improved aircraft rotation stability during the Recovery Phase @S489 */ }
            perform action a23 { doc /* compares actual handling times, sector load, connection outcomes, and regulation changes against the recorded diversion plan @S514 */ }
            perform action a24 { doc /* support post-operations review @S514 */ }
            perform action a25 { doc /* compares escalated exceptions with actual off-block performance @S538 */ }
            perform action a26 { doc /* tune severity thresholds @S538 */ }
            perform action a27 { doc /* reduce nuisance alerts over time @S538 */ }
            perform action a28 { doc /* retains remote stand timing measures @S565 */ }
            perform action a29 { doc /* extends the remote stand performance concept by describing how border, customs, and apron sensing inputs become constraints in the daily operating plan @S566 */ }
            perform action a30 { doc /* describing how border, customs, and apron sensing inputs become constraints in the daily operating plan @S566 */ }
            perform action a31 { doc /* compares planned clearance assumptions with actual border release timing and apron availability @S590 */ }
            perform action a32 { doc /* improve future demand prediction and resource planning @S590 */ }
            perform action a33 { doc /* compares predicted sector pressure, actual airborne delay, and airport departure compliance @S616 */ }
            perform action a34 { doc /* tune Demand Prediction Service and Capacity Assessment Module @S616 */ }
            perform action a35 { doc /* may analyze anonymized patterns of legality constraints and recovery selections @S639 */ }
            perform action a36 { doc /* improve disruption playbooks @S639 */ }
            perform action a37 { doc /* uses aggregated readiness and contamination timing data @S665 */ }
            perform action a38 { doc /* identify recurring debris locations, inefficient sweep patterns, and opportunities for preventive maintenance @S665 */ }
            perform action a39 { doc /* uses completed infrastructure events @S712 */ }
            perform action a40 { doc /* measure delay attribution, capacity recovery time, and the accuracy of initial duration estimates @S712 */ }
            perform action a41 { doc /* receives the outage timeline, manual intervention record, and recovery milestones for inclusion in the Post Operations Report @S737 */ }
            perform action a42 { doc /* compares later delay outcomes with the logged rationale @S760 */ }
            perform action a43 { doc /* determine whether the advisory use of passenger disruption data improved recovery performance @S760 */ }
            perform action a44 { doc /* keeps the primary system function focused on safe, efficient, and transparent traffic flow management @S761 */ }
            perform action a45 { doc /* allowing airline recovery information to inform proportionate metering choices @S761 */ }
            perform action a46 { doc /* aggregate compliance outcomes by carrier, route group, regulation, airport operating configuration, and time band @S804 */ }
            perform action a47 { doc /* retain data quality measures, including validation failure rates, freshness breaches, manual corrections, and recurring ownership conflicts @S836 */ }
            perform action a48 { doc /* calculate delay absorption as the portion of expected airborne or terminal-area delay that is converted into controlled ground delay before departure @S839 */ }
            perform action a49 { doc /* apply approved fuel burn and emissions factors by aircraft category, operating phase, and delay location @S856 */ }
        }
        part performanceMeasurement : PerformanceMeasurement {
            perform action a0 { doc /* convert operational events into repeatable indicators that can be reviewed after each operating day @S838 */ }
        }
        part performanceMeasures : PerformanceMeasures {
            perform action a0 { doc /* identify data sources, calculation versions, confidence limits, and known exclusions @S861 */ }
        }
        part phasedIncrements : PhasedIncrements {
            perform action a0 { doc /* limit operational exposure @S888 */ }
            perform action a1 { doc /* progressively adding airports, interfaces, and decision support functions @S888 */ }
        }
        part pilotAirportSelection : PilotAirportSelection {
            perform action a0 { doc /* shall favor locations with stable operational leadership, representative traffic complexity, available surface surveillance data, and demonstrated willingness to participate in joint procedure development @S891 */ }
        }
        part plannedArrival : PlannedArrival {
            perform action a0 { doc /* would create an overlapping occupancy condition at a stand or adjacent service lane @S210 */ }
        }
        part plannedChangeWindows : PlannedChangeWindows;
        part plannedConnectionInterval : PlannedConnectionInterval {
            exhibit state modes {
                state s0 { doc /* valid @S571 */ }
            }
        }
        part plannedRemoteStand : PlannedRemoteStand;
        part plannedStaffingLimitations : PlannedStaffingLimitations {
            perform action a0 { doc /* could influence arrival or departure metering @S058 */ }
        }
        part planners : Planners {
            perform action a0 { doc /* can see how small changes in capacity would affect stand occupancy and departure queues @S069 */ }
            perform action a1 { doc /* can compare scheduled assumptions with actual passenger transfer and apron release performance @S565 */ }
        }
        part planningComponents : PlanningComponents {
            perform action a0 { doc /* use the same constraint description @S447 */ }
        }
        part positions : Positions {
            perform action a0 { doc /* remove multiple downstream conflicts rather than a single isolated delay @S471 */ }
            exhibit state modes {
                state s0 { doc /* blocked @S469 */ }
                state s1 { doc /* boarding @S469 */ }
                state s2 { doc /* cleaning @S469 */ }
                state s3 { doc /* occupied @S469 */ }
                state s4 { doc /* tow-ready @S469 */ }
            }
        }
        part possibleSecondaryEffectsOnConnectedFlightsAndSurfaceMovements : PossibleSecondaryEffectsOnConnectedFlightsAndSurfaceMovements;
        part postEventAssessment : PostEventAssessment {
            perform action a0 { doc /* compares proposed opportunities, actual movement times, exemption usage, and operator-level delay equity @S248 */ }
            perform action a1 { doc /* improve subsequent rule calibration @S248 */ }
        }
        part postEventReview : PostEventReview {
            perform action a0 { doc /* can compare planned sequencing with actual apron performance @S222 */ }
            perform action a1 { doc /* can distinguish operational necessity from avoidable volatility @S289 */ }
        }
        part postExerciseReviews : PostExerciseReviews {
            perform action a0 { doc /* shall use evidence from the Performance Analytics Warehouse and Audit Event Ledger @S887 */ }
            perform action a1 { doc /* improve procedures @S887 */ }
            perform action a2 { doc /* refine training materials @S887 */ }
            perform action a3 { doc /* confirm that human performance concerns are assigned to accountable owners @S887 */ }
        }
        part postIncidentReview : PostIncidentReview {
            perform action a0 { doc /* identify technical root cause, operational contributing factors, effectiveness of workarounds, user communication quality, and corrective actions assigned to named owners @S929 */ }
        }
        part postOperationsReport : PostOperationsReport {
            perform action a0 { doc /* can compare planned performance with actual outcomes @S074 */ }
            perform action a1 { doc /* present regional benefits alongside operational trade-offs @S862 */ }
        }
        part postOperationsReportOutputs : PostOperationsReportOutputs;
        part preTacticalCapacityReview : PreTacticalCapacityReview {
            perform action a0 { doc /* begins @S085 */ }
        }
        part precipitation : Precipitation {
            perform action a0 { doc /* can increase the probability of foreign object debris and surface contamination @S661 */ }
        }
        part predictedChangesToTargetOffBlockTime : PredictedChangesToTargetOffBlockTime;
        part predictedHoldingStacks : PredictedHoldingStacks {
            perform action a0 { doc /* form @S407 */ }
        }
        part predictedQueue : PredictedQueue {
            perform action a0 { doc /* exceeds the warning threshold @S366 */ }
        }
        part preferenceFields : PreferenceFields {
            exhibit state modes {
                state s0 { doc /* hidden @S631 */ }
                state s1 { doc /* mandatory @S631 */ }
                state s2 { doc /* optional @S631 */ }
            }
        }
        part preferredRoute : PreferredRoute;
        part primaryCapacityConstraint : PrimaryCapacityConstraint {
            perform action a0 { doc /* has begun to clear @S756 */ }
        }
        part primaryInternationalHub : PrimaryInternationalHub {
            perform action a0 { doc /* operating within shared terminal airspace @S001 */ }
        }
        part primaryWorkspace : PrimaryWorkspace {
            perform action a0 { doc /* presents the Common Situation Display with synchronized clocks, active operating state, airport demand, runway configuration, stand occupancy, and milestone status for each managed movement @S153 */ }
        }
        part principalDelayAbsorptionIndicator : PrincipalDelayAbsorptionIndicator {
            perform action a0 { doc /* report minutes absorbed at origin, minutes remaining in the arrival stream, and minutes transferred to surface queues within the region @S841 */ }
        }
        part priorityHandling : PriorityHandling {
            perform action a0 { doc /* does not overload approach sectors @S500 */ }
            perform action a1 { doc /* create unstable runway demand @S500 */ }
        }
        part productionIncidents : ProductionIncidents {
            perform action a0 { doc /* affecting the Regional Flow Platform, Airport CDM Portal, Slot Allocation Engine, Departure Metering Service, Arrival Regulation Console, and Alert Distribution Hub @S914 */ }
        }
        part projectedRecoveredDepartures : ProjectedRecoveredDepartures {
            perform action a0 { doc /* require a consolidated view of demand by departure fix @S484 */ }
        }
        part proposal : Proposal {
            exhibit state modes {
                state s0 { doc /* pending @S681 */ }
            }
        }
        part proposedDeparture : ProposedDeparture {
            exhibit state modes {
                state s0 { doc /* feasible @S618 */ }
            }
        }
        part proposedTargetOffBlockTimeValues : ProposedTargetOffBlockTimeValues {
            perform action a0 { doc /* are likely to cause runway or sector imbalance @S251 */ }
        }
        part proposingFunction : ProposingFunction {
            perform action a0 { doc /* assigned by the proposing function or authorized user @S264 */ }
        }
        part protectionAgainstSilentModeChanges : ProtectionAgainstSilentModeChanges;
        part pushbackFlow : PushbackFlow {
            perform action a0 { doc /* affects the departure plan @S184 */ }
        }
        part pushbackPlanning : PushbackPlanning {
            perform action a0 { doc /* continue for the affected stand @S654 */ }
        }
        part pushbackSequence : PushbackSequence {
            perform action a0 { doc /* depends on rapid equipment removal or immediate stand reuse @S213 */ }
        }
        part pushbackWindows : PushbackWindows {
            perform action a0 { doc /* give the flight crew, ramp team, and tower sequence a common expectation @S354 */ }
        }
        part qualifiedPersonnel : QualifiedPersonnel {
            perform action a0 { doc /* perform apron sweeps during planned turnaround milestones and after any event that may introduce foreign object debris @S643 */ }
        }
        part queueLengthPerformance : QueueLengthPerformance;
        part queueMetrics : QueueMetrics {
            perform action a0 { doc /* include maximum queue length, average queue length, time above threshold, and recovery time after a constraint is lifted @S846 */ }
        }
        part rampBuses : RampBuses {
            perform action a0 { doc /* influence feasibility for remote stands @S306 */ }
        }
        part rampControlLead : RampControlLead {
            perform action a0 { doc /* require a common basis for decisions rather than separate local views of the same operational picture @S011 */ }
            perform action a1 { doc /* participate @S040 */ }
            perform action a2 { doc /* represent local airport, tower, ramp, handling, and winter operations considerations @S040 */ }
            perform action a3 { doc /* reviews early stand readiness using information from the Ramp Movement Board, East Apron Sensor, West Apron Sensor, and handling coordination calls @S063 */ }
            perform action a4 { doc /* using information from the Ramp Movement Board, East Apron Sensor, West Apron Sensor, and handling coordination calls @S063 */ }
            perform action a5 { doc /* maintains the Ramp Movement Board in a state that supports reliable departure metering @S090 */ }
            perform action a6 { doc /* uses the Ramp Movement Board @S142 */ }
            perform action a7 { doc /* identify whether the proposed recovery action can be supported without creating surface congestion @S142 */ }
            perform action a8 { doc /* maintaining stand release readiness, apron movement conflicts, tug availability, and local pushback sequencing inputs in the portal @S159 */ }
            perform action a9 { doc /* reviews apron movement constraints with the duty desk @S184 */ }
            perform action a10 { doc /* maintains the operational sequence for pushbacks, stand exits, stand entries, and towing movements within the controlled apron area @S200 */ }
            perform action a11 { doc /* shall not release a pushback @S202 */ }
            perform action a12 { doc /* reconciling sensor data with visual and operational reports @S205 */ }
            perform action a13 { doc /* assigns priority to towing movements that remove a blocking aircraft, protect a confirmed departure sequence, or create capacity for an inbound aircraft with no equivalent stand option @S206 */ }
            perform action a14 { doc /* sends the Stand Tow Request Form @S208 */ }
            perform action a15 { doc /* coordinates with the Ground Handling Dispatcher @S211 */ }
            perform action a16 { doc /* confirm whether servicing progress, equipment availability, or staffing constraints can change the sequence @S211 */ }
            perform action a17 { doc /* reviews Handling Resource Planner constraints @S213 */ }
            perform action a18 { doc /* committing to a pushback sequence that depends on rapid equipment removal or immediate stand reuse @S213 */ }
            perform action a19 { doc /* escalates the condition to the Tower Supervisor and Airport Duty Manager for a coordinated mitigation decision @S218 */ }
            perform action a20 { doc /* increases spacing between pushbacks and towing movements @S219 */ }
            perform action a21 { doc /* account for slower ground servicing and reduced driver visibility @S219 */ }
            perform action a22 { doc /* may identify apron constraints through the Ramp Movement Board @S244 */ }
            perform action a23 { doc /* assesses whether the proposed off-block pattern is compatible with apron access, stand conflicts, and local movement restrictions @S262 */ }
            perform action a24 { doc /* coordinates pushback release priorities against stand conflicts, taxi lane constraints, and the runway demand visible in the Tower Sequence Manager @S283 */ }
            perform action a25 { doc /* reviews the proposed windows against apron congestion, towing activity, and aircraft readiness @S357 */ }
            perform action a26 { doc /* accepting them for local execution @S357 */ }
            perform action a27 { doc /* uses the queue card @S378 */ }
            perform action a28 { doc /* verify pad entry order @S378 */ }
            perform action a29 { doc /* authorizing a movement from the staging area @S378 */ }
            perform action a30 { doc /* coordinate every pad release with the Tower Supervisor @S387 */ }
            perform action a31 { doc /* verifies whether the condition blocks a single movement, a stand group, or a wider apron route @S446 */ }
            perform action a32 { doc /* coordinates stand reopening with the Ground Handling Dispatcher @S473 */ }
            perform action a33 { doc /* confirm stand access, towing resources, refueling constraints, and unloading capacity through the Handling Resource Planner @S508 */ }
            perform action a34 { doc /* confirms that each planned remote stand has an assigned aircraft route, safe passenger transfer path, and defined contingency for blocked apron movement @S545 */ }
            perform action a35 { doc /* uses the Towbar Shortage Report to determine whether remote stand aircraft can be repositioned without creating secondary apron congestion @S556 */ }
            perform action a36 { doc /* determine whether remote stand aircraft can be repositioned without creating secondary apron congestion @S556 */ }
            perform action a37 { doc /* defines the sweep areas by stand, taxilane, service road interface, and equipment staging zone so that each check has a clear spatial boundary @S642 */ }
            perform action a38 { doc /* sends the Apron Sweep Completion Note @S647 */ }
            perform action a39 { doc /* reviews unresolved hazards against active turnaround demand @S654 */ }
            perform action a40 { doc /* allowing pushback planning to continue for the affected stand @S654 */ }
            perform action a41 { doc /* confirms that the revised sequence remains compatible with stand occupancy, pushback spacing, and tug availability shown on the Ramp Movement Board @S677 */ }
            perform action a42 { doc /* uses the Ramp Movement Board @S749 */ }
            perform action a43 { doc /* determine whether a proposed metering adjustment can be supported by stand availability, pushback feasibility, and taxi route status @S749 */ }
            perform action a44 { doc /* receive role profiles that reflect their normal operational responsibilities @S766 */ }
            perform action a45 { doc /* may update ramp movement status through the Ramp Movement Board @S770 */ }
            perform action a46 { doc /* may not change airport acceptance parameters or sector capacity assumptions @S770 */ }
            perform action a47 { doc /* own ramp movement status data maintained for the Ramp Movement Board @S818 */ }
            perform action a48 { doc /* have named accountable implementation contacts @S893 */ }
            perform action a49 { doc /* retain operational command authority during support activity @S917 */ }
            perform action a50 { doc /* maintaining accurate surface and handling status @S966 */ }
        }
        part rampMovementBoard : RampMovementBoard {
            perform action a0 { doc /* support the transition from regional planning decisions to executable airport and tower actions @S017 */ }
            perform action a1 { doc /* support tactical airport and regional coordination @S032 */ }
            perform action a2 { doc /* records a material change in planned off-block timing @S216 */ }
            perform action a3 { doc /* maintains milestone timestamps for stand readiness, boarding completion, doors closed, start approval readiness, taxi start, and other locally configured departure events @S255 */ }
            perform action a4 { doc /* shows occupied stands, blocked service roads, and pending pushback areas @S311 */ }
            perform action a5 { doc /* produces the Fuel Truck Hold Advice @S361 */ }
            perform action a6 { doc /* displays each aircraft as pending push, taxi to pad, in treatment, awaiting release, or returning to stand @S377 */ }
            perform action a7 { doc /* refresh the apron movement layer within five seconds of each validated surface event @S427 */ }
            perform action a8 { doc /* shows conflicting pushbacks, blocked lead-in lines, saturated holding points, or insufficient room for safe wingtip clearance @S458 */ }
            perform action a9 { doc /* maintains the operational view of occupied, blocked, cleaning, boarding, and tow-ready positions @S469 */ }
            perform action a10 { doc /* displays the resulting constraint as a stand-level exception with a time band rather than as a continuous stream of equipment messages @S525 */ }
            perform action a11 { doc /* displays remote stand occupancy, expected towing actions, and bus service readiness in a shared view for airside coordination @S551 */ }
            perform action a12 { doc /* presents apron sensor events as operational evidence for stand release, taxi lane availability, and vehicle conflict assessment @S581 */ }
            perform action a13 { doc /* displays stand readiness status using time-stamped states that distinguish unchecked, under inspection, cleaned, blocked, and ready conditions @S646 */ }
            perform action a14 { doc /* using time-stamped states that distinguish unchecked, under inspection, cleaned, blocked, and ready conditions @S646 */ }
            perform action a15 { doc /* receives the same operational status @S703 */ }
            perform action a16 { doc /* provide actual movement milestones that support independent verification of slot performance @S801 */ }
            perform action a17 { doc /* provide surface queue counts based on movement status and surveillance confirmation @S844 */ }
            perform action a18 { doc /* provide the main operational inputs for this capability @S947 */ }
            perform action a19 { doc /* must use the approved rules recorded in the Business Rules Registry @S980 */ }
        }
        part rampPersonnel : RampPersonnel {
            perform action a0 { doc /* use the Ramp Movement Board @S867 */ }
            perform action a1 { doc /* without substituting system indications for required visual checks, radio coordination, and local safety procedures @S867 */ }
        }
        part rampRoles : RampRoles {
            perform action a0 { doc /* share the same expectation for aircraft readiness @S560 */ }
        }
        part rampServiceOrganizations : RampServiceOrganizations {
            perform action a0 { doc /* operating under airport approval @S044 */ }
        }
        part rampUsers : RampUsers {
            perform action a0 { doc /* interpret treatment age consistently @S382 */ }
        }
        part rankedOptions : RankedOptions {
            perform action a0 { doc /* may include delay acceptance, aircraft substitution, flight cancellation, flight consolidation, repositioning, or slot exchange @S629 */ }
        }
        part readinessGate1 : ReadinessGate1 {
            perform action a0 { doc /* shall confirm that governance, security approvals, user role definitions, operating hours, and support escalation paths are documented and accepted by local stakeholders @S894 */ }
        }
        part readinessGate2 : ReadinessGate2 {
            perform action a0 { doc /* shall confirm that the Flight Data Exchange, Airline Interface Adapter, Surface Surveillance Adapter, and Weather Ingest Gateway can be connected without disrupting existing airport operations @S895 */ }
        }
        part readinessGate3 : ReadinessGate3 {
            perform action a0 { doc /* shall confirm that local procedures have been mapped to the Airport CDM Portal, Tower Sequence Manager, Ramp Movement Board, Departure Metering Service, and Arrival Regulation Console @S896 */ }
        }
        part readinessGate4 : ReadinessGate4 {
            perform action a0 { doc /* shall confirm that training, shadow operations, contingency procedures, and operational acceptance criteria have been completed before live collaborative decisions are made through the Regional Flow Platform @S897 */ }
        }
        part readinessMilestone : ReadinessMilestone;
        part readinessValidityWindow : ReadinessValidityWindow {
            perform action a0 { doc /* expires @S663 */ }
        }
        part recordedConcurrences : RecordedConcurrences {
            perform action a0 { doc /* conflict @S687 */ }
        }
        part recoveredGateAssignments : RecoveredGateAssignments {
            perform action a0 { doc /* reduced missed connections @S489 */ }
            perform action a1 { doc /* reduced secondary stand conflicts @S489 */ }
            perform action a2 { doc /* improved aircraft rotation stability during the Recovery Phase @S489 */ }
        }
        part recoveryAction : RecoveryAction {
            perform action a0 { doc /* does not destabilize the wider network plan @S674 */ }
        }
        part recoveryPhase : RecoveryPhase {
            perform action a0 { doc /* drive stakeholder participation and operating procedures @S047 */ }
        }
        part recoveryPlan : RecoveryPlan {
            perform action a0 { doc /* depends on unrealistic turnaround timing @S754 */ }
        }
        part recoveryRecommendations : RecoveryRecommendations;
        part recoveryTime : RecoveryTime;
        part recurrentTraining : RecurrentTraining;
        part recurringOwnershipConflicts : RecurringOwnershipConflicts;
        part reducedVisibility : ReducedVisibility {
            perform action a0 { doc /* increase the cost of taxiway conflicts and blocked stands @S464 */ }
        }
        part regionalAuthority : RegionalAuthority {
            perform action a0 { doc /* agreed by the airport operator, regional authority, and participating aircraft operators @S779 */ }
        }
        part regionalExpansion : RegionalExpansion;
        part regionalFlowManagementPersonnel : RegionalFlowManagementPersonnel;
        part regionalFlowManager : RegionalFlowManager {
            perform action a0 { doc /* balancing demand against capacity across the Meridian region @S010 */ }
            perform action a1 { doc /* coordinating regional traffic management actions @S010 */ }
            perform action a2 { doc /* balancing demand and capacity at the regional level @S038 */ }
            perform action a3 { doc /* owns the baseline process @S050 */ }
            perform action a4 { doc /* confirms that the planning horizon, cutover time, and review checkpoints are understood by the participating operational roles @S050 */ }
            perform action a5 { doc /* owns the regional operating intent @S077 */ }
            perform action a6 { doc /* confirms that planned demand, declared capacity, and coordination milestones are aligned @S077 */ }
            perform action a7 { doc /* reviews the Airport Capacity Plan, the Ground Delay Program status, and any Tactical Regulation Proposal @S078 */ }
            perform action a8 { doc /* chairs decision checkpoints @S094 */ }
            perform action a9 { doc /* authorizes changes to flow measures @S094 */ }
            perform action a10 { doc /* uses the Common Situation Display @S117 */ }
            perform action a11 { doc /* compare forecast demand, assessed capacity, and any active Ground Delay Program effects in one operational view @S117 */ }
            perform action a12 { doc /* confirms airline recovery priorities @S137 */ }
            perform action a13 { doc /* may authorize temporary rule changes during a Capacity Reduction State @S228 */ }
            perform action a14 { doc /* assesses whether the effect is localized to one stream or requires a broader Ground Delay Program @S327 */ }
            perform action a15 { doc /* decides whether to absorb the impact through metering, targeted delay, reroute coordination, or a wider regulation @S343 */ }
            perform action a16 { doc /* absorb the impact through metering, targeted delay, reroute coordination, or a wider regulation @S343 */ }
            perform action a17 { doc /* confirm the active interpretation of the restriction @S345 */ }
            perform action a18 { doc /* may increase stand absorption @S367 */ }
            perform action a19 { doc /* prevent unstable taxi queues from forming under reduced visibility or wet surface conditions @S367 */ }
            perform action a20 { doc /* authorizes a controlled transition from Capacity Reduction State toward Recovery Phase @S393 */ }
            perform action a21 { doc /* evaluates regulation options in the Arrival Regulation Console @S396 */ }
            perform action a22 { doc /* using runway availability, sector load, stand readiness, and forecast weather as the controlling inputs @S396 */ }
            perform action a23 { doc /* uses the restriction notice @S399 */ }
            perform action a24 { doc /* bound the arrival regulation timeline @S399 */ }
            perform action a25 { doc /* committing new landing-rate values in the Arrival Regulation Console @S399 */ }
            perform action a26 { doc /* may apply a tactical landing-rate reduction for a defined review interval @S410 */ }
            perform action a27 { doc /* may approve a staged landing-rate increase @S411 */ }
            perform action a28 { doc /* may combine arrival regulation with departure metering @S416 */ }
            perform action a29 { doc /* protect surface balance @S416 */ }
            perform action a30 { doc /* prevent inbound aircraft from occupying gates needed for recovery flights @S416 */ }
            perform action a31 { doc /* can compare planned demand, measured throughput, and active control measures without changing applications @S420 */ }
            perform action a32 { doc /* changing applications @S420 */ }
            perform action a33 { doc /* uses these advisories @S463 */ }
            perform action a34 { doc /* decide whether the tactical plan should retain normal sequencing, shift to local metering, or support a Tactical Regulation Proposal @S463 */ }
            perform action a35 { doc /* balances passenger connection pressure against network fairness @S479 */ }
            perform action a36 { doc /* uses the Regional Flow Platform @S492 */ }
            perform action a37 { doc /* maintain a ranked view of candidate diversions, expected arrival times, required services, and the operational consequence of accepting each aircraft @S492 */ }
            perform action a38 { doc /* shifts from acceptance decisions to recovery coordination @S513 */ }
            perform action a39 { doc /* balancing restored arrival capacity, departure release opportunities, and stand clearance timing @S513 */ }
            perform action a40 { doc /* sees aggregated impact by departure bank, runway stream, and airline group instead of individual baggage or handler work items @S532 */ }
            perform action a41 { doc /* considers repeated remote stand transfer delays as an input to tactical capacity assessment during peak arrival and departure banks @S555 */ }
            perform action a42 { doc /* uses aggregated border delay exposure to decide whether an arrival regulation should be adjusted or whether delay absorption should remain local to the airport @S573 */ }
            perform action a43 { doc /* decide whether an arrival regulation should be adjusted or whether delay absorption should remain local to the airport @S573 */ }
            perform action a44 { doc /* uses the load sheet @S598 */ }
            perform action a45 { doc /* confirm whether a departure fix constraint should be represented as an airport departure measure @S598 */ }
            perform action a46 { doc /* can see aggregate recovery pressure across operators @S634 */ }
            perform action a47 { doc /* may suspend collaborative substitution during a Capacity Reduction State @S675 */ }
            perform action a48 { doc /* reviews the published constraint @S696 */ }
            perform action a49 { doc /* applies the last verified Airport Capacity Plan @S721 */ }
            perform action a50 { doc /* adjusts it by direct coordination with the Airspace Sector Planner and Meteorology Briefing Officer @S721 */ }
            perform action a51 { doc /* approves any arrival regulation changes through direct coordination @S729 */ }
            perform action a52 { doc /* understand where a small metering adjustment may reduce downstream disruption without degrading the Airport Capacity Plan @S739 */ }
            perform action a53 { doc /* may consider a recovery action credible only when it is aligned with a valid Target Off Block Time, crew availability status, and confirmed aircraft readiness @S753 */ }
            perform action a54 { doc /* receive role profiles that reflect their normal operational responsibilities @S766 */ }
            perform action a55 { doc /* may authorize regional traffic management measures @S768 */ }
            perform action a56 { doc /* use the Post Operations Report @S808 */ }
            perform action a57 { doc /* identify whether noncompliance resulted from operator choice, airport constraint, airspace constraint, weather impact, or system issue @S808 */ }
            perform action a58 { doc /* own flow management policy data, including Ground Delay Program parameters and Tactical Regulation Proposal status values @S814 */ }
            perform action a59 { doc /* use this indicator @S842 */ }
            perform action a60 { doc /* verify that a Ground Delay Program reduced airborne holding without creating excessive departure congestion at constrained airports @S842 */ }
            perform action a61 { doc /* receive advanced instruction on interpreting demand and capacity information, leading collaborative decisions, and authorizing operational measures in the Regional Flow Platform @S864 */ }
            perform action a62 { doc /* interpreting demand and capacity information @S864 */ }
            perform action a63 { doc /* leading collaborative decisions @S864 */ }
            perform action a64 { doc /* authorizing operational measures in the Regional Flow Platform @S864 */ }
            perform action a65 { doc /* confirms that operational benefits, safety constraints, cyber controls, and stakeholder obligations remain stable across multiple airports and traffic conditions @S911 */ }
            perform action a66 { doc /* retain operational command authority during support activity @S917 */ }
            perform action a67 { doc /* direct transition to Contingency Fallback State using approved local procedures @S926 */ }
            perform action a68 { doc /* using approved local procedures @S926 */ }
            perform action a69 { doc /* see upstream demand pressure earlier @S938 */ }
            perform action a70 { doc /* negotiate measures before local capacity is saturated @S938 */ }
            perform action a71 { doc /* compare recommendations with actual outcomes @S959 */ }
            perform action a72 { doc /* activate @S961 */ }
            perform action a73 { doc /* amend @S961 */ }
            perform action a74 { doc /* terminate regional flow measures @S961 */ }
        }
        part regionalFlowPlatform : RegionalFlowPlatform {
            perform action a0 { doc /* integrate planning, tactical regulation, airport readiness, and post-event analysis into a single operational environment @S012 */ }
            perform action a1 { doc /* creates the initial demand picture from published schedules, approved seasonal allocations, overnight schedule changes, and received Flight Intent Message data @S051 */ }
            perform action a2 { doc /* used by the Regional Flow Platform @S101 */ }
            perform action a3 { doc /* reconciles them with airport and airspace constraints @S130 */ }
            perform action a4 { doc /* permits more frequent intent updates @S147 */ }
            perform action a5 { doc /* retaining the previous values needed for audit and performance review @S147 */ }
            perform action a6 { doc /* expose the current regional demand and constraint context to the shared workspace at each publication cycle without requiring manual re-entry @S164 */ }
            perform action a7 { doc /* without requiring manual re-entry @S164 */ }
            perform action a8 { doc /* receives confirmed capacity impacts through normal system interfaces @S191 */ }
            perform action a9 { doc /* enters Contingency Fallback State @S247 */ }
            perform action a10 { doc /* creates the initial Target Off Block Time proposal from current flight intent, stand readiness, turnaround progress, and applicable airport capacity constraints @S250 */ }
            perform action a11 { doc /* locks the Target Off Block Time @S268 */ }
            perform action a12 { doc /* distinguish an air traffic delay from a local handling delay @S302 */ }
            perform action a13 { doc /* marks a proposed Target Off Block Time as conditional @S314 */ }
            perform action a14 { doc /* records each airspace alert, acknowledgement, and downstream decision in the Audit Event Ledger for traceability and later review @S333 */ }
            perform action a15 { doc /* normalizes each Flight Intent Message against the current Airport Capacity Plan @S349 */ }
            perform action a16 { doc /* enters the winter operating mode @S371 */ }
            perform action a17 { doc /* synchronizes the tactical display with the Time Synchronization Service @S422 */ }
            perform action a18 { doc /* correlates surface equipment conditions with flight intent, stand assignment, and runway plan data @S444 */ }
            perform action a19 { doc /* recommending any change to the active tactical plan @S444 */ }
            perform action a20 { doc /* treats these conditions as operational exceptions rather than routine status messages @S517 */ }
            perform action a21 { doc /* enters Contingency Fallback State @S540 */ }
            perform action a22 { doc /* aligns these sector values with scheduled movements from Flight Data Exchange and predicted readiness from Demand Prediction Service @S593 */ }
            perform action a23 { doc /* treats the received legality status as an operator assertion @S621 */ }
            perform action a24 { doc /* does not independently calculate labor agreement compliance @S621 */ }
            perform action a25 { doc /* records each event as an operational constraint with an effective time, expected duration, affected resource, confidence level, and approving authority @S691 */ }
            perform action a26 { doc /* maintains the infrastructure event as a controlling assumption @S708 */ }
            perform action a27 { doc /* returns the affected resource to Normal Operations or Recovery Phase handling as appropriate @S713 */ }
            perform action a28 { doc /* cannot provide trusted automation for one or more airport, runway, apron, or airspace flow functions @S714 */ }
            perform action a29 { doc /* does not expose passenger names, booking references, or protected itinerary details @S742 */ }
            perform action a30 { doc /* shall record the initiating user, the approving user, the affected operational object, and the effective time of the decision @S775 */ }
            perform action a31 { doc /* reconcile contingency actions with the Collaborative Decision Log @S787 */ }
            perform action a32 { doc /* record slot compliance events in the Audit Event Ledger @S789 */ }
            perform action a33 { doc /* using the operating date, flight identifier, airport, runway direction, and applicable regulation reference @S789 */ }
            perform action a34 { doc /* produces parallel outputs for comparison by operational users @S905 */ }
            perform action a35 { doc /* cannot support safe collaborative operation @S926 */ }
            exhibit state modes {
                state s0 { doc /* Adverse Weather Mode @S047,S908 */ }
                state s1 { doc /* Capacity Reduction State @S047,S706,S708,S908 */ }
                state s2 { doc /* Contingency Fallback State @S047,S247,S540,S716,S908 */ }
                state s3 { doc /* Normal Operations @S047,S908 */ }
                state s4 { doc /* Recovery Phase @S047,S908 */ }
                state s5 { doc /* Slot Compliance State @S047 */ }
                state s6 { doc /* degraded operation @S715 */ }
                state s7 { doc /* shadow operations @S905 */ }
                state s8 { doc /* winter operating mode @S371 */ }
            }
        }
        part regionalFlowPlatformFunction : RegionalFlowPlatformFunction {
            perform action a0 { doc /* replaced by a Regional Flow Platform function @S903 */ }
        }
        part regionalFlowPlatformFunctions : RegionalFlowPlatformFunctions {
            exhibit state modes {
                state s0 { doc /* degraded @S097 */ }
            }
        }
        part regionalFlowProcess : RegionalFlowProcess;
        part regulatedFlight : RegulatedFlight {
            perform action a0 { doc /* can keep its allocated departure opportunity @S533 */ }
        }
        part regulatoryConstraints : RegulatoryConstraints {
            perform action a0 { doc /* require a new time @S723 */ }
        }
        part rejectionReasons : RejectionReasons;
        part releaseTiming : ReleaseTiming {
            perform action a0 { doc /* changes @S294 */ }
        }
        part remoteStand : RemoteStand {
            perform action a0 { doc /* absorb late arrivals @S564 */ }
            exhibit state modes {
                state s0 { doc /* nominally available @S558 */ }
            }
        }
        part remoteStandAreas : RemoteStandAreas {
            exhibit state modes {
                state s0 { doc /* available for the traffic pattern shown in the plan @S579 */ }
            }
        }
        part remoteStandDeparture : RemoteStandDeparture {
            exhibit state modes {
                state s0 { doc /* ready for push or tow @S562 */ }
            }
        }
        part remoteStandUse : RemoteStandUse {
            perform action a0 { doc /* increases @S559 */ }
        }
        part repeatableOnboardingPattern : RepeatableOnboardingPattern;
        part repeatedSlips : RepeatedSlips {
            perform action a0 { doc /* reduce confidence in the planned departure stream @S315 */ }
        }
        part replenishment : Replenishment {
            perform action a0 { doc /* affect the planned treatment rate @S383 */ }
        }
        part representation : Representation {
            perform action a0 { doc /* supports aircraft and crew combinations that are valid only if a Target Off Block Time is achieved within a limited tolerance @S624 */ }
        }
        part requestedDepartureTiming : RequestedDepartureTiming;
        part resequence : Resequence {
            perform action a0 { doc /* would materially affect passenger boarding, connection protection, or aircraft rotation plans @S214 */ }
        }
        part resourceConstraints : ResourceConstraints {
            perform action a0 { doc /* influence collaborative decisions @S869 */ }
        }
        part responsibleActor : ResponsibleActor {
            perform action a0 { doc /* used by the responsible actor @S487 */ }
        }
        part responsibleOperationalOwner : ResponsibleOperationalOwner {
            perform action a0 { doc /* verifies that its essential decisions, timing assumptions, and audit needs are supported in the target process @S904 */ }
        }
        part responsibleSweepTeam : ResponsibleSweepTeam {
            perform action a0 { doc /* confirms that the assigned apron area is clean, safe, and free of observed foreign object debris @S647 */ }
        }
        part restorationTime : RestorationTime;
        part restrictionHandlingProcess : RestrictionHandlingProcess {
            perform action a0 { doc /* supported timely and consistent decisions @S346 */ }
        }
        part resultingSequence : ResultingSequence {
            perform action a0 { doc /* would conflict with safe runway sequencing or local control workload @S676 */ }
        }
        part revisedOffBlockExpectation : RevisedOffBlockExpectation {
            perform action a0 { doc /* results from ramp resequencing @S215 */ }
        }
        part revisedSequence : RevisedSequence {
            perform action a0 { doc /* remains compatible with stand occupancy, pushback spacing, and tug availability shown on the Ramp Movement Board @S677 */ }
        }
        part richerIntentData : RicherIntentData;
        part roleAccountableForTheNextUpdate : RoleAccountableForTheNextUpdate;
        part roleProfiles : RoleProfiles {
            perform action a0 { doc /* reflect their normal operational responsibilities @S766 */ }
            perform action a1 { doc /* shall grant the minimum access needed to view, propose, approve, or administer operational data within the Regional Flow Platform @S767 */ }
        }
        part runwayBalancing : RunwayBalancing;
        part runwayConditions : RunwayConditions {
            perform action a0 { doc /* degrade faster than the model forecast @S410 */ }
        }
        part runwayConfiguration : RunwayConfiguration {
            perform action a0 { doc /* changes @S431 */ }
        }
        part runwayCrossingDemand : RunwayCrossingDemand {
            perform action a0 { doc /* indicates that uncontrolled pushback would create an unstable surface queue @S453 */ }
        }
        part runwayEntryQueues : RunwayEntryQueues {
            perform action a0 { doc /* are approaching the metering threshold @S454 */ }
        }
        part runwayLightingElements : RunwayLightingElements {
            exhibit state modes {
                state s0 { doc /* unavailable @S693 */ }
            }
        }
        part runwayOccupancyTrend : RunwayOccupancyTrend {
            perform action a0 { doc /* indicates that uncontrolled pushback would create an unstable surface queue @S453 */ }
        }
        part runwayQueueManagement : RunwayQueueManagement {
            perform action a0 { doc /* favors stable ordering @S287 */ }
        }
        part runwaySequence : RunwaySequence {
            perform action a0 { doc /* support departure @S305 */ }
        }
        part safeAccessRoutes : SafeAccessRoutes {
            exhibit state modes {
                state s0 { doc /* available @S473 */ }
            }
        }
        part safePassengerTransferPath : SafePassengerTransferPath;
        part safety : Safety {
            perform action a0 { doc /* require a new time @S723 */ }
        }
        part safetyEvent : SafetyEvent {
            perform action a0 { doc /* may affect airport acceptance, surface movement, or airspace availability @S096 */ }
        }
        part safetySecurityOrServiceabilityIssue : SafetySecurityOrServiceabilityIssue {
            perform action a0 { doc /* prevents compliance @S965 */ }
        }
        part scarceCapacity : ScarceCapacity;
        part scheduledPassengerOperators : ScheduledPassengerOperators;
        part schedules : Schedules {
            perform action a0 { doc /* exceed the declared infrastructure capability @S700 */ }
        }
        part schemaChecks : SchemaChecks;
        part seasonalThunderstorms : SeasonalThunderstorms {
            perform action a0 { doc /* frequently reduce the effective Airport Acceptance Rate across the network @S005 */ }
        }
        part section4 : Section4 {
            perform action a0 { doc /* defines the accountable roles used after the approved morning baseline is distributed through the Regional Flow Platform @S075 */ }
        }
        part sectorConstraints : SectorConstraints {
            perform action a0 { doc /* may affect regional capacity @S967 */ }
        }
        part sectorLoadMonitor : SectorLoadMonitor {
            perform action a0 { doc /* provide additional indicators of emerging capacity loss and operational imbalance @S019 */ }
            perform action a1 { doc /* contributes airspace demand indicators @S106 */ }
            perform action a2 { doc /* provides the operational view of expected demand against the reduced sector capacity @S329 */ }
            perform action a3 { doc /* highlights intervals where overload is likely @S329 */ }
            perform action a4 { doc /* contributes early warnings @S408 */ }
            perform action a5 { doc /* produces the Departure Fix Load Sheet @S484 */ }
            perform action a6 { doc /* supplies time-bucketed counts, predicted occupancy, and overload flags for the sectors that feed or constrain Meridian arrivals and departures @S592 */ }
            perform action a7 { doc /* absorb discretionary changes @S755 */ }
            perform action a8 { doc /* provide the common inputs needed to connect airspace capacity and airport capacity in the same prediction cycle @S943 */ }
            perform action a9 { doc /* provide planning evidence @S973 */ }
        }
        part sectorLoadingConstraints : SectorLoadingConstraints {
            perform action a0 { doc /* require close coordination with the Military Airspace Liaison @S006 */ }
        }
        part sectorPlanning : SectorPlanning {
            perform action a0 { doc /* act @S331 */ }
        }
        part sectorWorkload : SectorWorkload {
            perform action a0 { doc /* changes @S431 */ }
        }
        part sectors : Sectors {
            perform action a0 { doc /* feed or constrain Meridian arrivals and departures @S592 */ }
            perform action a1 { doc /* exceed its planning threshold @S594 */ }
        }
        part securityEvent : SecurityEvent {
            perform action a0 { doc /* may affect airport acceptance, surface movement, or airspace availability @S096 */ }
        }
        part securityMonitoring : SecurityMonitoring {
            perform action a0 { doc /* shall alert the System Support Engineer and Data Governance Steward when unusual access patterns indicate possible credential compromise or inappropriate privilege use @S780 */ }
        }
        part selectedArrivals : SelectedArrivals {
            perform action a0 { doc /* depart for the region @S398 */ }
        }
        part sensitivityOfSelectedDepartures : SensitivityOfSelectedDepartures {
            perform action a0 { doc /* do not create an entitlement for a flight to receive a favorable Calculated Takeoff Time @S744 */ }
        }
        part sequencingChanges : SequencingChanges {
            perform action a0 { doc /* affect sector workload, runway demand, and controller tactical flexibility @S865 */ }
        }
        part service : Service {
            exhibit state modes {
                state s0 { doc /* restored @S920 */ }
            }
        }
        part serviceCompletionForecasts : ServiceCompletionForecasts {
            perform action a0 { doc /* change @S261 */ }
        }
        part serviceLevelTargets : ServiceLevelTargets {
            perform action a0 { doc /* include monthly availability for critical production functions, incident response time, restoration time, data feed timeliness, and successful completion of scheduled operational reports @S933 */ }
        }
        part serviceModel : ServiceModel {
            perform action a0 { doc /* distinguish continuous operational support from planned engineering support @S913 */ }
        }
        part serviceRoads : ServiceRoads {
            exhibit state modes {
                state s0 { doc /* available for the traffic pattern shown in the plan @S579 */ }
            }
        }
        part serviceSequencingConflicts : ServiceSequencingConflicts {
            perform action a0 { doc /* could invalidate a readiness milestone @S526 */ }
        }
        part serviceUnavailability : ServiceUnavailability {
            perform action a0 { doc /* prevent users from relying on the normal decision support path without additional verification @S715 */ }
        }
        part servicingActivity : ServicingActivity {
            perform action a0 { doc /* remain clear of an aircraft that is being held at stand @S361 */ }
        }
        part servicingProgress : ServicingProgress {
            perform action a0 { doc /* can change the sequence @S211 */ }
        }
        part sharedAirTrafficFlowManagementAndAirportCollaborativeDecisionMakingCapability : SharedAirTrafficFlowManagementAndAirportCollaborativeDecisionMakingCapability {
            perform action a0 { doc /* aligns network demand, airport capacity, and surface readiness @S009 */ }
            perform action a1 { doc /* reduces avoidable delay @S024 */ }
            perform action a2 { doc /* improves predictability @S024 */ }
            perform action a3 { doc /* enables transparent collaboration across the Meridian airport network @S024 */ }
        }
        part sharedOperationalAccounts : SharedOperationalAccounts {
            perform action a0 { doc /* prevent reliable attribution during time-critical flow management decisions @S765 */ }
        }
        part sharedOperationalPicture : SharedOperationalPicture;
        part sharedWorkspace : SharedWorkspace;
        part shortDurationStandOccupancy : ShortDurationStandOccupancy {
            perform action a0 { doc /* would still disrupt a critical departure bank @S509 */ }
        }
        part shuttleAvailability : ShuttleAvailability;
        part simulationEvents : SimulationEvents {
            perform action a0 { doc /* shall require users to compare automated recommendations with local knowledge, document significant decisions in the Collaborative Decision Log, and explain departures from system proposals @S883 */ }
        }
        part simulationExercises : SimulationExercises {
            perform action a0 { doc /* shall use realistic traffic samples, weather constraints, surface congestion, airline schedule pressure, handling resource shortages, and recovery objectives @S880 */ }
            perform action a1 { doc /* test coordinated decision making @S880 */ }
        }
        part simultaneousPushbacks : SimultaneousPushbacks {
            perform action a0 { doc /* can exceed tow team availability @S320 */ }
            perform action a1 { doc /* block service roads @S320 */ }
        }
        part singleUser : SingleUser {
            perform action a0 { doc /* creating @S774 */ }
            perform action a1 { doc /* approving @S774 */ }
            perform action a2 { doc /* technically concealing a material change to a Ground Delay Program, Airport Acceptance Rate, or Tactical Regulation Proposal @S774 */ }
        }
        part slotAdherence : SlotAdherence;
        part slotAllocationEngine : SlotAllocationEngine {
            perform action a0 { doc /* supports fair and traceable allocation of constrained departure and arrival opportunities @S015 */ }
            perform action a1 { doc /* support planning and collaborative assessment @S031 */ }
            perform action a2 { doc /* applies the current Business Rules Registry parameters @S080 */ }
            perform action a3 { doc /* converts accepted constraints into Calculated Takeoff Time values and Target Off Block Time guidance for affected flights @S134 */ }
            perform action a4 { doc /* publishes a revised constraint set @S137 */ }
            perform action a5 { doc /* proposes regulated departure and arrival opportunities @S225 */ }
            perform action a6 { doc /* matching demand from the Demand Prediction Service to constraints supplied by the Capacity Assessment Module @S225 */ }
            perform action a7 { doc /* derives a Calculated Takeoff Time or arrival opportunity that preserves the declared capacity envelope @S227 */ }
            perform action a8 { doc /* shall not improve one operator's position by imposing an excessive delay on another operator unless the rule basis is visible and logged @S234 */ }
            perform action a9 { doc /* imposing an excessive delay on another operator @S234 */ }
            perform action a10 { doc /* recalculating the regulated opportunity @S244 */ }
            perform action a11 { doc /* derives the Calculated Takeoff Time @S253 */ }
            perform action a12 { doc /* combining runway metering constraints, departure fix loading, and applicable Ground Delay Program rules @S253 */ }
            perform action a13 { doc /* receives a capacity update @S269 */ }
            perform action a14 { doc /* may revise slot outcomes only within the authority defined for the current operating state and the applicable fairness rules @S342 */ }
            perform action a15 { doc /* adjust allocated departure times @S355 */ }
            perform action a16 { doc /* preserve the planned runway sequence @S355 */ }
            perform action a17 { doc /* recalculates affected Calculated Takeoff Time values @S374 */ }
            perform action a18 { doc /* can support a Ground Delay Program @S398 */ }
            perform action a19 { doc /* produces the Pushback Window Token @S428 */ }
            perform action a20 { doc /* uses the sanitized readiness state @S533 */ }
            perform action a21 { doc /* evaluating whether a regulated flight can keep its allocated departure opportunity @S533 */ }
            perform action a22 { doc /* treats an unresolved customs hold as a reason to avoid assigning an aggressive departure sequence position to the affected flight @S575 */ }
            perform action a23 { doc /* avoid assigning an aggressive departure sequence position to the affected flight @S575 */ }
            perform action a24 { doc /* assigning an aggressive departure sequence position to the affected flight @S575 */ }
            perform action a25 { doc /* preserves equity @S603 */ }
            perform action a26 { doc /* distributing delay across operators according to the active Ground Delay Program logic and local priority rules @S603 */ }
            perform action a27 { doc /* uses these constraints @S625 */ }
            perform action a28 { doc /* evaluating whether a Calculated Takeoff Time should be offered, retained, exchanged, or released @S625 */ }
            perform action a29 { doc /* retains the Calculated Takeoff Time until the operational delay exceeds the tolerance defined in the Business Rules Registry @S659 */ }
            perform action a30 { doc /* evaluates the candidate swap against active Ground Delay Program constraints, Calculated Takeoff Time integrity, Target Off Block Time dependencies, and Airport Acceptance Rate commitments @S669 */ }
            perform action a31 { doc /* raised by the Slot Allocation Engine @S671 */ }
            perform action a32 { doc /* publishing the revised slot assignment @S681 */ }
            perform action a33 { doc /* uses the reduced capacity value @S700 */ }
            perform action a34 { doc /* protect fairness @S700 */ }
            perform action a35 { doc /* avoiding schedules that exceed the declared infrastructure capability @S700 */ }
            perform action a36 { doc /* continues to apply the approved sequencing policy, runway capacity, airspace constraints, and published Ground Delay Program parameters as controlling inputs @S745 */ }
            perform action a37 { doc /* reject data that lacks a trusted timestamp @S825 */ }
            perform action a38 { doc /* use improved turnaround predictions @S949 */ }
            perform action a39 { doc /* protect feasible Calculated Takeoff Time assignments @S949 */ }
            perform action a40 { doc /* reduce avoidable re-sequencing @S949 */ }
            perform action a41 { doc /* must use the approved rules recorded in the Business Rules Registry @S980 */ }
        }
        part slotAllocationReferenceData : SlotAllocationReferenceData;
        part slotComplianceState : SlotComplianceState {
            perform action a0 { doc /* drive stakeholder participation and operating procedures @S047 */ }
            perform action a1 { doc /* indicate whether a flight was compliant, early, late, exempted, substituted, cancelled, or pending review at the end of the traffic period @S791 */ }
            exhibit state modes {
                state s0 { doc /* provisional @S247 */ }
            }
        }
        part slotComplianceStateDefinitions : SlotComplianceStateDefinitions;
        part slotCoordinator : SlotCoordinator {
            perform action a0 { doc /* require a common basis for decisions rather than separate local views of the same operational picture @S011 */ }
            perform action a1 { doc /* participate @S039 */ }
            perform action a2 { doc /* align airline intentions, schedule constraints, and slot management decisions with the shared plan @S039 */ }
            perform action a3 { doc /* uses the Slot Allocation Engine @S068 */ }
            perform action a4 { doc /* prepare an initial slot feasibility view @S068 */ }
            perform action a5 { doc /* does not publish binding Calculated Takeoff Time values during baseline construction @S068 */ }
            perform action a6 { doc /* maintains accountability for Calculated Takeoff Time allocation policy @S080 */ }
            perform action a7 { doc /* confirms that the Slot Allocation Engine applies the current Business Rules Registry parameters @S080 */ }
            perform action a8 { doc /* reviews airline requests for priority handling against published equity and operational feasibility rules @S136 */ }
            perform action a9 { doc /* checking Calculated Takeoff Time feasibility @S161 */ }
            perform action a10 { doc /* recording accepted slot adjustments, rejected slot adjustments, and unresolved slot conflicts in the Collaborative Decision Log @S161 */ }
            perform action a11 { doc /* administers the allocation run @S229 */ }
            perform action a12 { doc /* reviews exceptions @S229 */ }
            perform action a13 { doc /* confirms that proposed results are ready for publication through the Airport CDM Portal @S229 */ }
            perform action a14 { doc /* records each accepted or rejected exemption in the Collaborative Decision Log with the rule applied, the approving role, and the expected operational consequence @S239 */ }
            perform action a15 { doc /* reviews proposed Calculated Takeoff Time values against network constraints @S258 */ }
            perform action a16 { doc /* requests adjustment @S258 */ }
            perform action a17 { doc /* verifies that any proposed resequencing remains compatible with the Calculated Takeoff Time tolerance and the current Slot Compliance State @S285 */ }
            perform action a18 { doc /* records the agreed pushback window rationale in the coordination notes @S356 */ }
            perform action a19 { doc /* uses the Slot Allocation Engine @S404 */ }
            perform action a20 { doc /* distribute arrival times according to the approved business rules and any protected flight criteria in the Business Rules Registry @S404 */ }
            perform action a21 { doc /* reviews the relationship between the Calculated Takeoff Time and the proposed surface release time @S457 */ }
            perform action a22 { doc /* accepting the change @S457 */ }
            perform action a23 { doc /* protects constrained rotations @S481 */ }
            perform action a24 { doc /* checking that a recovered gate plan remains compatible with the applicable Calculated Takeoff Time and any slot compliance expectation @S481 */ }
            perform action a25 { doc /* reviews the effect of diversion acceptance on Calculated Takeoff Time and Target Off Block Time commitments for departures that are already in a Slot Compliance State @S502 */ }
            perform action a26 { doc /* can evaluate the operational acceptability of a requested change @S633 */ }
            perform action a27 { doc /* without receiving unnecessary commercial information @S633 */ }
            perform action a28 { doc /* reviews any exception raised by the Slot Allocation Engine @S671 */ }
            perform action a29 { doc /* confirms whether the swap remains consistent with regional flow objectives @S671 */ }
            perform action a30 { doc /* sends the Slot Swap Permission Email @S672 */ }
            perform action a31 { doc /* initiates manual slot procedures using a time-ordered control sheet maintained at the Contingency Operations Console @S722 */ }
            perform action a32 { doc /* using a time-ordered control sheet maintained at the Contingency Operations Console @S722 */ }
            perform action a33 { doc /* assigns any revised Calculated Takeoff Time @S724 */ }
            perform action a34 { doc /* confirming runway capacity with the Tower Supervisor and surface feasibility with the Ramp Control Lead @S724 */ }
            perform action a35 { doc /* uses the Crew Duty Extension Log @S726 */ }
            perform action a36 { doc /* check whether manually issued slot times remain operationally achievable @S726 */ }
            perform action a37 { doc /* returning automation to control @S736 */ }
            perform action a38 { doc /* reconciles the manual slot record with the Slot Allocation Engine @S736 */ }
            perform action a39 { doc /* resolves any conflict in the Collaborative Decision Log @S736 */ }
            perform action a40 { doc /* receive role profiles that reflect their normal operational responsibilities @S766 */ }
            perform action a41 { doc /* may administer slot allocation functions within boundaries defined by the Business Rules Registry @S768 */ }
            perform action a42 { doc /* review substitution activity after operations @S798 */ }
            perform action a43 { doc /* confirm that priority rules were applied consistently across participating operators @S798 */ }
            perform action a44 { doc /* own slot allocation reference data, including Calculated Takeoff Time tolerances and Slot Compliance State definitions @S815 */ }
            perform action a45 { doc /* review slot adherence by operator, airport, time band, and regulation identifier @S848 */ }
            perform action a46 { doc /* detect recurring causes of noncompliance @S848 */ }
            perform action a47 { doc /* receive training on the Slot Allocation Engine, Airport CDM Portal, and applicable Business Rules Registry entries @S870 */ }
        }
        part smallChangesInCapacity : SmallChangesInCapacity {
            perform action a0 { doc /* would affect stand occupancy and departure queues @S069 */ }
        }
        part source : Source {
            perform action a0 { doc /* provided by the source @S118 */ }
        }
        part sourceData : SourceData {
            perform action a0 { doc /* supports that attribution @S859 */ }
        }
        part southRunwayMeter : SouthRunwayMeter {
            perform action a0 { doc /* provide additional indicators of emerging capacity loss and operational imbalance @S019 */ }
            perform action a1 { doc /* receive runway-specific capacity values @S114 */ }
            perform action a2 { doc /* maintain separate queues @S280 */ }
            perform action a3 { doc /* maintain independent queue counts @S359 */ }
            perform action a4 { doc /* applies the same planning principle to its assigned runway stream @S455 */ }
            perform action a5 { doc /* preserving separation from arrival regulation actions @S455 */ }
            perform action a6 { doc /* support independent checks of queue length where surveillance coverage is available @S845 */ }
        }
        part southportAirport : SouthportAirport {
            perform action a0 { doc /* remains responsible for its local safety management, aerodrome certification obligations, and operational command authority @S027 */ }
        }
        part specialUseAirspace : SpecialUseAirspace {
            perform action a0 { doc /* also create recurring sector loading constraints @S006 */ }
            perform action a1 { doc /* affect available capacity @S041 */ }
        }
        part stabilizationPeriod : StabilizationPeriod;
        part staffingAssumptions : StaffingAssumptions {
            perform action a0 { doc /* changes @S431 */ }
        }
        part staffingConstraints : StaffingConstraints {
            perform action a0 { doc /* can change the sequence @S211 */ }
        }
        part staffingGaps : StaffingGaps;
        part stakeholderBenefitTracking : StakeholderBenefitTracking {
            perform action a0 { doc /* allocate measured outcomes to aircraft operators, airport operations, air navigation service functions, ground handling activities, and passengers @S859 */ }
        }
        part stakeholderOrganization : StakeholderOrganization {
            perform action a0 { doc /* assign accountable representatives @S048 */ }
            perform action a1 { doc /* maintain current contact details @S048 */ }
            perform action a2 { doc /* follow agreed data use rules @S048 */ }
            perform action a3 { doc /* support post-operational review of decisions made through the Regional Flow Platform @S048 */ }
        }
        part stakeholders : Stakeholders {
            perform action a0 { doc /* restore scheduled flow @S023 */ }
        }
        part staleData : StaleData {
            perform action a0 { doc /* affect sequencing, metering, regulation, or resource allocation decisions @S822 */ }
        }
        part stand : Stand {
            perform action a0 { doc /* becomes usable after snow clearance @S386 */ }
            perform action a1 { doc /* remains unavailable until the hazard is removed or mitigated @S652 */ }
            perform action a2 { doc /* returns to an inspection-required state @S663 */ }
            exhibit state modes {
                state s0 { doc /* blocked @S646 */ }
                state s1 { doc /* cleaned @S646 */ }
                state s2 { doc /* inspection-required state @S663 */ }
                state s3 { doc /* ready @S646,S656 */ }
                state s4 { doc /* unavailable @S209,S652 */ }
                state s5 { doc /* unchecked @S646 */ }
                state s6 { doc /* under inspection @S646 */ }
                state s7 { doc /* usable @S386 */ }
            }
        }
        part standAccess : StandAccess {
            perform action a0 { doc /* affects the departure plan @S184 */ }
        }
        part standClosures : StandClosures {
            perform action a0 { doc /* materially reduce usable gate capacity @S660 */ }
        }
        part standCluster : StandCluster {
            perform action a0 { doc /* dispatch departures at the planned rate @S309 */ }
        }
        part standConflicts : StandConflicts {
            perform action a0 { doc /* would undermine a proposed departure recovery plan @S439 */ }
            perform action a1 { doc /* compress arrival unloading capacity @S439 */ }
        }
        part standEquipmentShortages : StandEquipmentShortages {
            perform action a0 { doc /* create hidden delay @S308 */ }
        }
        part standGateAndPassengerConnectionRecovery : StandGateAndPassengerConnectionRecovery {
            perform action a0 { doc /* begins @S467 */ }
        }
        part standPlan : StandPlan {
            perform action a0 { doc /* override accepted airspace constraints @S485 */ }
        }
        part standReadinessIndication : StandReadinessIndication {
            perform action a0 { doc /* supports coordinated surface planning @S655 */ }
            perform action a1 { doc /* prevents premature sequencing @S655 */ }
        }
        part standRestoration : StandRestoration {
            perform action a0 { doc /* delay the planned turnaround @S658 */ }
        }
        part standStatus : StandStatus {
            perform action a0 { doc /* stops advancing @S318 */ }
        }
        part standardServiceDeskCoverage : StandardServiceDeskCoverage;
        part startTime : StartTime;
        part stewardshipReviews : StewardshipReviews {
            perform action a0 { doc /* use those measures @S837 */ }
            perform action a1 { doc /* update training @S837 */ }
            perform action a2 { doc /* adjust validation rules @S837 */ }
            perform action a3 { doc /* improve the reliability of information used in operational decision making @S837 */ }
        }
        part strongCrosswinds : StrongCrosswinds {
            perform action a0 { doc /* frequently reduce the effective Airport Acceptance Rate across the network @S005 */ }
        }
        part subscribedOperationalRole : SubscribedOperationalRole;
        part subscribedOperationalRoles : SubscribedOperationalRoles;
        part substitution : Substitution {
            perform action a0 { doc /* would move an international departure into an earlier operating position @S680 */ }
        }
        part substitutionRecords : SubstitutionRecords {
            perform action a0 { doc /* show the original flight, replacement flight, assigned Calculated Takeoff Time, acceptance status, and any subsequent cancellation or reversion @S796 */ }
        }
        part successfulCompletionOfScheduledOperationalReports : SuccessfulCompletionOfScheduledOperationalReports;
        part surfaceConstraints : SurfaceConstraints {
            perform action a0 { doc /* combine @S008 */ }
            perform action a1 { doc /* can change the feasible order, timing, and routing of aircraft @S443 */ }
        }
        part surfaceHolds : SurfaceHolds {
            perform action a0 { doc /* constrain multiple rotations @S465 */ }
        }
        part surfaceMovementEvidence : SurfaceMovementEvidence {
            perform action a0 { doc /* support dispute resolution and regulatory audit requests @S802 */ }
        }
        part surfaceSurveillance : SurfaceSurveillance {
            perform action a0 { doc /* shows that runway-entry queues are approaching the metering threshold @S454 */ }
        }
        part surfaceSurveillanceAdapter : SurfaceSurveillanceAdapter {
            perform action a0 { doc /* provide the data feeds needed to maintain a current and consistent operational picture @S018 */ }
            perform action a1 { doc /* provide managed integration points with external systems @S033 */ }
            perform action a2 { doc /* consolidates position updates from the East Apron Sensor and West Apron Sensor @S179 */ }
            perform action a3 { doc /* presents movement indications to the Airport CDM Portal @S179 */ }
            perform action a4 { doc /* confirms whether an aircraft is still at stand, entering the movement area, holding short, or already committed to the departure stream @S281 */ }
            perform action a5 { doc /* confirms that aircraft leaving the pad follow the assigned route and do not block inbound traffic to the same treatment complex @S389 */ }
            perform action a6 { doc /* provides current movement area occupancy and equipment status indicators to the Ramp Movement Board and the Tower Sequence Manager @S445 */ }
            perform action a7 { doc /* verifies that the apron position is physically clear @S474 */ }
            perform action a8 { doc /* normalizes apron sensing data into movement, occupancy, and blockage events that can be correlated with flight milestones @S580 */ }
            perform action a9 { doc /* produces the Runway Lighting Outage Card @S606 */ }
            perform action a10 { doc /* apply position quality checks @S828 */ }
            perform action a11 { doc /* mark uncertain observations @S828 */ }
        }
        part surfaceSurveillanceAdapterInputs : SurfaceSurveillanceAdapterInputs {
            perform action a0 { doc /* support the Ramp Control Lead by confirming aircraft position, stand occupancy, and blocking conditions on critical apron lanes @S204 */ }
            perform action a1 { doc /* confirming aircraft position, stand occupancy, and blocking conditions on critical apron lanes @S204 */ }
        }
        part surveillanceData : SurveillanceData {
            perform action a0 { doc /* conflicts with tower observations @S183 */ }
        }
        part sustainedSaturation : SustainedSaturation {
            perform action a0 { doc /* requiring a Tactical Regulation Proposal @S600 */ }
        }
        part swap : Swap {
            perform action a0 { doc /* remains consistent with regional flow objectives @S671 */ }
            perform action a1 { doc /* creating a new demand peak at a departure fix @S686 */ }
        }
        part swapBetweenCompanyFlights : SwapBetweenCompanyFlights {
            perform action a0 { doc /* transfers a handling bottleneck to another stand @S317 */ }
        }
        part swapVolume : SwapVolume;
        part sweep : Sweep {
            perform action a0 { doc /* identifies debris, leaking fluid, damaged pavement, unsecured equipment, wildlife activity, or lighting damage @S652 */ }
        }
        part systemPart : System {
            perform action a0 { doc /* detects a material difference from the published schedule @S104 */ }
            perform action a1 { doc /* assumes that typical service durations remain valid unless the Handling Resource Planner reports a constraint or the stand status stops advancing @S318 */ }
            perform action a2 { doc /* does not release every aircraft as soon as it becomes ready @S320 */ }
            perform action a3 { doc /* proposes a broader departure delay @S459 */ }
            perform action a4 { doc /* prioritizes removal of surface holds that constrain multiple rotations @S465 */ }
            perform action a5 { doc /* optimizing isolated punctuality impacts @S465 */ }
            perform action a6 { doc /* treats passenger disruption information as a secondary planning signal that can refine, but not replace, capacity and safety constraints in traffic flow decisions @S738 */ }
            perform action a7 { doc /* help the Regional Flow Manager understand where a small metering adjustment may reduce downstream disruption without degrading the Airport Capacity Plan @S739 */ }
            perform action a8 { doc /* records these actions as operational context rather than as passenger service tasks assigned to the airport flow management process @S752 */ }
            perform action a9 { doc /* impose a Ground Delay Program @S953 */ }
            perform action a10 { doc /* change an Airport Acceptance Rate @S953 */ }
            perform action a11 { doc /* alter a tactical measure @S953 */ }
            exhibit state modes {
                state s0 { doc /* Contingency Fallback State @S735 */ }
                state s1 { doc /* Normal Operations @S318,S717 */ }
                state s2 { doc /* Recovery Phase @S320,S717 */ }
                state s3 { doc /* manual operation @S727 */ }
                state s4 { doc /* manual slot control @S728 */ }
            }
        }
        part systemSupportEngineer : SystemSupportEngineer {
            perform action a0 { doc /* participate @S042 */ }
            perform action a1 { doc /* maintain data quality, access control, operational continuity, and controlled configuration of the Regional Flow Platform @S042 */ }
            perform action a2 { doc /* monitors portal availability, interface latency, user session faults, and synchronization status against the Time Synchronization Service @S171 */ }
            perform action a3 { doc /* investigates technical failures in submission, validation, or publication @S688 */ }
            perform action a4 { doc /* altering the operational decision @S688 */ }
            perform action a5 { doc /* classifies the technical condition @S732 */ }
            perform action a6 { doc /* isolates failed components @S732 */ }
            perform action a7 { doc /* advises whether partial restoration is safe for operational use @S732 */ }
            perform action a8 { doc /* may maintain infrastructure components @S772 */ }
            perform action a9 { doc /* investigate technical faults @S772 */ }
            perform action a10 { doc /* investigate technical gaps @S807 */ }
            perform action a11 { doc /* investigate technical causes of missing, delayed, duplicated, or transformed records @S835 */ }
            perform action a12 { doc /* provide evidence needed for stewardship decisions @S835 */ }
            perform action a13 { doc /* train superusers on service status checks, access fault escalation, and safe use of the Contingency Operations Console during partial outages @S877 */ }
            perform action a14 { doc /* monitor defect trends, data quality, access changes, and user adoption @S910 */ }
            perform action a15 { doc /* provide round the clock on call coverage for production incidents affecting the Regional Flow Platform, Airport CDM Portal, Slot Allocation Engine, Departure Metering Service, Arrival Regulation Console, and Alert Distribution Hub @S914 */ }
            perform action a16 { doc /* join the Digital Briefing Room without delay @S916 */ }
            perform action a17 { doc /* advise operational supervisors on technical status, known workarounds, data integrity concerns, and recovery options @S918 */ }
            perform action a18 { doc /* not issue traffic management instructions @S918 */ }
            perform action a19 { doc /* maintain an incident record that captures the initial symptom, affected components, operational state, timeline, mitigation actions, data corrections, and supervisor decisions @S923 */ }
            perform action a20 { doc /* verify that fallback tools, exported operational data, and restoration checkpoints are available @S927 */ }
            perform action a21 { doc /* advising that normal technical service can resume @S927 */ }
        }
        part tacticalConstraints : TacticalConstraints {
            perform action a0 { doc /* affect sector capacity, arrival acceptance, departure release timing, and the sequencing assumptions used by the Meridian regional operation @S323 */ }
            exhibit state modes {
                state s0 { doc /* active @S324 */ }
            }
        }
        part tacticalPlan : TacticalPlan {
            perform action a0 { doc /* should retain normal sequencing @S463 */ }
            perform action a1 { doc /* shift to local metering @S463 */ }
            perform action a2 { doc /* support a Tactical Regulation Proposal @S463 */ }
        }
        part tacticalRegulationProposalReview : TacticalRegulationProposalReview;
        part tacticalRegulationProposalStatus : TacticalRegulationProposalStatus;
        part tacticalRegulationProposalStatusValues : TacticalRegulationProposalStatusValues;
        part targetOffBlockTime : TargetOffBlockTime {
            perform action a0 { doc /* protects the Calculated Takeoff Time @S352 */ }
            perform action a1 { doc /* support a realistic treatment sequence @S376 */ }
            exhibit state modes {
                state s0 { doc /* achievable @S553 */ }
                state s1 { doc /* conditional @S314 */ }
                state s2 { doc /* frozen @S268 */ }
            }
        }
        part targetOffBlockTimeCommitments : TargetOffBlockTimeCommitments;
        part targetOffBlockTimeValues : TargetOffBlockTimeValues;
        part taxiQueues : TaxiQueues {
            perform action a0 { doc /* forming under reduced visibility or wet surface conditions @S367 */ }
        }
        part technicalConformanceDefects : TechnicalConformanceDefects {
            perform action a0 { doc /* do not become unresolved procedural issues @S898 */ }
        }
        part technicalPriorityCases : TechnicalPriorityCases {
            perform action a0 { doc /* include aircraft with abnormal system indications, degraded performance, fuel limitations, or maintenance requirements that make continued flight or extended holding undesirable @S498 */ }
        }
        part temporalSequenceChecks : TemporalSequenceChecks;
        part temporaryAccess : TemporaryAccess;
        part temporaryRestrictedArea : TemporaryRestrictedArea {
            perform action a0 { doc /* reduces usable route options @S327 */ }
            perform action a1 { doc /* affects feeder sectors or arrival metering fixes @S336 */ }
        }
        part terminalAndEnRouteSectorLoads : TerminalAndEnRouteSectorLoads {
            perform action a0 { doc /* can absorb the regulated stream without generating unsafe compression @S402 */ }
            perform action a1 { doc /* generating unsafe compression @S402 */ }
        }
        part terminalCurbSpace : TerminalCurbSpace;
        part timeAboveThreshold : TimeAboveThreshold;
        part timeOfLastAcceptedUpdate : TimeOfLastAcceptedUpdate;
        part timeSynchronizationService : TimeSynchronizationService {
            perform action a0 { doc /* provide governance, security, traceability, and performance measurement capabilities @S034 */ }
            perform action a1 { doc /* provides the reference clock used to compare forecast issue times with operational decision times @S110 */ }
            perform action a2 { doc /* are time-stamped by the Time Synchronization Service @S149 */ }
            perform action a3 { doc /* keep tower, duty desk, surveillance, and portal event times aligned @S187 */ }
            perform action a4 { doc /* provides the reference clock for all target time calculations @S256 */ }
            perform action a5 { doc /* provides the common time reference for sweep records, readiness confirmations, and safety-related release decisions @S651 */ }
            perform action a6 { doc /* applied by the Time Synchronization Service @S792 */ }
            perform action a7 { doc /* provide the common time basis used for freshness calculations across the Regional Flow Platform @S824 */ }
        }
        part timestamps : Timestamps {
            perform action a0 { doc /* use the same operational clock @S422 */ }
        }
        part tow : Tow {
            perform action a0 { doc /* would create an overlapping occupancy condition at a stand or adjacent service lane @S210 */ }
        }
        part towbarAvailability : TowbarAvailability {
            perform action a0 { doc /* cannot support the agreed pushback sequence @S523 */ }
        }
        part towerAndAirportDutyCoordination : TowerAndAirportDutyCoordination {
            perform action a0 { doc /* establishes the working link between live control positions, the airport duty desk, surface surveillance feeds, and operational safety checks @S174 */ }
        }
        part towerCoordination : TowerCoordination {
            perform action a0 { doc /* act @S331 */ }
        }
        part towerParticipants : TowerParticipants {
            perform action a0 { doc /* share one operational assumption @S372 */ }
        }
        part towerPlanning : TowerPlanning {
            perform action a0 { doc /* continue without interpreting ramp work details @S536 */ }
            perform action a1 { doc /* interpreting ramp work details @S536 */ }
        }
        part towerRoles : TowerRoles {
            perform action a0 { doc /* share the same expectation for aircraft readiness @S560 */ }
        }
        part towerSequenceManager : TowerSequenceManager {
            perform action a0 { doc /* support the transition from regional planning decisions to executable airport and tower actions @S017 */ }
            perform action a1 { doc /* support tactical airport and regional coordination @S032 */ }
            perform action a2 { doc /* reflects the current runway configuration @S089 */ }
            perform action a3 { doc /* uses validated surface status @S180 */ }
            perform action a4 { doc /* support local sequencing decisions @S180 */ }
            perform action a5 { doc /* without replacing controller judgment or established radio procedures @S180 */ }
            perform action a6 { doc /* receives the current ramp intent through system synchronization @S217 */ }
            perform action a7 { doc /* maintains the tactical runway sequence expectation @S254 */ }
            perform action a8 { doc /* highlights cases where the Calculated Takeoff Time is inconsistent with the local departure order @S254 */ }
            perform action a9 { doc /* builds a provisional order by runway, departure fix, aircraft wake category, and locally configured spacing rule @S279 */ }
            perform action a10 { doc /* applies the active spacing rules from the Business Rules Registry @S297 */ }
            perform action a11 { doc /* highlights flights that may miss their Calculated Takeoff Time @S297 */ }
            perform action a12 { doc /* refresh affected departure sequence advisories @S334 */ }
            perform action a13 { doc /* reserves departure sequence positions only for aircraft with an achievable pad release time and a valid runway taxi path @S380 */ }
            perform action a14 { doc /* confirms stable spacing and runway occupancy performance @S411 */ }
            perform action a15 { doc /* uses the hold advice @S450 */ }
            perform action a16 { doc /* prevent a departure from being sequenced ahead of a fueling constraint that is still active @S450 */ }
            perform action a17 { doc /* receives a stable readiness indicator and an escalation flag @S536 */ }
            perform action a18 { doc /* does not advance an aircraft toward an active departure sequence unless the remote stand release time supports the expected taxi plan @S552 */ }
            perform action a19 { doc /* considers confirmed apron blockage @S583 */ }
            perform action a20 { doc /* determining whether a departure can be included in the next practical movement sequence @S583 */ }
            perform action a21 { doc /* displays the accepted constraint @S702 */ }
            perform action a22 { doc /* support runway sequencing decisions @S702 */ }
            perform action a23 { doc /* reduce conflicting tactical instructions @S702 */ }
            perform action a24 { doc /* provide actual movement milestones that support independent verification of slot performance @S801 */ }
            perform action a25 { doc /* provide runway sequence counts @S844 */ }
            perform action a26 { doc /* receive only the information needed for tactical sequencing @S950 */ }
            perform action a27 { doc /* must use the approved rules recorded in the Business Rules Registry @S980 */ }
        }
        part towerSequenceWorkflow : TowerSequenceWorkflow {
            perform action a0 { doc /* emphasizes measured acceleration rather than first-come recovery @S298 */ }
        }
        part towerSequencingFunction : TowerSequencingFunction {
            perform action a0 { doc /* translates the frozen operational targets from the regional flow process into an executable runway order for departures at Meridian Regional Airport @S275 */ }
        }
        part towerSupervisor : TowerSupervisor {
            perform action a0 { doc /* require a common basis for decisions rather than separate local views of the same operational picture @S011 */ }
            perform action a1 { doc /* participate @S040 */ }
            perform action a2 { doc /* represent local airport, tower, ramp, handling, and winter operations considerations @S040 */ }
            perform action a3 { doc /* sends the Runway Inspection Note before the first planning consolidation window @S060 */ }
            perform action a4 { doc /* declares anticipated runway configuration, usable operating length assumptions, and any local sequencing constraints that affect the North Runway Meter and South Runway Meter @S061 */ }
            perform action a5 { doc /* confirms that the Tower Sequence Manager reflects the current runway configuration @S089 */ }
            perform action a6 { doc /* reviews metering effects in the Tower Sequence Manager @S143 */ }
            perform action a7 { doc /* reviewing runway configuration assumptions, departure sequence feasibility, and tactical tower constraints @S160 */ }
            perform action a8 { doc /* keeps the Airport Duty Manager informed of conditions that may affect runway, taxiway, stand, or apron availability @S175 */ }
            perform action a9 { doc /* used by Tower Supervisor during voice coordination drills @S176 */ }
            perform action a10 { doc /* agree on the operational interpretation @S183 */ }
            perform action a11 { doc /* verifies that any proposed reduction in declared runway use is consistent with observed traffic, controller workload, and the current safety position @S189 */ }
            perform action a12 { doc /* has confirmed that the movement can be integrated with the active ground route and runway plan @S202 */ }
            perform action a13 { doc /* may reject a proposed departure opportunity when runway safety, wake spacing, or local sequencing conditions make the proposal impracticable @S243 */ }
            perform action a14 { doc /* may challenge a proposed Calculated Takeoff Time @S263 */ }
            perform action a15 { doc /* uses the Tower Sequence Manager @S277 */ }
            perform action a16 { doc /* confirm that each flight can be advanced without creating unsafe surface compression @S277 */ }
            perform action a17 { doc /* can view both queues together @S280 */ }
            perform action a18 { doc /* may intervene @S287 */ }
            perform action a19 { doc /* compares pad release expectations with runway queue gaps @S296 */ }
            perform action a20 { doc /* accepting an aircraft into the active departure stream @S296 */ }
            perform action a21 { doc /* confirm that any revised off-block sequence remains compatible with the Departure Metering Service @S313 */ }
            perform action a22 { doc /* confirm the active interpretation of the restriction @S345 */ }
            perform action a23 { doc /* monitors whether the planned release rate remains compatible with departure spacing and runway crossing demand @S358 */ }
            perform action a24 { doc /* agree whether the metering horizon should be extended so that delay is absorbed before pushback rather than near the runway @S368 */ }
            perform action a25 { doc /* protects runway departure spacing @S388 */ }
            perform action a26 { doc /* accounting for reduced braking action, slower lineup, and possible repeat treatment requests @S388 */ }
            perform action a27 { doc /* confirms whether the proposed landing rate is compatible with runway occupancy, missed approach protection, and local spacing constraints @S401 */ }
            perform action a28 { doc /* uses the display to see runway assignment pressure, airborne sequence spacing, and expected crossing points at the North Runway Meter and the South Runway Meter @S425 */ }
            perform action a29 { doc /* see runway assignment pressure, airborne sequence spacing, and expected crossing points at the North Runway Meter and the South Runway Meter @S425 */ }
            perform action a30 { doc /* coordinates airborne sequencing with the Airspace Sector Planner @S500 */ }
            perform action a31 { doc /* uses the same result @S605 */ }
            perform action a32 { doc /* understand whether a runway queue is being held for surface capacity, runway capacity, or downstream airspace capacity @S605 */ }
            perform action a33 { doc /* does not use a stand readiness indication as clearance for aircraft movement @S655 */ }
            perform action a34 { doc /* retains authority to reject a swap @S676 */ }
            perform action a35 { doc /* reject a swap @S676 */ }
            perform action a36 { doc /* uses the Runway Lighting Outage Card @S693 */ }
            perform action a37 { doc /* confirm which runway lighting elements are unavailable @S693 */ }
            perform action a38 { doc /* approving the operational status shown in the Tower Sequence Manager @S693 */ }
            perform action a39 { doc /* retains authority over tactical runway sequencing @S748 */ }
            perform action a40 { doc /* may reject any advisory that would impair safe separation, wake spacing, or local controller workload @S748 */ }
            perform action a41 { doc /* receive role profiles that reflect their normal operational responsibilities @S766 */ }
            perform action a42 { doc /* may operate the Tower Sequence Manager @S769 */ }
            perform action a43 { doc /* view runway metering information @S769 */ }
            perform action a44 { doc /* may not modify airline recovery priorities or user entitlement records @S769 */ }
            perform action a45 { doc /* own tower sequence status data maintained for the Tower Sequence Manager @S817 */ }
            perform action a46 { doc /* receive practical training on the Tower Sequence Manager, Departure Metering Service, Arrival Regulation Console, North Runway Meter, and South Runway Meter @S866 */ }
            perform action a47 { doc /* have named accountable implementation contacts @S893 */ }
            perform action a48 { doc /* retain operational command authority during support activity @S917 */ }
            perform action a49 { doc /* compare recommendations with actual outcomes @S959 */ }
            perform action a50 { doc /* retains authority for air traffic control safety decisions and runway sequencing @S963 */ }
        }
        part towerSupervisoryPersonnel : TowerSupervisoryPersonnel;
        part towerTeam : TowerTeam {
            perform action a0 { doc /* trust the displayed status @S291 */ }
        }
        part towerUsers : TowerUsers {
            perform action a0 { doc /* interpret treatment age consistently @S382 */ }
        }
        part towingMovements : TowingMovements {
            perform action a0 { doc /* remove a blocking aircraft @S206 */ }
            perform action a1 { doc /* protect a confirmed departure sequence @S206 */ }
            perform action a2 { doc /* create capacity for an inbound aircraft with no equivalent stand option @S206 */ }
        }
        part towingProviders : TowingProviders;
        part towingResources : TowingResources {
            perform action a0 { doc /* affect apron readiness @S212 */ }
        }
        part trafficDemand : TrafficDemand {
            perform action a0 { doc /* exceeds available capacity @S015 */ }
        }
        part trainingAssessments : TrainingAssessments {
            perform action a0 { doc /* shall verify that users can identify stale data, time synchronization problems, duplicate flights, conflicting constraints, and inappropriate automation reliance before such issues affect live operations @S886 */ }
        }
        part trainingForTheMeridianRegionalAirTrafficFlowManagementAndAirportCollaborativeDecisionMakingSystem : TrainingForTheMeridianRegionalAirTrafficFlowManagementAndAirportCollaborativeDecisionMakingSystem {
            perform action a0 { doc /* cover normal coordination, constrained operations, recovery actions, and degraded system use @S863 */ }
        }
        part trajectoryPrediction : TrajectoryPrediction {
            perform action a0 { doc /* make greater use of weather features, sector configuration, runway direction, and surface movement status @S942 */ }
            perform action a1 { doc /* estimating flight progress @S942 */ }
        }
        part treatedAircraft : TreatedAircraft {
            perform action a0 { doc /* cannot depart within its applicable holdover reference @S390 */ }
            exhibit state modes {
                state s0 { doc /* queue state @S390 */ }
            }
        }
        part treatment : Treatment {
            exhibit state modes {
                state s0 { doc /* expired @S390 */ }
            }
        }
        part treatmentProgress : TreatmentProgress {
            perform action a0 { doc /* changes @S294 */ }
        }
        part triggerConditions : TriggerConditions {
            perform action a0 { doc /* would justify moving from Normal Operations to Adverse Weather Mode @S087 */ }
        }
        part tugRouting : TugRouting {
            perform action a0 { doc /* affects the departure plan @S184 */ }
        }
        part turnaroundEvent : TurnaroundEvent {
            perform action a0 { doc /* affects a regulated departure or constrained arrival @S156 */ }
        }
        part turnaroundMilestone : TurnaroundMilestone {
            exhibit state modes {
                state s0 { doc /* uncertain @S571 */ }
            }
        }
        part turnaroundStatus : TurnaroundStatus;
        part uncontrolledParallelRecords : UncontrolledParallelRecords {
            perform action a0 { doc /* undermine common situational awareness @S907 */ }
        }
        part uncontrolledPushback : UncontrolledPushback {
            perform action a0 { doc /* would create an unstable surface queue @S453 */ }
        }
        part uncontrolledPushbackSurges : UncontrolledPushbackSurges {
            perform action a0 { doc /* overload taxiways @S298 */ }
            perform action a1 { doc /* recreate delay @S298 */ }
        }
        part unevenAvailabilityOfGroundHandlingResources : UnevenAvailabilityOfGroundHandlingResources;
        part unusualAccessPatterns : UnusualAccessPatterns {
            perform action a0 { doc /* indicate possible credential compromise or inappropriate privilege use @S780 */ }
        }
        part updatedDepartureReadinessInformation : UpdatedDepartureReadinessInformation;
        part upstreamDelay : UpstreamDelay {
            perform action a0 { doc /* would create a disproportionate connection or aircraft rotation penalty @S403 */ }
        }
        part urgentDiscrepancies : UrgentDiscrepancies {
            perform action a0 { doc /* change a metering, arrival regulation, or slot allocation decision @S834 */ }
        }
        part useOfEmergencyAccess : UseOfEmergencyAccess {
            perform action a0 { doc /* generate prominent audit events @S785 */ }
            perform action a1 { doc /* require post-event review by the Data Governance Steward and the responsible operational authority @S785 */ }
        }
        part user : User {
            perform action a0 { doc /* sees only the workspaces, aircraft, stands, and decision records appropriate to the assigned role @S152 */ }
            perform action a1 { doc /* changes role @S781 */ }
            perform action a2 { doc /* leaves an organization @S781 */ }
            perform action a3 { doc /* becomes subject to an operational integrity concern @S781 */ }
        }
        part userDecisions : UserDecisions;
        part users : Users {
            perform action a0 { doc /* confirmed by users @S165 */ }
            perform action a1 { doc /* can approve frozen-time changes, manual exemptions, or retrospective corrections @S272 */ }
            perform action a2 { doc /* relying on the normal decision support path without additional verification @S715 */ }
            perform action a3 { doc /* compare automated recommendations with local knowledge @S883 */ }
            perform action a4 { doc /* document significant decisions in the Collaborative Decision Log @S883 */ }
            perform action a5 { doc /* explain departures from system proposals @S883 */ }
            perform action a6 { doc /* copy critical values manually @S885 */ }
            perform action a7 { doc /* can identify stale data, time synchronization problems, duplicate flights, conflicting constraints, and inappropriate automation reliance @S886 */ }
        }
        part validationFailureRates : ValidationFailureRates;
        part validationRules : ValidationRules {
            perform action a0 { doc /* include schema checks, mandatory field checks, code set checks, temporal sequence checks, and operational plausibility checks @S826 */ }
        }
        part validityIntervals : ValidityIntervals {
            perform action a0 { doc /* use the same operational clock @S422 */ }
        }
        part vehicleAvailability : VehicleAvailability;
        part vehicles : Vehicles;
        part visibilityReductions : VisibilityReductions {
            perform action a0 { doc /* change achievable runway throughput @S409 */ }
        }
        part visualConfirmation : VisualConfirmation;
        part visualState : VisualState {
            perform action a0 { doc /* distinguishes current, aging, stale, and unavailable data @S823 */ }
        }
        part walkingRoutes : WalkingRoutes {
            exhibit state modes {
                state s0 { doc /* less predictable @S563 */ }
            }
        }
        part waves : Waves {
            perform action a0 { doc /* group airports by interface maturity, traffic dependency, stakeholder readiness, and available support capacity @S909 */ }
        }
        part weather : Weather {
            perform action a0 { doc /* affect available capacity @S041 */ }
            perform action a1 { doc /* degrade faster than the model forecast @S410 */ }
        }
        part weatherCategory : WeatherCategory {
            perform action a0 { doc /* changes @S431 */ }
        }
        part weatherConstraints : WeatherConstraints {
            perform action a0 { doc /* may affect regional capacity @S967 */ }
        }
        part weatherFeed : WeatherFeed {
            exhibit state modes {
                state s0 { doc /* degraded @S111 */ }
            }
        }
        part weatherIngestGateway : WeatherIngestGateway {
            perform action a0 { doc /* provide the data feeds needed to maintain a current and consistent operational picture @S018 */ }
            perform action a1 { doc /* provide managed integration points with external systems @S033 */ }
            perform action a2 { doc /* makes the outlook available to the Capacity Assessment Module @S057 */ }
            perform action a3 { doc /* preserves the forecast issue time for audit and later performance review @S057 */ }
            perform action a4 { doc /* normalizes external and local meteorological feeds @S102 */ }
            perform action a5 { doc /* accepts aviation forecasts, radar-derived precipitation fields, lightning alerts, wind forecasts, ceiling and visibility forecasts, and runway condition weather inputs from approved sources @S108 */ }
            perform action a6 { doc /* marks the feed as degraded @S111 */ }
            perform action a7 { doc /* rather than silently excluding it from the operational picture @S111 */ }
            perform action a8 { doc /* issue time-stamped weather condition updates for use in tower and airport duty coordination @S182 */ }
            perform action a9 { doc /* updates the arrival model @S409 */ }
            perform action a10 { doc /* supports the assumptions used during briefings @S873 */ }
            perform action a11 { doc /* provide the common inputs needed to connect airspace capacity and airport capacity in the same prediction cycle @S943 */ }
        }
        part weatherRouting : WeatherRouting {
            perform action a0 { doc /* dominated fuel performance @S858 */ }
        }
        part westApronSensor : WestApronSensor {
            perform action a0 { doc /* provide additional indicators of emerging capacity loss and operational imbalance @S019 */ }
            perform action a1 { doc /* improve queue accuracy @S282 */ }
            perform action a2 { doc /* detecting aircraft movement @S282 */ }
            perform action a3 { doc /* provide supporting movement evidence for the reopened area @S474 */ }
            perform action a4 { doc /* provide supporting surveillance cues @S645 */ }
            perform action a5 { doc /* support independent checks of queue length where surveillance coverage is available @S845 */ }
        }
        part wetPavement : WetPavement {
            perform action a0 { doc /* increase the cost of taxiway conflicts and blocked stands @S464 */ }
        }
        part wind : Wind {
            perform action a0 { doc /* can increase the probability of foreign object debris and surface contamination @S661 */ }
        }
        part windShifts : WindShifts {
            perform action a0 { doc /* change achievable runway throughput @S409 */ }
        }
        part winterOperations : WinterOperations {
            perform action a0 { doc /* affect departure readiness, metering stability, or achievable throughput @S092 */ }
        }
        part workflow : Workflow {
            perform action a0 { doc /* starts @S278 */ }
        }
        part workloadMonitoring : WorkloadMonitoring;
        part workstationLayouts : WorkstationLayouts {
            perform action a0 { doc /* shall support rapid comparison between the Common Situation Display, Airport CDM Portal, Tower Sequence Manager, Ramp Movement Board, and relevant advisory messages @S885 */ }
            perform action a1 { doc /* without forcing users to copy critical values manually @S885 */ }
        }
        flow f0 of ControlledInterfaceItem from airportCDMPortal to airportStakeholders { doc /* @S016 */ }
        flow f1 of SharedViewOfDemandCapacityConstraintsAndActiveTrafficManagementMeasuresItem from commonSituationDisplay to authorizedUsers { doc /* @S020 */ }
        flow f2 of ReferenceRecordItem from flightDataExchange to laterComparisons { doc /* @S052 */ }
        flow f3 of NormalizedScheduleItem from flightDataExchange to demandPredictionService { doc /* @S053 */ }
        flow f4 of MorningWeatherOutlookItem from meteorologyBriefingOfficer to weatherIngestGateway { doc /* @S056 */ }
        flow f6 of MorningWeatherOutlookItem from weatherIngestGateway to capacityAssessmentModule { doc /* @S057 */ }
        flow f7 of InformationItem from rampMovementBoard to rampControlLead { doc /* @S063 */ }
        flow f8 of InformationItem from eastApronSensor to rampControlLead { doc /* @S063 */ }
        flow f9 of InformationItem from westApronSensor to rampControlLead { doc /* @S063 */ }
        flow f10 of InformationItem from handlingCoordinationCalls to rampControlLead { doc /* @S063 */ }
        flow f11 of RunwayDeclarationItem from towerSupervisor to capacityAssessmentModule { doc /* @S066 */ }
        flow f12 of UnresolvedAssumptionsItem from digitalBriefingRoom to collaborativeDecisionLog { doc /* @S071 */ }
        flow f13 of MorningPlanItem from alertDistributionHub to participatingRoles { doc /* @S073 */ }
        flow f14 of DemandSmoothingItem from airspaceSectorPlanner to regionalFlowManager { doc /* @S079 */ }
        flow f15 of CurrentBusinessRulesRegistryParametersItem from businessRulesRegistry to slotAllocationEngine { doc /* @S080 */ }
        flow f16 of ExternalCoordinationOutcomesItem from networkOperationsLiaison to collaborativeDecisionLog { doc /* @S084 */ }
        flow f17 of MaterialDeviationsItem from groundHandlingDispatcher to airportDutyManager { doc /* @S091 */ }
        flow f18 of CivilRoutingOptionsItem from militaryAirspaceLiaison to regionalFlowManager { doc /* @S093 */ }
        flow f19 of OutputsItem from departureMeteringService to commonSituationDisplay { doc /* @S095 */ }
        flow f20 of OutputsItem from arrivalRegulationConsole to commonSituationDisplay { doc /* @S095 */ }
        flow f21 of SynchronizedTimestampsItem from timeSynchronizationService to auditEventLedger { doc /* @S098 */ }
        flow f22 of DemandForecastsItem from demandPredictionService to capacityPicture { doc /* @S100 */ }
        flow f23 of DemandForecastsItem from demandPredictionService to regionalFlowPlatform { doc /* @S101 */ }
        flow f24 of FiledFlightInformationItem from flightDataExchange to demandPredictionService { doc /* @S103 */ }
        flow f25 of CurrentOperatingScheduleItem from airlineInterfaceAdapter to demandPredictionService { doc /* @S103 */ }
        flow f26 of AviationForecastsItem from approvedSources to weatherIngestGateway { doc /* @S108 */ }
        flow f27 of RadarDerivedPrecipitationFieldsItem from approvedSources to weatherIngestGateway { doc /* @S108 */ }
        flow f28 of LightningAlertsItem from approvedSources to weatherIngestGateway { doc /* @S108 */ }
        flow f29 of WindForecastsItem from approvedSources to weatherIngestGateway { doc /* @S108 */ }
        flow f30 of CeilingAndVisibilityForecastsItem from approvedSources to weatherIngestGateway { doc /* @S108 */ }
        flow f31 of RunwayConditionWeatherInputsItem from approvedSources to weatherIngestGateway { doc /* @S108 */ }
        flow f32 of RunwaySpecificCapacityValuesItem from capacityAssessmentModule to northRunwayMeter { doc /* @S114 */ }
        flow f33 of RunwaySpecificCapacityValuesItem from capacityAssessmentModule to southRunwayMeter { doc /* @S114 */ }
        flow f34 of ProbabilityValueItem from source to confidenceRecord { doc /* @S118 */ }
        flow f35 of TheCapacityPictureMayChangeItem from alertDistributionHub to regionalFlowManager { doc /* @S121 */ }
        flow f36 of TheCapacityPictureMayChangeItem from alertDistributionHub to towerSupervisor { doc /* @S121 */ }
        flow f37 of TheCapacityPictureMayChangeItem from alertDistributionHub to airlineOperationsCoordinator { doc /* @S121 */ }
        flow f38 of SynchronizedTimestampsItem from timeSynchronizationService to collaborativeDecisionLog { doc /* @S122 */ }
        flow f39 of TraceFromIncomingForecastProductToCapacityValueItem from auditEventLedger to performanceAnalyticsWarehouse { doc /* @S123 */ }
        flow f40 of FlightIntentMessageItem from airlineOperationsCentre to airlineInterfaceAdapter { doc /* @S126 */ }
        flow f41 of AcceptedIntentDataItem from airlineInterfaceAdapter to flightDataExchange { doc /* @S128 */ }
        flow f42 of AcceptedConstraintsItem from airlineInterfaceAdapter to airlineOperationsCentres { doc /* @S135 */ }
        flow f43 of CurrentRegionalDemandAndConstraintContextItem from regionalFlowPlatform to sharedWorkspace { doc /* @S164 */ }
        flow f44 of AffectedFlightItem from airportCDMPortal to roleAccountableForTheNextUpdate { doc /* @S166 */ }
        flow f45 of ConditionsThatMayAffectRunwayTaxiwayStandOrApronAvailabilityItem from towerSupervisor to airportDutyManager { doc /* @S175 */ }
        flow f46 of PositionUpdatesItem from eastApronSensor to surfaceSurveillanceAdapter { doc /* @S179 */ }
        flow f47 of PositionUpdatesItem from westApronSensor to surfaceSurveillanceAdapter { doc /* @S179 */ }
        flow f48 of MovementIndicationsItem from surfaceSurveillanceAdapter to airportCDMPortal { doc /* @S179 */ }
        flow f49 of ApprovedDutyCoordinationAlertsItem from alertDistributionHub to affectedOperationalRoles { doc /* @S193 */ }
        flow f50 of TransactionItem from identityAccessService to auditEventLedger { doc /* @S194 */ }
        flow f51 of AircraftPositionItem from surfaceSurveillanceAdapter to rampControlLead { doc /* @S204 */ }
        flow f52 of StandOccupancyItem from surfaceSurveillanceAdapter to rampControlLead { doc /* @S204 */ }
        flow f53 of BlockingConditionsItem from surfaceSurveillanceAdapter to rampControlLead { doc /* @S204 */ }
        flow f54 of EastApronSensorIndicationsItem from eastApronSensor to rampControlLead { doc /* @S205 */ }
        flow f55 of WestApronSensorIndicationsItem from westApronSensor to rampControlLead { doc /* @S205 */ }
        flow f56 of OverlappingOccupancyConditionItem from gateConflictDetector to rampControlLead { doc /* @S210 */ }
        flow f57 of HandlingResourcePlannerConstraintsItem from handlingResourcePlanner to rampControlLead { doc /* @S213 */ }
        flow f58 of ApronCongestionItem from rampControlLead to towerSupervisor { doc /* @S218 */ }
        flow f59 of ApronCongestionItem from rampControlLead to airportDutyManager { doc /* @S218 */ }
        flow f60 of MovementUpdatesItem from rampMovementBoard to auditEventLedger { doc /* @S222 */ }
        flow f61 of DemandItem from demandPredictionService to slotAllocationEngine { doc /* @S225 */ }
        flow f62 of ConstraintsItem from capacityAssessmentModule to slotAllocationEngine { doc /* @S225 */ }
        flow f63 of AcceptedOrRejectedExemptionWithTheRuleAppliedTheApprovingRoleAndTheExpectedOperationalConsequenceItem from slotCoordinator to collaborativeDecisionLog { doc /* @S239 */ }
        flow f64 of ProposedDepartureOpportunitiesItem from departureMeteringService to towerSequenceManager { doc /* @S242 */ }
        flow f65 of CalculatedTakeoffTimeItem from departureMeteringService to towerSequenceManager { doc /* @S242 */ }
        flow f66 of StandReadinessItem from rampMovementBoard to regionalFlowPlatform { doc /* @S250 */ }
        flow f67 of CurrentAgreedTargetSetItem from commonSituationDisplay to operationalParticipants { doc /* @S265 */ }
        flow f68 of AuditRecordsItem from auditEventLedger to performanceAnalyticsWarehouse { doc /* @S274 */ }
        flow f69 of FrozenOperationalTargetsItem from regionalFlowProcess to towerSequencingFunction { doc /* @S275 */ }
        flow f70 of RunwayDemandItem from towerSequenceManager to rampControlLead { doc /* @S283 */ }
        flow f71 of TowerReadinessChangesItem from airportCDMPortal to authenticatedAirlineAndHandlingUsers { doc /* @S293 */ }
        flow f72 of ActiveSpacingRulesItem from businessRulesRegistry to towerSequenceManager { doc /* @S297 */ }
        flow f73 of ExpectedServiceCompletionTimesItem from groundHandlingDispatcher to handlingResourcePlanner { doc /* @S302 */ }
        flow f74 of ResourceDrivenFeasibilityStatusItem from airportCDMPortal to airlineOperationsCoordinator { doc /* @S312 */ }
        flow f75 of ResourceDrivenFeasibilityStatusItem from airportCDMPortal to aircraftOperatorRepresentative { doc /* @S312 */ }
        flow f76 of WhetherTheOperatorCanAcceptALaterOffBlockTimeWithoutCausingCrewConnectionOrAircraftRotationImpactsItem from aircraftOperatorRepresentative to airlineOperationsCoordinator { doc /* @S317 */ }
        flow f77 of AirspaceAlertsItem from alertDistributionHub to flowManagement { doc /* @S331 */ }
        flow f78 of AirspaceAlertsItem from alertDistributionHub to sectorPlanning { doc /* @S331 */ }
        flow f79 of AirspaceAlertsItem from alertDistributionHub to towerCoordination { doc /* @S331 */ }
        flow f80 of AirspaceAlertsItem from alertDistributionHub to operatorCoordinationRoles { doc /* @S331 */ }
        flow f81 of SubscriptionRulesItem from businessRulesRegistry to alertDistributionHub { doc /* @S332 */ }
        flow f82 of AirspaceAlertsItem from alertDistributionHub to operationalPositions { doc /* @S332 */ }
        flow f83 of ActiveRestrictionStatusItem from airportCDMPortal to commonSituationDisplay { doc /* @S337 */ }
        flow f84 of ExpectedOperationalEffectItem from airportCDMPortal to commonSituationDisplay { doc /* @S337 */ }
        flow f85 of RelatedCoordinationNotesItem from airportCDMPortal to commonSituationDisplay { doc /* @S337 */ }
        flow f86 of ActiveRestrictionStatusItem from airportCDMPortal to airlineOperationsCoordinator { doc /* @S338 */ }
        flow f87 of ExpectedOperationalEffectItem from airportCDMPortal to airlineOperationsCoordinator { doc /* @S338 */ }
        flow f88 of RelatedCoordinationNotesItem from airportCDMPortal to airlineOperationsCoordinator { doc /* @S338 */ }
        flow f89 of AirportAcceptanceRateItem from capacityAssessmentModule to operationalPlanningCycle { doc /* @S341 */ }
        flow f90 of DepartureDemandProfileItem from demandPredictionService to capacityAssessmentModule { doc /* @S351 */ }
        flow f91 of AffectedRunwayQueueItem from alertDistributionHub to commonSituationDisplay { doc /* @S366 */ }
        flow f92 of ExpiredTreatmentsItem from commonSituationDisplay to participants { doc /* @S391 */ }
        flow f93 of PadClosuresItem from commonSituationDisplay to participants { doc /* @S391 */ }
        flow f94 of FluidShortagesItem from commonSituationDisplay to participants { doc /* @S391 */ }
        flow f95 of RampBlockagesItem from commonSituationDisplay to participants { doc /* @S391 */ }
        flow f96 of OperationalBasisItem from capacityAssessmentModule to commonSituationDisplay { doc /* @S400 */ }
        flow f97 of ArrivalPlanItem from airportCDMPortal to aircraftOperatorRepresentative { doc /* @S405 */ }
        flow f98 of AcknowledgementsItem from airportCDMPortal to collaborativeDecisionLog { doc /* @S405 */ }
        flow f99 of CombinedTacticalViewItem from integratedTacticalManagementPosition to regionalFlowManager { doc /* @S420 */ }
        flow f100 of BaseMapItem from commonSituationDisplay to integratedTacticalManagementPosition { doc /* @S421 */ }
        flow f101 of TimelineItem from commonSituationDisplay to integratedTacticalManagementPosition { doc /* @S421 */ }
        flow f102 of FlightListItem from commonSituationDisplay to integratedTacticalManagementPosition { doc /* @S421 */ }
        flow f103 of MeasureStatusPanelsItem from commonSituationDisplay to integratedTacticalManagementPosition { doc /* @S421 */ }
        flow f104 of TargetOffBlockTimeItem from airportCDMPortal to integratedTacticalManagementPosition { doc /* @S429 */ }
        flow f105 of StakeholderRemarksItem from airportCDMPortal to integratedTacticalManagementPosition { doc /* @S429 */ }
        flow f106 of WeatherImpactsItem from weatherIngestGateway to meteorologyBriefingOfficer { doc /* @S434 */ }
        flow f107 of TimelineItem from commonSituationDisplay to flowStaff { doc /* @S437 */ }
        flow f108 of TimelineItem from commonSituationDisplay to airlineOperationsCoordinator { doc /* @S437 */ }
        flow f109 of TimelineItem from commonSituationDisplay to aircraftOperatorRepresentative { doc /* @S437 */ }
        flow f110 of CurrentMovementAreaOccupancyItem from surfaceSurveillanceAdapter to rampMovementBoard { doc /* @S445 */ }
        flow f111 of EquipmentStatusIndicatorsItem from surfaceSurveillanceAdapter to rampMovementBoard { doc /* @S445 */ }
        flow f112 of CurrentMovementAreaOccupancyItem from surfaceSurveillanceAdapter to towerSequenceManager { doc /* @S445 */ }
        flow f113 of EquipmentStatusIndicatorsItem from surfaceSurveillanceAdapter to towerSequenceManager { doc /* @S445 */ }
        flow f114 of OperationalSignificanceItem from airportDutyManager to airportCDMPortal { doc /* @S447 */ }
        flow f115 of RunwayEntryQueuesItem from surfaceSurveillance to northRunwayMeter { doc /* @S454 */ }
        flow f116 of CandidatePushbackSpacingItem from departureMeteringService to slotAllocationEngine { doc /* @S456 */ }
        flow f117 of ConflictingPushbacksItem from rampMovementBoard to nullPart { doc /* @S458 */ }
        flow f118 of BlockedLeadInLinesItem from rampMovementBoard to nullPart { doc /* @S458 */ }
        flow f119 of SaturatedHoldingPointsItem from rampMovementBoard to nullPart { doc /* @S458 */ }
        flow f120 of InsufficientRoomForSafeWingtipClearanceItem from rampMovementBoard to nullPart { doc /* @S458 */ }
        flow f121 of SurfaceEquipmentAdvisoriesItem from alertDistributionHub to subscribedOperationalRoles { doc /* @S461 */ }
        flow f122 of ApronCongestionAdvisoriesItem from alertDistributionHub to subscribedOperationalRoles { doc /* @S461 */ }
        flow f123 of ActiveSurfaceAdvisoriesItem from commonSituationDisplay to authorizedUsers { doc /* @S462 */ }
        flow f124 of AffectedStandsItem from commonSituationDisplay to authorizedUsers { doc /* @S462 */ }
        flow f125 of TaxiSegmentsItem from commonSituationDisplay to authorizedUsers { doc /* @S462 */ }
        flow f126 of RunwayMetersItem from commonSituationDisplay to authorizedUsers { doc /* @S462 */ }
        flow f127 of FlightIdentifiersItem from commonSituationDisplay to authorizedUsers { doc /* @S462 */ }
        flow f128 of ActiveSurfaceAdvisoriesItem from commonSituationDisplay to regionalFlowManager { doc /* @S463 */ }
        flow f129 of AcceptedSurfaceEquipmentAdjustmentItem from nullPart to collaborativeDecisionLog { doc /* @S466 */ }
        flow f130 of AcceptedFuelHoldAdjustmentItem from nullPart to collaborativeDecisionLog { doc /* @S466 */ }
        flow f131 of AcceptedRunwayMeteringAdjustmentItem from nullPart to collaborativeDecisionLog { doc /* @S466 */ }
        flow f132 of AcceptedApronCongestionAdjustmentItem from nullPart to collaborativeDecisionLog { doc /* @S466 */ }
        flow f133 of AcceptedSurfaceEquipmentAdjustmentItem from nullPart to auditEventLedger { doc /* @S466 */ }
        flow f134 of AcceptedFuelHoldAdjustmentItem from nullPart to auditEventLedger { doc /* @S466 */ }
        flow f135 of AcceptedRunwayMeteringAdjustmentItem from nullPart to auditEventLedger { doc /* @S466 */ }
        flow f136 of AcceptedApronCongestionAdjustmentItem from nullPart to auditEventLedger { doc /* @S466 */ }
        flow f137 of GateConflictItem from airportCDMPortal to nullPart { doc /* @S470 */ }
        flow f138 of AffectedFlightsItem from airportCDMPortal to nullPart { doc /* @S470 */ }
        flow f139 of PassengerConnectionExposureItem from airportCDMPortal to nullPart { doc /* @S470 */ }
        flow f140 of AircraftSizeCompatibilityItem from airportCDMPortal to nullPart { doc /* @S470 */ }
        flow f141 of LatestFeasibleOffBlockTimeItem from airportCDMPortal to nullPart { doc /* @S470 */ }
        flow f142 of SupportingMovementEvidenceItem from eastApronSensor to nullPart { doc /* @S474 */ }
        flow f143 of SupportingMovementEvidenceItem from westApronSensor to nullPart { doc /* @S474 */ }
        flow f144 of GateOrStandDecisionItem from nullPart to towerSupervisor { doc /* @S475 */ }
        flow f145 of RoleSpecificAlertSummariesItem from alertDistributionHub to operationalGroup { doc /* @S505 */ }
        flow f146 of TimingConstraintAndDecisionOwnershipInformationItem from alertDistributionHub to operationalGroup { doc /* @S505 */ }
        flow f147 of DiversionRationaleItem from digitalBriefingRoom to collaborativeDecisionLog { doc /* @S506 */ }
        flow f148 of PriorityClassificationItem from digitalBriefingRoom to collaborativeDecisionLog { doc /* @S506 */ }
        flow f149 of ResourceCommitmentItem from digitalBriefingRoom to collaborativeDecisionLog { doc /* @S506 */ }
        flow f150 of AgreedRecoveryTargetItem from digitalBriefingRoom to collaborativeDecisionLog { doc /* @S506 */ }
        flow f151 of NotificationsItem from alertDistributionHub to subscribedOperationalRole { doc /* @S529 */ }
        flow f152 of ProposedMitigationItem from accountableOperationalRole to collaborativeDecisionLog { doc /* @S531 */ }
        flow f153 of PlannedRemoteStandOperatingPostureItem from airportDutyManager to airportCDMPortal { doc /* @S544 */ }
        flow f154 of RemoteStandStatusItem from commonSituationDisplay to airlineRoles { doc /* @S560 */ }
        flow f155 of RemoteStandStatusItem from commonSituationDisplay to rampRoles { doc /* @S560 */ }
        flow f156 of RemoteStandStatusItem from commonSituationDisplay to towerRoles { doc /* @S560 */ }
        flow f157 of RemoteStandStatusItem from commonSituationDisplay to airportRoles { doc /* @S560 */ }
        flow f158 of BorderAndCustomsStatusItem from airportCDMPortal to authorizedOperationalUsers { doc /* @S572 */ }
        flow f159 of TimeBucketedCountsItem from sectorLoadMonitor to regionalFlowPlatform { doc /* @S592 */ }
        flow f160 of PredictedOccupancyItem from sectorLoadMonitor to regionalFlowPlatform { doc /* @S592 */ }
        flow f161 of OverloadFlagsItem from sectorLoadMonitor to regionalFlowPlatform { doc /* @S592 */ }
        flow f165 of ScheduledMovementsItem from flightDataExchange to regionalFlowPlatform { doc /* @S593 */ }
        flow f166 of PredictedReadinessItem from demandPredictionService to regionalFlowPlatform { doc /* @S593 */ }
        flow f167 of DelayItem from slotAllocationEngine to operators { doc /* @S603 */ }
        flow f168 of NotificationsItem from alertDistributionHub to regionalFlowManager { doc /* @S614 */ }
        flow f169 of NotificationsItem from alertDistributionHub to towerSupervisor { doc /* @S614 */ }
        flow f170 of NotificationsItem from alertDistributionHub to rampControlLead { doc /* @S614 */ }
        flow f171 of NotificationsItem from alertDistributionHub to slotCoordinator { doc /* @S614 */ }
        flow f172 of NotificationsItem from alertDistributionHub to networkOperationsLiaison { doc /* @S614 */ }
        flow f173 of CrewLegalityImpactsItem from commonSituationDisplay to authorizedUsers { doc /* @S627 */ }
        flow f174 of ApprovedOperationalResultItem from flightDataExchange to downstreamServices { doc /* @S638 */ }
        flow f175 of ExceptionItem from slotAllocationEngine to slotCoordinator { doc /* @S671 */ }
        flow f176 of TugAvailabilityItem from rampMovementBoard to rampControlLead { doc /* @S677 */ }
        flow f177 of CalculatedTakeoffTimeItem from commonSituationDisplay to operationalUsers { doc /* @S685 */ }
        flow f178 of TargetOffBlockTimeItem from commonSituationDisplay to operationalUsers { doc /* @S685 */ }
        flow f179 of OperationalStatusItem from towerSequenceManager to towerSupervisor { doc /* @S693 */ }
        flow f180 of AerodromeInfrastructureEventsItem from airportCDMPortal to authorizedAirportAirlineAndFlowManagementUsers { doc /* @S695 */ }
        flow f181 of RevisedInputsItem from departureMeteringService to slotAllocationEngine { doc /* @S699 */ }
        flow f182 of OperationalStatusItem from towerSequenceManager to rampMovementBoard { doc /* @S703 */ }
        flow f183 of AffectedResourceItem from commonSituationDisplay to operationalStaff { doc /* @S704 */ }
        flow f184 of StartTimeItem from commonSituationDisplay to operationalStaff { doc /* @S704 */ }
        flow f185 of ReviewTimeItem from commonSituationDisplay to operationalStaff { doc /* @S704 */ }
        flow f186 of CurrentDecisionStatusItem from commonSituationDisplay to operationalStaff { doc /* @S704 */ }
        flow f187 of MandatoryOperationalAdvisoriesItem from alertDistributionHub to participants { doc /* @S731 */ }
        flow f188 of CurrentOperatingBasisItem from airportDutyManager to digitalBriefingRoom { doc /* @S734 */ }
        flow f189 of CalculatedTakeoffTimeItem from slotCoordinator to flight { doc /* @S744 */ }
        flow f190 of PassengerDisruptionCuesItem from commonSituationDisplay to participants { doc /* @S758 */ }
        flow f191 of RationaleItem from collaborativeDecisionLog to performanceAnalyticsWarehouse { doc /* @S760 */ }
        flow f192 of TimeItem from timeSynchronizationService to auditRecords { doc /* @S778 */ }
        flow f193 of PossibleCredentialCompromiseItem from securityMonitoring to systemSupportEngineer { doc /* @S780 */ }
        flow f194 of PossibleCredentialCompromiseItem from securityMonitoring to dataGovernanceSteward { doc /* @S780 */ }
        flow f195 of InappropriatePrivilegeUseItem from securityMonitoring to systemSupportEngineer { doc /* @S780 */ }
        flow f196 of InappropriatePrivilegeUseItem from securityMonitoring to dataGovernanceSteward { doc /* @S780 */ }
        flow f197 of SlotComplianceEventsItem from regionalFlowPlatform to auditEventLedger { doc /* @S789 */ }
        flow f198 of AssignmentsItem from dataGovernance to airportCDMPortal { doc /* @S812 */ }
        flow f199 of CommonTimeBasisItem from timeSynchronizationService to regionalFlowPlatform { doc /* @S824 */ }
        flow f200 of DispositionItem from dataGovernanceSteward to auditEventLedger { doc /* @S833 */ }
        flow f201 of ChangesInStandOccupancySurfaceCongestionRecoveryDurationAndPassengerFacingDisruptionIndicatorsItem from benefitSummaries to airportDutyManager { doc /* @S860 */ }
        flow f202 of RegionalBenefitsItem from postOperationsReport to decisionMakers { doc /* @S862 */ }
        flow f203 of OperationalTradeOffsItem from postOperationsReport to decisionMakers { doc /* @S862 */ }
        flow f204 of EvidenceItem from performanceAnalyticsWarehouse to postExerciseReviews { doc /* @S887 */ }
        flow f205 of EvidenceItem from auditEventLedger to postExerciseReviews { doc /* @S887 */ }
        flow f206 of OperationalDecisionsItem from localUsers to airportCDMPortal { doc /* @S907 */ }
        flow f207 of TechnicalStatusItem from systemSupportEngineer to operationalSupervisors { doc /* @S918 */ }
        flow f208 of KnownWorkaroundsItem from systemSupportEngineer to operationalSupervisors { doc /* @S918 */ }
        flow f209 of DataIntegrityConcernsItem from systemSupportEngineer to operationalSupervisors { doc /* @S918 */ }
        flow f210 of RecoveryOptionsItem from systemSupportEngineer to operationalSupervisors { doc /* @S918 */ }
        flow f211 of TargetUpdatesItem from nullPart to nullPart { doc /* @S922 */ }
        flow f212 of TransitionToContingencyFallbackStateItem from regionalFlowManager to nullPart { doc /* @S926 */ }
        flow f213 of NormalTechnicalServiceCanResumeItem from systemSupportEngineer to nullPart { doc /* @S927 */ }
        flow f214 of UseOfContingencyProceduresForNontechnicalReasonsItem from operationalSupervisors to nullPart { doc /* @S934 */ }
        flow f215 of MainOperationalInputsItem from airportCDMPortal to advancedTurnaroundPrediction { doc /* @S947 */ }
        flow f216 of MainOperationalInputsItem from airlineInterfaceAdapter to advancedTurnaroundPrediction { doc /* @S947 */ }
        flow f217 of MainOperationalInputsItem from handlingResourcePlanner to advancedTurnaroundPrediction { doc /* @S947 */ }
        flow f218 of MainOperationalInputsItem from rampMovementBoard to advancedTurnaroundPrediction { doc /* @S947 */ }
    }
    requirement def R0 { doc /* require close coordination with the Military Airspace Liaison @S006 */ subject s : SectorLoadingConstraints; }
    requirement def R1 { doc /* require a common basis for decisions rather than separate local views of the same operational picture @S011 */ subject s : AirlineOperationsCoordinator; }
    requirement def R2 { doc /* require a common basis for decisions rather than separate local views of the same operational picture @S011 */ subject s : AircraftOperatorRepresentative; }
    requirement def R3 { doc /* require a common basis for decisions rather than separate local views of the same operational picture @S011 */ subject s : AirportDutyManager; }
    requirement def R4 { doc /* require a common basis for decisions rather than separate local views of the same operational picture @S011 */ subject s : TowerSupervisor; }
    requirement def R5 { doc /* require a common basis for decisions rather than separate local views of the same operational picture @S011 */ subject s : RampControlLead; }
    requirement def R6 { doc /* require a common basis for decisions rather than separate local views of the same operational picture @S011 */ subject s : SlotCoordinator; }
    requirement def R7 { doc /* During Adverse Weather Mode or Capacity Reduction State, the system must support rapid development of a Tactical Regulation Proposal and consistent communication of the resulting Ground Delay Program when one is required. @S022 */ subject s : MeridianRegionalCapability; }
    requirement def R8 { doc /* During Recovery Phase, the system must help stakeholders restore scheduled flow while monitoring Target Off Block Time, Calculated Takeoff Time, and Slot Compliance State performance. @S023 */ subject s : MeridianRegionalCapability; }
    requirement def R9 { doc /* Interfaces to external systems are included in the boundary only to the extent required to validate identity, receive authorized operational data, publish approved coordination information, and maintain auditable records. @S037 */ subject s : InterfacesToExternalSystems; }
    requirement def R10 { doc /* Participation in the regional system requires each stakeholder organization to assign accountable representatives, maintain current contact details, follow agreed data use rules, and support post-operational review of decisions made through the Regional Flow Platform. @S048 */ subject s : StakeholderOrganization; }
    requirement def R11 { doc /* conditional availability that must be treated as uncertain @S059 */ subject s : ConditionalAvailability; }
    requirement def R12 { doc /* changes must be entered through controlled Regional Flow Platform functions @S073 */ subject s : Changes; }
    requirement def R13 { doc /* whether demand smoothing is required before tactical execution @S079 */ subject s : DemandSmoothing; }
    requirement def R14 { doc /* The Departure Metering Service and Arrival Regulation Console are used only under the authority of the accountable flow roles @S095 */ subject s : DepartureMeteringService; }
    requirement def R15 { doc /* The Departure Metering Service and Arrival Regulation Console are used only under the authority of the accountable flow roles @S095 */ subject s : ArrivalRegulationConsole; }
    requirement def R16 { doc /* their outputs must remain visible on the Common Situation Display @S095 */ subject s : Outputs; }
    requirement def R17 { doc /* Escalation to the Emergency Response Coordinator is required when a safety event, security event, or emergency response activity may affect airport acceptance, surface movement, or airspace availability. @S096 */ subject s : Escalation; }
    requirement def R18 { doc /* During Adverse Weather Mode or a Capacity Reduction State, airline operations centres are expected to submit conservative intents that distinguish firm operating plans from speculative recovery options. @S146 */ subject s : AirlineOperationsCentres; }
    requirement def R19 { doc /* The Airline Operations Coordinator is responsible for keeping the Flight Intent Message status, Target Off Block Time, passenger readiness indicator, and aircraft operational constraint notes current for each represented flight. @S157 */ subject s : AirlineOperationsCoordinator; }
    requirement def R20 { doc /* The Ground Handling Dispatcher is responsible for updating servicing completion, baggage readiness, staffing limitation, and equipment availability milestones as soon as the handling status changes. @S158 */ subject s : GroundHandlingDispatcher; }
    requirement def R21 { doc /* The Ramp Control Lead is responsible for maintaining stand release readiness, apron movement conflicts, tug availability, and local pushback sequencing inputs in the portal. @S159 */ subject s : RampControlLead; }
    requirement def R22 { doc /* The Tower Supervisor is responsible for reviewing runway configuration assumptions, departure sequence feasibility, and tactical tower constraints before those values are used for metering decisions. @S160 */ subject s : TowerSupervisor; }
    requirement def R23 { doc /* Cedarbell shall expose the current regional demand and constraint context to the shared workspace at each publication cycle without requiring manual re-entry. @S164 */ subject s : RegionalFlowPlatform; }
    requirement def R24 { doc /* When a milestone becomes stale, the Airport CDM Portal shall highlight the affected flight and notify the role accountable for the next update through the Alert Distribution Hub. @S166 */ subject s : AirportCDMPortal; }
    requirement def R25 { doc /* Each airport participant shall update a material change within two minutes of becoming aware of it during Normal Operations and within one minute during Adverse Weather Mode or Capacity Reduction State. @S167 */ subject s : AirportParticipant; }
    requirement def R26 { doc /* If the exact value is not yet known, the accountable participant shall enter a provisional value with an uncertainty flag rather than leaving the milestone unchanged. @S168 */ subject s : AccountableParticipant; }
    requirement def R27 { doc /* During Contingency Fallback State, the Airport CDM Portal shall preserve the last synchronized milestone set and clearly mark any updates entered under degraded operating procedures. @S172 */ subject s : AirportCDMPortal; }
    requirement def R28 { doc /* a local condition should be reflected in the Airport Capacity Plan @S178 */ subject s : LocalCondition; }
    requirement def R29 { doc /* Orchard shall issue time-stamped weather condition updates for use in tower and airport duty coordination. @S182 */ subject s : WeatherIngestGateway; }
    requirement def R30 { doc /* The Time Synchronization Service shall keep tower, duty desk, surveillance, and portal event times aligned so that later review can reconstruct the sequence of events. @S187 */ subject s : TimeSynchronizationService; }
    requirement def R31 { doc /* The Ramp Control Lead shall not release a pushback until the Tower Supervisor has confirmed that the movement can be integrated with the active ground route and runway plan. @S202 */ subject s : RampControlLead; }
    requirement def R32 { doc /* Ramp Control Lead sends the Stand Tow Request Form when a parked aircraft must be repositioned to release a stand, remove an apron blockage, or support a confirmed operating plan. @S208 */ subject s : ParkedAircraft; }
    requirement def R33 { doc /* Airline Operations Coordinator participation is required when a resequence would materially affect passenger boarding, connection protection, or aircraft rotation plans. @S214 */ subject s : AirlineOperationsCoordinator; }
    requirement def R34 { doc /* Marlinstone shall refresh stand demand forecasts when the Ramp Movement Board records a material change in planned off-block timing. @S216 */ subject s : DemandPredictionService; }
    requirement def R35 { doc /* The engine shall not improve one operator's position by imposing an excessive delay on another operator unless the rule basis is visible and logged. @S234 */ subject s : SlotAllocationEngine; }
    requirement def R36 { doc /* Saffron shall confirm any operator-requested Target Off Block Time revision in the Airport CDM Portal before the freeze horizon expires. @S260 */ subject s : AirlineOperationsCoordinator; }
    requirement def R37 { doc /* runway balancing is required @S280 */ subject s : RunwayBalancing; }
    requirement def R38 { doc /* Foxglove shall publish tower readiness changes to authenticated airline and handling users within the configured refresh interval. @S293 */ subject s : AirportCDMPortal; }
    requirement def R39 { doc /* Brindle must confirm that any revised off-block sequence remains compatible with the Departure Metering Service before the change is released to the airport community. @S313 */ subject s : TowerSupervisor; }
    requirement def R40 { doc /* The Aircraft Operator Representative is expected to declare whether the operator can accept a later off-block time without causing crew, connection, or aircraft rotation impacts. @S316 */ subject s : AircraftOperatorRepresentative; }
    requirement def R41 { doc /* Ironleaf must refresh affected departure sequence advisories when a restriction changes the usable departure routes or expected release spacing. @S334 */ subject s : TowerSequenceManager; }
    requirement def R42 { doc /* Blueharbor shall adjust allocated departure times when metering rules require additional stand absorption to preserve the planned runway sequence. @S355 */ subject s : SlotAllocationEngine; }
    requirement def R43 { doc /* the metering horizon should be extended so that delay is absorbed before pushback rather than near the runway @S368 */ subject s : MeteringHorizon; }
    requirement def R44 { doc /* Quartzline must coordinate every pad release with the Tower Supervisor before the aircraft leaves the treated area. @S387 */ subject s : RampControlLead; }
    requirement def R45 { doc /* inbound demand will exceed the Airport Acceptance Rate within the planning horizon @S395 */ subject s : InboundDemand; }
    requirement def R46 { doc /* Skylark must refresh the apron movement layer within five seconds of each validated surface event. @S427 */ subject s : RampMovementBoard; }
    requirement def R47 { doc /* the affected flight should keep its Target Off Block Time, request a new value, or accept a later Calculated Takeoff Time @S451 */ subject s : AffectedFlight; }
    requirement def R48 { doc /* Lantern must distribute surface equipment and apron congestion advisories to subscribed operational roles within the latency target defined in the Business Rules Registry. @S461 */ subject s : AlertDistributionHub; }
    requirement def R49 { doc /* the tactical plan should retain normal sequencing, shift to local metering, or support a Tactical Regulation Proposal @S463 */ subject s : TacticalPlan; }
    requirement def R50 { doc /* groups that require assisted transfer @S478 */ subject s : Groups; }
    requirement def R51 { doc /* Nightjar shall suppress handler-exception annotations for arriving flights unless the exception changes the Airport Acceptance Rate or a regulated arrival sequence. @S535 */ subject s : ArrivalRegulationConsole; }
    requirement def R52 { doc /* an aircraft must wait clear of the terminal pier @S542 */ subject s : Aircraft; }
    requirement def R53 { doc /* whether an arrival regulation should be adjusted @S573 */ subject s : ArrivalRegulation; }
    requirement def R54 { doc /* whether delay absorption should remain local to the airport @S573 */ subject s : DelayAbsorption; }
    requirement def R55 { doc /* The Time Synchronization Service is required because customs status events and apron sensor events must align with Calculated Takeoff Time and Target Off Block Time decisions. @S585 */ subject s : TimeSynchronizationService; }
    requirement def R56 { doc /* customs status events and apron sensor events must align with Calculated Takeoff Time and Target Off Block Time decisions @S585 */ subject s : CustomsStatusEvents; }
    requirement def R57 { doc /* customs status events and apron sensor events must align with Calculated Takeoff Time and Target Off Block Time decisions @S585 */ subject s : ApronSensorEvents; }
    requirement def R58 { doc /* confirm whether a departure fix constraint should be represented as an airport departure measure @S598 */ subject s : DepartureFixConstraint; }
    requirement def R59 { doc /* sustained saturation requiring a Tactical Regulation Proposal @S600 */ subject s : SustainedSaturation; }
    requirement def R60 { doc /* Slot Allocation Engine uses these constraints when evaluating whether a Calculated Takeoff Time should be offered, retained, exchanged, or released. @S625 */ subject s : CalculatedTakeoffTime; }
    requirement def R61 { doc /* downstream services that need to update schedules, metering, or airport resource plans @S638 */ subject s : DownstreamServices; }
    requirement def R62 { doc /* visual confirmation remains required where sensor coverage is obstructed by parked aircraft or ground equipment @S645 */ subject s : VisualConfirmation; }
    requirement def R63 { doc /* scarce capacity must be protected for the published tactical plan @S675 */ subject s : ScarceCapacity; }
    requirement def R64 { doc /* which infrastructure events require approval @S706 */ subject s : AerodromeInfrastructureEvents; }
    requirement def R65 { doc /* will approve restoration to Normal Operations or Recovery Phase @S717 */ subject s : Authority; }
    requirement def R66 { doc /* must not automatically overwrite issued times @S728 */ subject s : DepartureMeteringService; }
    requirement def R67 { doc /* Transition out of the Contingency Fallback State requires stable service performance, verified data consistency, successful user access, and agreement from the operational leads affected by the outage. @S735 */ subject s : System; }
    requirement def R68 { doc /* Each named operational user shall authenticate with an individually assigned identity before accessing the Airport CDM Portal, Digital Briefing Room, or any operational console. @S764 */ subject s : NamedOperationalUser; }
    requirement def R69 { doc /* Shared operational accounts are not permitted for routine use because they prevent reliable attribution during time-critical flow management decisions. @S765 */ subject s : SharedOperationalAccounts; }
    requirement def R70 { doc /* Role profiles shall grant the minimum access needed to view, propose, approve, or administer operational data within the Regional Flow Platform. @S767 */ subject s : RoleProfiles; }
    requirement def R71 { doc /* operational approval privileges shall remain separated from technical administration privileges @S772 */ subject s : OperationalApprovalPrivileges; }
    requirement def R72 { doc /* Operational segregation shall prevent a single user from creating, approving, and technically concealing a material change to a Ground Delay Program, Airport Acceptance Rate, or Tactical Regulation Proposal. @S774 */ subject s : OperationalSegregation; }
    requirement def R73 { doc /* Where dual control is required @S775 */ subject s : DualControl; }
    requirement def R74 { doc /* Where dual control is required, the Regional Flow Platform shall record the initiating user, the approving user, the affected operational object, and the effective time of the decision. @S775 */ subject s : RegionalFlowPlatform; }
    requirement def R75 { doc /* Access to the Performance Analytics Warehouse shall be restricted to authorized analytical roles and shall not allow retrospective alteration of operational records held in the Audit Event Ledger. @S776 */ subject s : PerformanceAnalyticsWarehouse; }
    requirement def R76 { doc /* The Audit Event Ledger shall capture successful and failed authentication attempts, role changes, privilege elevations, operational approvals, configuration changes, data exports, and emergency access activations. @S777 */ subject s : AuditEventLedger; }
    requirement def R77 { doc /* All audit records shall use time derived from the Time Synchronization Service so that investigations can reconstruct event order across the Airport CDM Portal, Slot Allocation Engine, and Alert Distribution Hub. @S778 */ subject s : AuditRecords; }
    requirement def R78 { doc /* Audit records shall be protected against ordinary user modification and retained for a period agreed by the airport operator, regional authority, and participating aircraft operators. @S779 */ subject s : AuditRecords; }
    requirement def R79 { doc /* Security monitoring shall alert the System Support Engineer and Data Governance Steward when unusual access patterns indicate possible credential compromise or inappropriate privilege use. @S780 */ subject s : SecurityMonitoring; }
    requirement def R80 { doc /* The Identity Access Service shall support rapid suspension of accounts when a user changes role, leaves an organization, or becomes subject to an operational integrity concern. @S781 */ subject s : IdentityAccessService; }
    requirement def R81 { doc /* Temporary access shall have a defined sponsor, purpose, role scope, and expiry time, and shall be reviewed after the operational need has ended. @S782 */ subject s : TemporaryAccess; }
    requirement def R82 { doc /* Silverpine shall accept emergency access activations only after the Identity Access Service records the authorizing incident reference and expiry time. @S783 */ subject s : ContingencyOperationsConsole; }
    requirement def R83 { doc /* Use of emergency access shall generate prominent audit events and shall require post-event review by the Data Governance Steward and the responsible operational authority. @S785 */ subject s : UseOfEmergencyAccess; }
    requirement def R84 { doc /* During Contingency Fallback State, access control shall continue to enforce role separation even when some integrations are unavailable and manual coordination becomes necessary. @S786 */ subject s : AccessControl; }
    requirement def R85 { doc /* When normal connectivity is restored, the Regional Flow Platform shall reconcile contingency actions with the Collaborative Decision Log so that accountability is preserved across the full incident timeline. @S787 */ subject s : RegionalFlowPlatform; }
    requirement def R86 { doc /* After connectivity is restored, audit processing shall treat reconciled contingency actions as part of the same operational record as actions taken during Normal Operations. @S788 */ subject s : AuditProcessing; }
    requirement def R87 { doc /* The Regional Flow Platform shall record slot compliance events in the Audit Event Ledger using the operating date, flight identifier, airport, runway direction, and applicable regulation reference. @S789 */ subject s : RegionalFlowPlatform; }
    requirement def R88 { doc /* Each compliance assessment shall compare the Calculated Takeoff Time, the Target Off Block Time, actual off-block time, and actual takeoff time against the tolerance defined in the Business Rules Registry. @S790 */ subject s : ComplianceAssessment; }
    requirement def R89 { doc /* The Slot Compliance State shall indicate whether a flight was compliant, early, late, exempted, substituted, cancelled, or pending review at the end of the traffic period. @S791 */ subject s : SlotComplianceState; }
    requirement def R90 { doc /* The Audit Event Ledger shall preserve the time source applied by the Time Synchronization Service so that later review can distinguish operational delay from data latency. @S792 */ subject s : AuditEventLedger; }
    requirement def R91 { doc /* User decisions entered through the Airport CDM Portal shall be linked to the authenticated role provided by the Identity Access Service. @S793 */ subject s : UserDecisions; }
    requirement def R92 { doc /* The Collaborative Decision Log shall retain the stated reason, decision time, affected flight, and visible operational context for each material change to a slot or sequence. @S794 */ subject s : CollaborativeDecisionLog; }
    requirement def R93 { doc /* Substitution records shall show the original flight, replacement flight, assigned Calculated Takeoff Time, acceptance status, and any subsequent cancellation or reversion. @S796 */ subject s : SubstitutionRecords; }
    requirement def R94 { doc /* When an Aircraft Operator Representative proposes a substitution, the audit trail shall capture whether the change preserved the constraints of the active Ground Delay Program. @S797 */ subject s : AuditTrail; }
    requirement def R95 { doc /* The Slot Coordinator shall review substitution activity after operations to confirm that priority rules were applied consistently across participating operators. @S798 */ subject s : SlotCoordinator; }
    requirement def R96 { doc /* Late operational changes shall be distinguished from planned updates by comparing the change timestamp with the freeze horizon held in the Business Rules Registry. @S799 */ subject s : LateOperationalChanges; }
    requirement def R97 { doc /* Changes made inside the freeze horizon shall require a reason code and shall be visible to the Regional Flow Manager during post-operations review. @S800 */ subject s : Changes; }
    requirement def R98 { doc /* The Tower Sequence Manager and Ramp Movement Board shall provide actual movement milestones that support independent verification of slot performance. @S801 */ subject s : TowerSequenceManager; }
    requirement def R99 { doc /* The Tower Sequence Manager and Ramp Movement Board shall provide actual movement milestones that support independent verification of slot performance. @S801 */ subject s : RampMovementBoard; }
    requirement def R100 { doc /* Surface movement evidence from the Surface Surveillance Adapter shall be retained long enough to support dispute resolution and regulatory audit requests. @S802 */ subject s : SurfaceMovementEvidence; }
    requirement def R101 { doc /* Capacity changes made through the Capacity Assessment Module shall be correlated with the active Airport Capacity Plan and Airport Acceptance Rate used at the time of allocation. @S803 */ subject s : CapacityChanges; }
    requirement def R102 { doc /* The Performance Analytics Warehouse shall aggregate compliance outcomes by carrier, route group, regulation, airport operating configuration, and time band. @S804 */ subject s : PerformanceAnalyticsWarehouse; }
    requirement def R103 { doc /* Aggregated metrics shall support review of systemic lateness without exposing commercially sensitive detail beyond authorized roles. @S805 */ subject s : AggregatedMetrics; }
    requirement def R104 { doc /* The Data Governance Steward shall verify that audit fields required for slot performance reporting remain complete, immutable, and traceable to approved data definitions. @S806 */ subject s : DataGovernanceSteward; }
    requirement def R105 { doc /* The System Support Engineer shall investigate technical gaps when audit sequences show missing events, duplicate updates, or inconsistent timestamps. @S807 */ subject s : SystemSupportEngineer; }
    requirement def R106 { doc /* The Regional Flow Manager shall use the Post Operations Report to identify whether noncompliance resulted from operator choice, airport constraint, airspace constraint, weather impact, or system issue. @S808 */ subject s : RegionalFlowManager; }
    requirement def R107 { doc /* The Airport Duty Manager shall review late airport-driven changes that affected multiple flights and shall record whether the operational justification was valid. @S809 */ subject s : AirportDutyManager; }
    requirement def R108 { doc /* Findings from the review shall feed adjustments to tolerance values, reason code definitions, and training material, subject to change control. @S810 */ subject s : Findings; }
    requirement def R109 { doc /* All audit outputs shall be retained according to the approved records schedule and shall remain searchable for compliance investigations, performance meetings, and lessons-learned activity. @S811 */ subject s : AuditOutputs; }
    requirement def R110 { doc /* Data governance for the Regional Flow Platform shall assign accountable owners to each operational data domain and shall make those assignments visible in the Airport CDM Portal. @S812 */ subject s : DataGovernance; }
    requirement def R111 { doc /* The Data Governance Steward shall maintain the data ownership register and shall coordinate updates through the Business Rules Registry. @S813 */ subject s : DataGovernanceSteward; }
    requirement def R112 { doc /* The Regional Flow Manager shall own flow management policy data, including Ground Delay Program parameters and Tactical Regulation Proposal status values. @S814 */ subject s : RegionalFlowManager; }
    requirement def R113 { doc /* The Slot Coordinator shall own slot allocation reference data, including Calculated Takeoff Time tolerances and Slot Compliance State definitions. @S815 */ subject s : SlotCoordinator; }
    requirement def R114 { doc /* The Airport Duty Manager shall own airport capacity declarations, including Airport Capacity Plan records and Airport Acceptance Rate values. @S816 */ subject s : AirportDutyManager; }
    requirement def R115 { doc /* The Tower Supervisor shall own tower sequence status data maintained for the Tower Sequence Manager. @S817 */ subject s : TowerSupervisor; }
    requirement def R116 { doc /* The Ramp Control Lead shall own ramp movement status data maintained for the Ramp Movement Board. @S818 */ subject s : RampControlLead; }
    requirement def R117 { doc /* The Meteorology Briefing Officer shall own operational weather classification inputs accepted by the Weather Ingest Gateway. @S819 */ subject s : MeteorologyBriefingOfficer; }
    requirement def R118 { doc /* The Airline Operations Coordinator shall be accountable for airline-supplied schedule intent, readiness status, and Target Off Block Time updates submitted through approved interfaces. @S820 */ subject s : AirlineOperationsCoordinator; }
    requirement def R119 { doc /* Each owned data element shall have a defined business meaning, allowed value range, update authority, retention class, and escalation contact. @S821 */ subject s : OwnedDataElement; }
    requirement def R120 { doc /* Freshness indicators shall be displayed on the Common Situation Display wherever stale data could affect sequencing, metering, regulation, or resource allocation decisions. @S822 */ subject s : FreshnessIndicators; }
    requirement def R121 { doc /* The freshness indicator shall include the time of last accepted update, the maximum permitted age, and a visual state that distinguishes current, aging, stale, and unavailable data. @S823 */ subject s : FreshnessIndicators; }
    requirement def R122 { doc /* The Time Synchronization Service shall provide the common time basis used for freshness calculations across the Regional Flow Platform. @S824 */ subject s : TimeSynchronizationService; }
    requirement def R123 { doc /* The Demand Prediction Service, Capacity Assessment Module, Slot Allocation Engine, and Departure Metering Service shall reject data that lacks a trusted timestamp. @S825 */ subject s : DemandPredictionService; }
    requirement def R124 { doc /* The Demand Prediction Service, Capacity Assessment Module, Slot Allocation Engine, and Departure Metering Service shall reject data that lacks a trusted timestamp. @S825 */ subject s : CapacityAssessmentModule; }
    requirement def R125 { doc /* The Demand Prediction Service, Capacity Assessment Module, Slot Allocation Engine, and Departure Metering Service shall reject data that lacks a trusted timestamp. @S825 */ subject s : SlotAllocationEngine; }
    requirement def R126 { doc /* The Demand Prediction Service, Capacity Assessment Module, Slot Allocation Engine, and Departure Metering Service shall reject data that lacks a trusted timestamp. @S825 */ subject s : DepartureMeteringService; }
    requirement def R127 { doc /* Validation rules shall include schema checks, mandatory field checks, code set checks, temporal sequence checks, and operational plausibility checks. @S826 */ subject s : ValidationRules; }
    requirement def R128 { doc /* The Flight Data Exchange shall validate Flight Intent Message content before the data is made available for operational use. @S827 */ subject s : FlightDataExchange; }
    requirement def R129 { doc /* The Surface Surveillance Adapter shall apply position quality checks and shall mark uncertain observations before they are used by surface decision functions. @S828 */ subject s : SurfaceSurveillanceAdapter; }
    requirement def R130 { doc /* The Airline Interface Adapter shall apply carrier-specific format checks while preserving the common operational meaning required by the Regional Flow Platform. @S829 */ subject s : AirlineInterfaceAdapter; }
    requirement def R131 { doc /* The Handling Resource Planner shall validate resource quantities, task timing, and allocation identifiers against active operational reference data. @S830 */ subject s : HandlingResourcePlanner; }
    requirement def R132 { doc /* The Business Rules Registry shall hold the current validation thresholds, allowable reason codes, and exception rules approved for Normal Operations, Adverse Weather Mode, Capacity Reduction State, Recovery Phase, and Contingency Fallback State. @S831 */ subject s : BusinessRulesRegistry; }
    requirement def R133 { doc /* The Data Governance Steward shall coordinate discrepancy resolution with the responsible operational owner and shall record the disposition in the Audit Event Ledger. @S833 */ subject s : DataGovernanceSteward; }
    requirement def R134 { doc /* Urgent discrepancies that could change a metering, arrival regulation, or slot allocation decision shall be raised through the Alert Distribution Hub and reviewed in the Digital Briefing Room. @S834 */ subject s : UrgentDiscrepancies; }
    requirement def R135 { doc /* The System Support Engineer shall investigate technical causes of missing, delayed, duplicated, or transformed records and shall provide evidence needed for stewardship decisions. @S835 */ subject s : SystemSupportEngineer; }
    requirement def R136 { doc /* The Performance Analytics Warehouse shall retain data quality measures, including validation failure rates, freshness breaches, manual corrections, and recurring ownership conflicts. @S836 */ subject s : PerformanceAnalyticsWarehouse; }
    requirement def R137 { doc /* Stewardship reviews shall use those measures to update training, adjust validation rules, and improve the reliability of information used in operational decision making. @S837 */ subject s : StewardshipReviews; }
    requirement def R138 { doc /* Performance measurement for the Meridian Regional Air Traffic Flow Management and Airport Collaborative Decision-Making System shall convert operational events into repeatable indicators that can be reviewed after each operating day. @S838 */ subject s : PerformanceMeasurement; }
    requirement def R139 { doc /* The Performance Analytics Warehouse shall calculate delay absorption as the portion of expected airborne or terminal-area delay that is converted into controlled ground delay before departure. @S839 */ subject s : PerformanceAnalyticsWarehouse; }
    requirement def R140 { doc /* Delay absorption shall be measured by comparing the unconstrained demand predicted by the Demand Prediction Service with the regulated demand produced by the Slot Allocation Engine and the realized movement times captured through the Flight Data Exchange. @S840 */ subject s : DelayAbsorption; }
    requirement def R141 { doc /* The principal delay absorption indicator shall report minutes absorbed at origin, minutes remaining in the arrival stream, and minutes transferred to surface queues within the region. @S841 */ subject s : PrincipalDelayAbsorptionIndicator; }
    requirement def R142 { doc /* The Regional Flow Manager shall use this indicator to verify that a Ground Delay Program reduced airborne holding without creating excessive departure congestion at constrained airports. @S842 */ subject s : RegionalFlowManager; }
    requirement def R143 { doc /* Queue length performance shall be measured for runway departure queues, arrival metering queues, apron movement queues, and regulation waiting lists. @S843 */ subject s : QueueLengthPerformance; }
    requirement def R144 { doc /* The Tower Sequence Manager shall provide runway sequence counts, while the Ramp Movement Board shall provide surface queue counts based on movement status and surveillance confirmation. @S844 */ subject s : TowerSequenceManager; }
    requirement def R145 { doc /* The Tower Sequence Manager shall provide runway sequence counts, while the Ramp Movement Board shall provide surface queue counts based on movement status and surveillance confirmation. @S844 */ subject s : RampMovementBoard; }
    requirement def R146 { doc /* The North Runway Meter, South Runway Meter, East Apron Sensor, and West Apron Sensor shall support independent checks of queue length where surveillance coverage is available. @S845 */ subject s : NorthRunwayMeter; }
    requirement def R147 { doc /* The North Runway Meter, South Runway Meter, East Apron Sensor, and West Apron Sensor shall support independent checks of queue length where surveillance coverage is available. @S845 */ subject s : SouthRunwayMeter; }
    requirement def R148 { doc /* The North Runway Meter, South Runway Meter, East Apron Sensor, and West Apron Sensor shall support independent checks of queue length where surveillance coverage is available. @S845 */ subject s : EastApronSensor; }
    requirement def R149 { doc /* The North Runway Meter, South Runway Meter, East Apron Sensor, and West Apron Sensor shall support independent checks of queue length where surveillance coverage is available. @S845 */ subject s : WestApronSensor; }
    requirement def R150 { doc /* Queue metrics shall include maximum queue length, average queue length, time above threshold, and recovery time after a constraint is lifted. @S846 */ subject s : QueueMetrics; }
    requirement def R151 { doc /* Slot adherence shall be measured as the difference between actual movement times and the assigned Calculated Takeoff Time or Target Off Block Time. @S847 */ subject s : SlotAdherence; }
    requirement def R152 { doc /* The Slot Coordinator shall review slot adherence by operator, airport, time band, and regulation identifier to detect recurring causes of noncompliance. @S848 */ subject s : SlotCoordinator; }
    requirement def R153 { doc /* A flight shall be counted within tolerance when the actual takeoff or off-block event occurs inside the operating window defined in the Business Rules Registry. @S849 */ subject s : Flight; }
    requirement def R154 { doc /* The Slot Compliance State shall be used to identify periods when adherence monitoring has operational priority over advisory optimization. @S850 */ subject s : SlotComplianceState; }
    requirement def R155 { doc /* Cancellation avoidance shall be estimated by comparing actual cancellations with a baseline scenario derived from demand, capacity, weather, and historical disruption outcomes. @S852 */ subject s : CancellationAvoidance; }
    requirement def R156 { doc /* The Capacity Assessment Module shall record the available Airport Acceptance Rate used in each baseline so that avoided cancellation estimates remain traceable. @S853 */ subject s : CapacityAssessmentModule; }
    requirement def R157 { doc /* The Airline Operations Coordinator and Aircraft Operator Representative shall be able to challenge cancellation avoidance results through the Collaborative Decision Log when local business decisions affected the outcome. @S854 */ subject s : AirlineOperationsCoordinator; }
    requirement def R158 { doc /* The Airline Operations Coordinator and Aircraft Operator Representative shall be able to challenge cancellation avoidance results through the Collaborative Decision Log when local business decisions affected the outcome. @S854 */ subject s : AircraftOperatorRepresentative; }
    requirement def R159 { doc /* Emissions reduction shall be estimated from reduced airborne holding, reduced taxi-out time, avoided engine running in queues, and smoother departure metering. @S855 */ subject s : EmissionsReduction; }
    requirement def R160 { doc /* The Performance Analytics Warehouse shall apply approved fuel burn and emissions factors by aircraft category, operating phase, and delay location. @S856 */ subject s : PerformanceAnalyticsWarehouse; }
    requirement def R161 { doc /* Emissions metrics shall distinguish between actual reductions and delay transfers that only move fuel burn from one phase of flight to another. @S857 */ subject s : EmissionsMetrics; }
    requirement def R162 { doc /* The Meteorology Briefing Officer shall support interpretation of emissions results by identifying periods when weather routing or convective avoidance dominated fuel performance. @S858 */ subject s : MeteorologyBriefingOfficer; }
    requirement def R163 { doc /* Stakeholder benefit tracking shall allocate measured outcomes to aircraft operators, airport operations, air navigation service functions, ground handling activities, and passengers where the source data supports that attribution. @S859 */ subject s : StakeholderBenefitTracking; }
    requirement def R164 { doc /* The Airport Duty Manager shall receive benefit summaries that show changes in stand occupancy, surface congestion, recovery duration, and passenger-facing disruption indicators. @S860 */ subject s : AirportDutyManager; }
    requirement def R165 { doc /* The Data Governance Steward shall ensure that published performance measures identify data sources, calculation versions, confidence limits, and known exclusions. @S861 */ subject s : DataGovernanceSteward; }
    requirement def R166 { doc /* The Post Operations Report shall present regional benefits alongside operational trade-offs so that decision makers can see whether delay, queue, slot, cancellation, and emissions objectives were balanced in practice. @S862 */ subject s : PostOperationsReport; }
    requirement def R167 { doc /* Training for the Meridian Regional Air Traffic Flow Management and Airport Collaborative Decision-Making System shall be role based and shall cover normal coordination, constrained operations, recovery actions, and degraded system use. @S863 */ subject s : TrainingForTheMeridianRegionalAirTrafficFlowManagementAndAirportCollaborativeDecisionMakingSystem; }
    requirement def R168 { doc /* The Regional Flow Manager shall receive advanced instruction on interpreting demand and capacity information, leading collaborative decisions, and authorizing operational measures in the Regional Flow Platform. @S864 */ subject s : RegionalFlowManager; }
    requirement def R169 { doc /* Air traffic controllers shall be trained to understand how flow measures, sequencing changes, and calculated times affect sector workload, runway demand, and controller tactical flexibility. @S865 */ subject s : AirTrafficControllers; }
    requirement def R170 { doc /* The Tower Supervisor shall receive practical training on the Tower Sequence Manager, Departure Metering Service, Arrival Regulation Console, North Runway Meter, and South Runway Meter. @S866 */ subject s : TowerSupervisor; }
    requirement def R171 { doc /* Ramp personnel shall be trained under the direction of the Ramp Control Lead to use the Ramp Movement Board without substituting system indications for required visual checks, radio coordination, and local safety procedures. @S867 */ subject s : RampPersonnel; }
    requirement def R172 { doc /* The Airline Operations Coordinator and Aircraft Operator Representative shall be trained to submit, review, and update Flight Intent Message data through approved interfaces and to assess the operational effect of Calculated Takeoff Time and Target Off Block Time changes. @S868 */ subject s : AirlineOperationsCoordinator; }
    requirement def R173 { doc /* The Airline Operations Coordinator and Aircraft Operator Representative shall be trained to submit, review, and update Flight Intent Message data through approved interfaces and to assess the operational effect of Calculated Takeoff Time and Target Off Block Time changes. @S868 */ subject s : AircraftOperatorRepresentative; }
    requirement def R174 { doc /* Ground handling personnel shall be trained by the Ground Handling Dispatcher on the Handling Resource Planner and on procedures for confirming that resource constraints are represented accurately before they influence collaborative decisions. @S869 */ subject s : GroundHandlingPersonnel; }
    requirement def R175 { doc /* The Slot Coordinator shall receive training on the Slot Allocation Engine, Airport CDM Portal, and applicable Business Rules Registry entries so that slot actions are applied consistently and transparently. @S870 */ subject s : SlotCoordinator; }
    requirement def R176 { doc /* The Network Operations Liaison and Airspace Sector Planner shall be trained to coordinate regional constraints, sector load conditions, and network measures using the Sector Load Monitor and Common Situation Display. @S871 */ subject s : NetworkOperationsLiaison; }
    requirement def R177 { doc /* The Network Operations Liaison and Airspace Sector Planner shall be trained to coordinate regional constraints, sector load conditions, and network measures using the Sector Load Monitor and Common Situation Display. @S871 */ subject s : AirspaceSectorPlanner; }
    requirement def R178 { doc /* The Airport Duty Manager shall be trained to recognize when an Airport Capacity Plan requires revision and when the operational state should move from Normal Operations to Adverse Weather Mode or Capacity Reduction State. @S872 */ subject s : AirportDutyManager; }
    requirement def R179 { doc /* an Airport Capacity Plan requires revision @S872 */ subject s : AirportCapacityPlan; }
    requirement def R180 { doc /* the operational state should move from Normal Operations to Adverse Weather Mode or Capacity Reduction State @S872 */ subject s : OperationalState; }
    requirement def R181 { doc /* The Meteorology Briefing Officer shall be trained to explain weather uncertainty in operational terms and to verify that the Weather Ingest Gateway supports the assumptions used during briefings. @S873 */ subject s : MeteorologyBriefingOfficer; }
    requirement def R182 { doc /* The Emergency Response Coordinator shall participate in recurrent training so that emergency priorities are integrated into flow management decisions without obscuring command authority or safety responsibilities. @S874 */ subject s : EmergencyResponseCoordinator; }
    requirement def R183 { doc /* The Deicing Coordinator shall receive seasonal refresher training on how deicing capacity assumptions are represented in demand and departure metering tools. @S875 */ subject s : DeicingCoordinator; }
    requirement def R184 { doc /* The Data Governance Steward shall train operational users on data quality responsibilities, privacy expectations, and the correct interpretation of audit records in the Audit Event Ledger. @S876 */ subject s : DataGovernanceSteward; }
    requirement def R185 { doc /* The System Support Engineer shall train superusers on service status checks, access fault escalation, and safe use of the Contingency Operations Console during partial outages. @S877 */ subject s : SystemSupportEngineer; }
    requirement def R186 { doc /* Initial training shall include classroom instruction, supervised workstation practice, scenario walkthroughs in the Digital Briefing Room, and observed operational shadowing before independent system use is authorized. @S878 */ subject s : InitialTraining; }
    requirement def R187 { doc /* Recurrent training shall be required at least annually and after major changes to the Regional Flow Platform, Demand Prediction Service, Capacity Assessment Module, or Flight Data Exchange. @S879 */ subject s : RecurrentTraining; }
    requirement def R188 { doc /* Simulation exercises shall use realistic traffic samples, weather constraints, surface congestion, airline schedule pressure, handling resource shortages, and recovery objectives to test coordinated decision making. @S880 */ subject s : SimulationExercises; }
    requirement def R189 { doc /* Each exercise shall include participants from tower, ramp, airline operations, handling, airport operations, network coordination, meteorology, data governance, and system support functions when those functions are relevant to the scenario. @S881 */ subject s : Exercise; }
    requirement def R190 { doc /* Exercises shall cover transitions among Normal Operations, Adverse Weather Mode, Capacity Reduction State, Recovery Phase, Contingency Fallback State, and Slot Compliance State. @S882 */ subject s : Exercises; }
    requirement def R191 { doc /* Simulation events shall require users to compare automated recommendations with local knowledge, document significant decisions in the Collaborative Decision Log, and explain departures from system proposals. @S883 */ subject s : SimulationEvents; }
    requirement def R192 { doc /* Human factors safeguards shall include workload monitoring, clear alert prioritization, consistent terminology, confirmation steps for high impact actions, and protection against silent mode changes. @S884 */ subject s : HumanFactorsSafeguards; }
    requirement def R193 { doc /* Workstation layouts shall support rapid comparison between the Common Situation Display, Airport CDM Portal, Tower Sequence Manager, Ramp Movement Board, and relevant advisory messages without forcing users to copy critical values manually. @S885 */ subject s : WorkstationLayouts; }
    requirement def R194 { doc /* Training assessments shall verify that users can identify stale data, time synchronization problems, duplicate flights, conflicting constraints, and inappropriate automation reliance before such issues affect live operations. @S886 */ subject s : TrainingAssessments; }
    requirement def R195 { doc /* Post-exercise reviews shall use evidence from the Performance Analytics Warehouse and Audit Event Ledger to improve procedures, refine training materials, and confirm that human performance concerns are assigned to accountable owners. @S887 */ subject s : PostExerciseReviews; }
    requirement def R196 { doc /* Deployment of the Regional Flow Platform shall proceed through phased increments that limit operational exposure while progressively adding airports, interfaces, and decision support functions. @S888 */ subject s : DeploymentOfTheRegionalFlowPlatform; }
    requirement def R197 { doc /* The first increment shall establish the core operational baseline for the Regional Flow Manager, Network Operations Liaison, Data Governance Steward, and System Support Engineer in a controlled production environment. @S889 */ subject s : FirstIncrement; }
    requirement def R198 { doc /* This baseline shall include the Identity Access Service, Time Synchronization Service, Audit Event Ledger, Performance Analytics Warehouse, and Business Rules Registry before any airport is permitted to exchange operational data. @S890 */ subject s : CoreOperationalBaseline; }
    requirement def R199 { doc /* Pilot airport selection shall favor locations with stable operational leadership, representative traffic complexity, available surface surveillance data, and demonstrated willingness to participate in joint procedure development. @S891 */ subject s : PilotAirportSelection; }
    requirement def R200 { doc /* The initial pilot shall include one constrained primary airport and one less constrained regional airport so that both high-demand and routine operating patterns are exercised. @S892 */ subject s : InitialPilot; }
    requirement def R201 { doc /* Each candidate airport shall provide evidence that the Airport Duty Manager, Tower Supervisor, Ramp Control Lead, Airline Operations Coordinator, Ground Handling Dispatcher, and Aircraft Operator Representative have named accountable implementation contacts. @S893 */ subject s : CandidateAirport; }
    requirement def R202 { doc /* Readiness Gate 1 shall confirm that governance, security approvals, user role definitions, operating hours, and support escalation paths are documented and accepted by local stakeholders. @S894 */ subject s : ReadinessGate1; }
    requirement def R203 { doc /* Readiness Gate 2 shall confirm that the Flight Data Exchange, Airline Interface Adapter, Surface Surveillance Adapter, and Weather Ingest Gateway can be connected without disrupting existing airport operations. @S895 */ subject s : ReadinessGate2; }
    requirement def R204 { doc /* Readiness Gate 3 shall confirm that local procedures have been mapped to the Airport CDM Portal, Tower Sequence Manager, Ramp Movement Board, Departure Metering Service, and Arrival Regulation Console. @S896 */ subject s : ReadinessGate3; }
    requirement def R205 { doc /* Readiness Gate 4 shall confirm that training, shadow operations, contingency procedures, and operational acceptance criteria have been completed before live collaborative decisions are made through the Regional Flow Platform. @S897 */ subject s : ReadinessGate4; }
    requirement def R206 { doc /* Interface certification shall be performed separately from operational acceptance so that technical conformance defects do not become unresolved procedural issues. @S898 */ subject s : InterfaceCertification; }
    requirement def R207 { doc /* Each interface shall be tested for message structure, time stamping, identity attribution, replay handling, duplicate detection, outage recovery, and rejection behavior under degraded network conditions. @S899 */ subject s : Interface; }
    requirement def R208 { doc /* The Demand Prediction Service, Capacity Assessment Module, Slot Allocation Engine, Gate Conflict Detector, Sector Load Monitor, North Runway Meter, and South Runway Meter shall be certified against agreed reference scenarios before they are used for operational recommendations. @S900 */ subject s : DemandPredictionService; }
    requirement def R209 { doc /* The Demand Prediction Service, Capacity Assessment Module, Slot Allocation Engine, Gate Conflict Detector, Sector Load Monitor, North Runway Meter, and South Runway Meter shall be certified against agreed reference scenarios before they are used for operational recommendations. @S900 */ subject s : CapacityAssessmentModule; }
    requirement def R210 { doc /* The Demand Prediction Service, Capacity Assessment Module, Slot Allocation Engine, Gate Conflict Detector, Sector Load Monitor, North Runway Meter, and South Runway Meter shall be certified against agreed reference scenarios before they are used for operational recommendations. @S900 */ subject s : SlotAllocationEngine; }
    requirement def R211 { doc /* The Demand Prediction Service, Capacity Assessment Module, Slot Allocation Engine, Gate Conflict Detector, Sector Load Monitor, North Runway Meter, and South Runway Meter shall be certified against agreed reference scenarios before they are used for operational recommendations. @S900 */ subject s : GateConflictDetector; }
    requirement def R212 { doc /* The Demand Prediction Service, Capacity Assessment Module, Slot Allocation Engine, Gate Conflict Detector, Sector Load Monitor, North Runway Meter, and South Runway Meter shall be certified against agreed reference scenarios before they are used for operational recommendations. @S900 */ subject s : SectorLoadMonitor; }
    requirement def R213 { doc /* The Demand Prediction Service, Capacity Assessment Module, Slot Allocation Engine, Gate Conflict Detector, Sector Load Monitor, North Runway Meter, and South Runway Meter shall be certified against agreed reference scenarios before they are used for operational recommendations. @S900 */ subject s : NorthRunwayMeter; }
    requirement def R214 { doc /* The Demand Prediction Service, Capacity Assessment Module, Slot Allocation Engine, Gate Conflict Detector, Sector Load Monitor, North Runway Meter, and South Runway Meter shall be certified against agreed reference scenarios before they are used for operational recommendations. @S900 */ subject s : SouthRunwayMeter; }
    requirement def R215 { doc /* Certification results shall be recorded in the Collaborative Decision Log when they affect operational procedures and in the Audit Event Ledger when they affect access, configuration, or transaction traceability. @S901 */ subject s : CertificationResults; }
    requirement def R216 { doc /* Airport onboarding shall start with data discovery workshops that identify local tools, manual workarounds, unofficial spreadsheets, and locally maintained constraint registers. @S902 */ subject s : AirportOnboarding; }
    requirement def R217 { doc /* The migration plan shall classify each local tool as retired, retained for read-only reference, integrated through an approved interface, or replaced by a Regional Flow Platform function. @S903 */ subject s : MigrationPlan; }
    requirement def R218 { doc /* No local tool shall be retired until the responsible operational owner verifies that its essential decisions, timing assumptions, and audit needs are supported in the target process. @S904 */ subject s : LocalTool; }
    requirement def R219 { doc /* During shadow operations, local tools shall remain the authoritative source while the Regional Flow Platform produces parallel outputs for comparison by operational users. @S905 */ subject s : LocalTools; }
    requirement def R220 { doc /* The cutover decision shall be based on measured agreement between local practice and Regional Flow Platform outputs, user confidence, defect closure, and demonstrated recovery from simulated failures. @S906 */ subject s : CutoverDecision; }
    requirement def R221 { doc /* After cutover, local users shall enter operational decisions through the Airport CDM Portal and shall avoid reintroducing uncontrolled parallel records that undermine common situational awareness. @S907 */ subject s : LocalUsers; }
    requirement def R222 { doc /* The Contingency Operations Console shall be available at each onboarded airport before reliance on the Regional Flow Platform is declared for Normal Operations, Adverse Weather Mode, Capacity Reduction State, Recovery Phase, or Contingency Fallback State. @S908 */ subject s : ContingencyOperationsConsole; }
    requirement def R223 { doc /* Expansion beyond the pilot airports shall occur in waves that group airports by interface maturity, traffic dependency, stakeholder readiness, and available support capacity. @S909 */ subject s : ExpansionBeyondThePilotAirports; }
    requirement def R224 { doc /* Each onboarding wave shall include a stabilization period in which the System Support Engineer and Data Governance Steward monitor defect trends, data quality, access changes, and user adoption. @S910 */ subject s : OnboardingWave; }
    requirement def R225 { doc /* Full regional deployment shall be declared only after the Regional Flow Manager confirms that operational benefits, safety constraints, cyber controls, and stakeholder obligations remain stable across multiple airports and traffic conditions. @S911 */ subject s : FullRegionalDeployment; }
    requirement def R226 { doc /* Operational service management for the Regional Flow Platform shall begin when a deployed airport is accepted into steady state support after the regional stabilization period. @S912 */ subject s : OperationalServiceManagement; }
    requirement def R227 { doc /* The service model shall distinguish continuous operational support from planned engineering support so that safety related traffic flow functions remain protected at all times. @S913 */ subject s : ServiceModel; }
    requirement def R228 { doc /* The System Support Engineer shall provide round the clock on call coverage for production incidents affecting the Regional Flow Platform, Airport CDM Portal, Slot Allocation Engine, Departure Metering Service, Arrival Regulation Console, and Alert Distribution Hub. @S914 */ subject s : SystemSupportEngineer; }
    requirement def R229 { doc /* Standard service desk coverage for access requests, reporting questions, configuration inquiries, and minor usability issues shall be available during normal regional administrative hours on business days. @S915 */ subject s : StandardServiceDeskCoverage; }
    requirement def R230 { doc /* During published peak traffic periods, Adverse Weather Mode, Capacity Reduction State, and Recovery Phase, the on call support posture shall be raised so that the System Support Engineer can join the Digital Briefing Room without delay. @S916 */ subject s : OnCallSupportPosture; }
    requirement def R231 { doc /* The Regional Flow Manager, Tower Supervisor, Ramp Control Lead, Airport Duty Manager, and Network Operations Liaison shall retain operational command authority during support activity. @S917 */ subject s : RegionalFlowManager; }
    requirement def R232 { doc /* The Regional Flow Manager, Tower Supervisor, Ramp Control Lead, Airport Duty Manager, and Network Operations Liaison shall retain operational command authority during support activity. @S917 */ subject s : TowerSupervisor; }
    requirement def R233 { doc /* The Regional Flow Manager, Tower Supervisor, Ramp Control Lead, Airport Duty Manager, and Network Operations Liaison shall retain operational command authority during support activity. @S917 */ subject s : RampControlLead; }
    requirement def R234 { doc /* The Regional Flow Manager, Tower Supervisor, Ramp Control Lead, Airport Duty Manager, and Network Operations Liaison shall retain operational command authority during support activity. @S917 */ subject s : AirportDutyManager; }
    requirement def R235 { doc /* The Regional Flow Manager, Tower Supervisor, Ramp Control Lead, Airport Duty Manager, and Network Operations Liaison shall retain operational command authority during support activity. @S917 */ subject s : NetworkOperationsLiaison; }
    requirement def R236 { doc /* The System Support Engineer shall advise operational supervisors on technical status, known workarounds, data integrity concerns, and recovery options, but shall not issue traffic management instructions. @S918 */ subject s : SystemSupportEngineer; }
    requirement def R237 { doc /* Incidents shall be classified by operational effect, with the highest priority assigned to loss of common situational awareness, loss of slot computation, corruption of operational timing data, or failure of alert distribution during active traffic management. @S919 */ subject s : Incidents; }
    requirement def R238 { doc /* A critical incident shall be acknowledged within fifteen minutes and shall have continuous technical ownership until service is restored or an agreed operational workaround is in place. @S920 */ subject s : CriticalIncident; }
    requirement def R239 { doc /* A high priority incident that degrades a major function without stopping tactical coordination shall be acknowledged within thirty minutes and shall be reviewed with the affected operational supervisor at least hourly. @S921 */ subject s : HighPriorityIncident; }
    requirement def R240 { doc /* Medium and low priority incidents shall be handled through the service queue, with target updates provided at intervals appropriate to their operational impact and planned resolution path. @S922 */ subject s : MediumAndLowPriorityIncidents; }
    requirement def R241 { doc /* The System Support Engineer shall maintain an incident record that captures the initial symptom, affected components, operational state, timeline, mitigation actions, data corrections, and supervisor decisions. @S923 */ subject s : SystemSupportEngineer; }
    requirement def R242 { doc /* Incident records shall reference the Audit Event Ledger where user actions, configuration changes, interface events, or automated decisions are relevant to the investigation. @S924 */ subject s : IncidentRecord; }
    requirement def R243 { doc /* The Collaborative Decision Log shall be used to preserve the operational context of major incidents when traffic management decisions are made while a technical degradation is present. @S925 */ subject s : CollaborativeDecisionLog; }
    requirement def R244 { doc /* The System Support Engineer shall verify that fallback tools, exported operational data, and restoration checkpoints are available before advising that normal technical service can resume. @S927 */ subject s : SystemSupportEngineer; }
    requirement def R245 { doc /* Post incident review shall be required for critical incidents, repeated high priority incidents, security related events, and failures that occur during capacity constrained operations. @S928 */ subject s : PostIncidentReview; }
    requirement def R246 { doc /* The review shall identify technical root cause, operational contributing factors, effectiveness of workarounds, user communication quality, and corrective actions assigned to named owners. @S929 */ subject s : PostIncidentReview; }
    requirement def R247 { doc /* Planned change windows shall normally be scheduled during low demand night periods and shall be coordinated with the Regional Flow Manager, Airport Duty Manager, Tower Supervisor, and affected Aircraft Operator Representative groups before approval. @S930 */ subject s : PlannedChangeWindows; }
    requirement def R248 { doc /* Changes that modify the Business Rules Registry, Identity Access Service, Time Synchronization Service, Flight Data Exchange, or operational metering behavior shall require additional validation in a representative test environment before production release. @S931 */ subject s : Changes; }
    requirement def R249 { doc /* Emergency changes may be applied outside the standard window when needed to restore service, protect cyber security, or prevent material operational harm, but they shall be documented and retrospectively approved. @S932 */ subject s : EmergencyChanges; }
    requirement def R250 { doc /* Service level targets shall include monthly availability for critical production functions, incident response time, restoration time, data feed timeliness, and successful completion of scheduled operational reports. @S933 */ subject s : ServiceLevelTargets; }
    requirement def R251 { doc /* Availability targets shall exclude approved maintenance windows, customer network outages outside the managed boundary, and periods when operational supervisors have directed use of contingency procedures for nontechnical reasons. @S934 */ subject s : AvailabilityTargets; }
    requirement def R252 { doc /* Performance against service targets shall be reviewed with the Regional Flow Manager and Data Governance Steward so that service quality, operational benefit, data quality, and user confidence are managed as a single operating obligation. @S935 */ subject s : PerformanceAgainstServiceTargets; }
    requirement def R253 { doc /* Future enhancement of the Regional Flow Platform should be treated as an incremental extension of the operational service rather than as a replacement of the current concept. @S936 */ subject s : RegionalFlowPlatform; }
    requirement def R254 { doc /* Cross-border exchange should use standardized message structures where practical @S939 */ subject s : CrossBorderExchange; }
    requirement def R255 { doc /* the Business Rules Registry should retain the local parameters needed for Meridian operations @S939 */ subject s : BusinessRulesRegistry; }
    requirement def R256 { doc /* The Flight Data Exchange should be enhanced to accept richer intent data, including improved route options, expected cruise profiles, and updated departure readiness information. @S940 */ subject s : FlightDataExchange; }
    requirement def R257 { doc /* The Demand Prediction Service should use this data to create more stable demand pictures across longer planning horizons while still preserving tactical responsiveness. @S941 */ subject s : DemandPredictionService; }
    requirement def R258 { doc /* Trajectory prediction should also make greater use of weather features, sector configuration, runway direction, and surface movement status when estimating flight progress. @S942 */ subject s : TrajectoryPrediction; }
    requirement def R259 { doc /* The Weather Ingest Gateway and Sector Load Monitor should provide the common inputs needed to connect airspace capacity and airport capacity in the same prediction cycle. @S943 */ subject s : WeatherIngestGateway; }
    requirement def R260 { doc /* The Weather Ingest Gateway and Sector Load Monitor should provide the common inputs needed to connect airspace capacity and airport capacity in the same prediction cycle. @S943 */ subject s : SectorLoadMonitor; }
    requirement def R261 { doc /* The Capacity Assessment Module should evolve from a mainly rules-based assessment into a service that can compare planned capacity, observed throughput, and predicted constraint persistence. @S944 */ subject s : CapacityAssessmentModule; }
    requirement def R262 { doc /* Any use of learning models should be introduced with explainability requirements so that operational users can understand why a capacity or delay estimate has changed. @S945 */ subject s : LearningModels; }
    requirement def R263 { doc /* Advanced turnaround prediction should combine aircraft state, handling milestones, stand occupancy, crew readiness, passenger processing, and ramp congestion signals. @S946 */ subject s : AdvancedTurnaroundPrediction; }
    requirement def R264 { doc /* The Airport CDM Portal, Airline Interface Adapter, Handling Resource Planner, and Ramp Movement Board should provide the main operational inputs for this capability. @S947 */ subject s : AirportCDMPortal; }
    requirement def R265 { doc /* The Airport CDM Portal, Airline Interface Adapter, Handling Resource Planner, and Ramp Movement Board should provide the main operational inputs for this capability. @S947 */ subject s : AirlineInterfaceAdapter; }
    requirement def R266 { doc /* The Airport CDM Portal, Airline Interface Adapter, Handling Resource Planner, and Ramp Movement Board should provide the main operational inputs for this capability. @S947 */ subject s : HandlingResourcePlanner; }
    requirement def R267 { doc /* The Airport CDM Portal, Airline Interface Adapter, Handling Resource Planner, and Ramp Movement Board should provide the main operational inputs for this capability. @S947 */ subject s : RampMovementBoard; }
    requirement def R268 { doc /* Predicted changes to Target Off Block Time should be presented with confidence levels rather than as unconditional system corrections. @S948 */ subject s : PredictedChangesToTargetOffBlockTime; }
    requirement def R269 { doc /* The Slot Allocation Engine should use improved turnaround predictions to protect feasible Calculated Takeoff Time assignments and to reduce avoidable re-sequencing. @S949 */ subject s : SlotAllocationEngine; }
    requirement def R270 { doc /* The Tower Sequence Manager and Departure Metering Service should receive only the information needed for tactical sequencing, with detailed airline operational data controlled by policy. @S950 */ subject s : TowerSequenceManager; }
    requirement def R271 { doc /* The Tower Sequence Manager and Departure Metering Service should receive only the information needed for tactical sequencing, with detailed airline operational data controlled by policy. @S950 */ subject s : DepartureMeteringService; }
    requirement def R272 { doc /* Machine-assisted recovery options should support the Recovery Phase by proposing coordinated actions that balance runway throughput, sector loading, stand availability, and airline priorities. @S951 */ subject s : MachineAssistedRecoveryOptions; }
    requirement def R273 { doc /* These options should be generated by the Contingency Operations Console and reviewed through the Common Situation Display before any operational decision is applied. @S952 */ subject s : MachineAssistedRecoveryOptions; }
    requirement def R274 { doc /* The system should not automatically impose a Ground Delay Program, change an Airport Acceptance Rate, or alter a tactical measure without authorized human confirmation. @S953 */ subject s : System; }
    requirement def R275 { doc /* Recovery recommendations should include the operational rationale, expected benefit, key assumptions, and possible secondary effects on connected flights and surface movements. @S954 */ subject s : RecoveryRecommendations; }
    requirement def R276 { doc /* The Collaborative Decision Log and Audit Event Ledger should record each proposed option, the user response, and the final decision so that performance can be reviewed after operations. @S955 */ subject s : CollaborativeDecisionLog; }
    requirement def R277 { doc /* The Collaborative Decision Log and Audit Event Ledger should record each proposed option, the user response, and the final decision so that performance can be reviewed after operations. @S955 */ subject s : AuditEventLedger; }
    requirement def R278 { doc /* Regional expansion should include a repeatable onboarding pattern for new airports, airspace sectors, airlines, and handling organizations. @S956 */ subject s : RegionalExpansion; }
    requirement def R279 { doc /* The Identity Access Service, Time Synchronization Service, and Performance Analytics Warehouse should be scaled early because they form shared foundations for a wider regional deployment. @S957 */ subject s : IdentityAccessService; }
    requirement def R280 { doc /* The Identity Access Service, Time Synchronization Service, and Performance Analytics Warehouse should be scaled early because they form shared foundations for a wider regional deployment. @S957 */ subject s : TimeSynchronizationService; }
    requirement def R281 { doc /* The Identity Access Service, Time Synchronization Service, and Performance Analytics Warehouse should be scaled early because they form shared foundations for a wider regional deployment. @S957 */ subject s : PerformanceAnalyticsWarehouse; }
    requirement def R282 { doc /* Data governance should remain under the Data Governance Steward, with clear rules for retention, consent, quality thresholds, and permitted operational use. @S958 */ subject s : DataGovernance; }
    requirement def R283 { doc /* Future releases should be validated in shadow mode before operational activation so that the Regional Flow Manager, Airline Operations Coordinator, Tower Supervisor, and Airport Duty Manager can compare recommendations with actual outcomes. @S959 */ subject s : FutureReleases; }
    requirement def R284 { doc /* Sustained regional ATFM and A-CDM operation requires each participating organization to treat the operating picture as a shared operational asset rather than a local advisory product. @S960 */ subject s : ParticipatingOrganization; }
    requirement def R285 { doc /* The Airline Operations Coordinator and Aircraft Operator Representative are committed to providing operationally realistic airline intentions and to honoring agreed times unless a safety, security, or serviceability issue prevents compliance. @S965 */ subject s : AirlineOperationsCoordinator; }
    requirement def R286 { doc /* The Airline Operations Coordinator and Aircraft Operator Representative are committed to providing operationally realistic airline intentions and to honoring agreed times unless a safety, security, or serviceability issue prevents compliance. @S965 */ subject s : AircraftOperatorRepresentative; }
    requirement def R287 { doc /* The Ramp Control Lead and Ground Handling Dispatcher are committed to maintaining accurate surface and handling status so that departure metering is based on feasible ground operations. @S966 */ subject s : RampControlLead; }
    requirement def R288 { doc /* The Ramp Control Lead and Ground Handling Dispatcher are committed to maintaining accurate surface and handling status so that departure metering is based on feasible ground operations. @S966 */ subject s : GroundHandlingDispatcher; }
    requirement def R289 { doc /* The Common Situation Display is the shared baseline for time-critical coordination and should be kept consistent with the Regional Flow Platform and Airport CDM Portal. @S974 */ subject s : CommonSituationDisplay; }
    requirement def R290 { doc /* Calculated Takeoff Time and Target Off Block Time commitments should be treated as executable operating constraints unless they are revised through the agreed coordination process. @S976 */ subject s : CalculatedTakeoffTimeCommitments; }
    requirement def R291 { doc /* Calculated Takeoff Time and Target Off Block Time commitments should be treated as executable operating constraints unless they are revised through the agreed coordination process. @S976 */ subject s : TargetOffBlockTimeCommitments; }
    requirement def R292 { doc /* Ground Delay Program decisions, Tactical Regulation Proposal review, and Airport Acceptance Rate changes should be visible to affected participants before they are applied whenever operational time permits. @S977 */ subject s : GroundDelayProgramDecisions; }
    requirement def R293 { doc /* Ground Delay Program decisions, Tactical Regulation Proposal review, and Airport Acceptance Rate changes should be visible to affected participants before they are applied whenever operational time permits. @S977 */ subject s : TacticalRegulationProposalReview; }
    requirement def R294 { doc /* Ground Delay Program decisions, Tactical Regulation Proposal review, and Airport Acceptance Rate changes should be visible to affected participants before they are applied whenever operational time permits. @S977 */ subject s : AirportAcceptanceRateChanges; }
    requirement def R295 { doc /* The Flight Data Exchange, Airline Interface Adapter, Surface Surveillance Adapter, and Weather Ingest Gateway must be operated with monitored data quality thresholds and clear fallback procedures. @S979 */ subject s : FlightDataExchange; }
    requirement def R296 { doc /* The Flight Data Exchange, Airline Interface Adapter, Surface Surveillance Adapter, and Weather Ingest Gateway must be operated with monitored data quality thresholds and clear fallback procedures. @S979 */ subject s : AirlineInterfaceAdapter; }
    requirement def R297 { doc /* The Flight Data Exchange, Airline Interface Adapter, Surface Surveillance Adapter, and Weather Ingest Gateway must be operated with monitored data quality thresholds and clear fallback procedures. @S979 */ subject s : SurfaceSurveillanceAdapter; }
    requirement def R298 { doc /* The Flight Data Exchange, Airline Interface Adapter, Surface Surveillance Adapter, and Weather Ingest Gateway must be operated with monitored data quality thresholds and clear fallback procedures. @S979 */ subject s : WeatherIngestGateway; }
    requirement def R299 { doc /* The Slot Allocation Engine, Departure Metering Service, Arrival Regulation Console, Tower Sequence Manager, and Ramp Movement Board must use the approved rules recorded in the Business Rules Registry. @S980 */ subject s : SlotAllocationEngine; }
    requirement def R300 { doc /* The Slot Allocation Engine, Departure Metering Service, Arrival Regulation Console, Tower Sequence Manager, and Ramp Movement Board must use the approved rules recorded in the Business Rules Registry. @S980 */ subject s : DepartureMeteringService; }
    requirement def R301 { doc /* The Slot Allocation Engine, Departure Metering Service, Arrival Regulation Console, Tower Sequence Manager, and Ramp Movement Board must use the approved rules recorded in the Business Rules Registry. @S980 */ subject s : ArrivalRegulationConsole; }
    requirement def R302 { doc /* The Slot Allocation Engine, Departure Metering Service, Arrival Regulation Console, Tower Sequence Manager, and Ramp Movement Board must use the approved rules recorded in the Business Rules Registry. @S980 */ subject s : TowerSequenceManager; }
    requirement def R303 { doc /* The Slot Allocation Engine, Departure Metering Service, Arrival Regulation Console, Tower Sequence Manager, and Ramp Movement Board must use the approved rules recorded in the Business Rules Registry. @S980 */ subject s : RampMovementBoard; }
    requirement def R304 { doc /* The Identity Access Service and Audit Event Ledger must support traceability, least-privilege access, and after-action accountability for all operationally significant changes. @S981 */ subject s : IdentityAccessService; }
    requirement def R305 { doc /* The Identity Access Service and Audit Event Ledger must support traceability, least-privilege access, and after-action accountability for all operationally significant changes. @S981 */ subject s : AuditEventLedger; }
    requirement def R306 { doc /* The Performance Analytics Warehouse and Post Operations Report should be used to measure compliance, delay outcomes, capacity use, and the effectiveness of collaborative decisions. @S982 */ subject s : PerformanceAnalyticsWarehouse; }
    requirement def R307 { doc /* The Performance Analytics Warehouse and Post Operations Report should be used to measure compliance, delay outcomes, capacity use, and the effectiveness of collaborative decisions. @S982 */ subject s : PostOperationsReport; }
    requirement def R308 { doc /* Governance should favor transparent decision making, timely challenge by affected parties, documented resolution of disputes, and continuous improvement through training, exercises, and post-operations review. @S983 */ subject s : Governance; }
}
