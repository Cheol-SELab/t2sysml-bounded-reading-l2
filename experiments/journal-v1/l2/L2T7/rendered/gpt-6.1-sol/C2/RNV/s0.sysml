package L2Model {
    item def ASecurityExceptionTicketItem { doc /* @S170 */ }
    item def AcceptedOrbitFilesItem { doc /* @S142 */ }
    item def AcceptedRawDataItem { doc /* @S153 */ }
    item def AntennaDeicingNoticeItem { doc /* @S113 */ }
    item def AntennaPointingPredictionsItem { doc /* @S148 */ }
    item def AntennaPointingSupportProductsItem { doc /* @S040 */ }
    item def AntennaStatusItem { doc /* @S079 */ }
    item def AssociatedQualityMetadataItem { doc /* @S178 */ }
    item def AttitudeIndicatorsItem { doc /* @S082 */ }
    item def ChecksumEvidenceItem { doc /* @S178 */ }
    item def CommandCountersItem { doc /* @S082 */ }
    item def CommandPreparationPackageItem { doc /* @S118 */ }
    item def ConfirmedServiceImpactsItem { doc /* @S225 */ }
    item def DegradedLinkConditionsItem { doc /* @S085 */ }
    item def DeviationsFromExpectedStateItem { doc /* @S083 */ }
    item def DopplerResidualReportItem { doc /* @S131 */ }
    item def DynamicOrbitSolutionsItem { doc /* @S130,S131 */ }
    item def EventPredictionsItem { doc /* @S141 */ }
    item def FaultProtectionMessagesItem { doc /* @S082 */ }
    item def HealthTelemetryItem { doc /* @S086 */ }
    item def LaserRetroreflectorWindowItem { doc /* @S207 */ }
    item def LinkConfigurationItem { doc /* @S079 */ }
    item def LocalConstraintsItem { doc /* @S043 */ }
    item def NavigationProductsItem { doc /* @S008 */ }
    item def NullItem { doc /* @S065 */ }
    item def OnboardStorageItem { doc /* @S082 */ }
    item def OperationalConstraintsItem { doc /* @S099 */ }
    item def OrbitPredictionsItem { doc /* @S106 */ }
    item def OrbitQualityStateChangesItem { doc /* @S194 */ }
    item def PassReplayPacketItem { doc /* @S198 */ }
    item def PowerStateItem { doc /* @S082 */ }
    item def PredictedOrbitItem { doc /* @S138 */ }
    item def PredictedViewingGeometryItem { doc /* @S147 */ }
    item def ProcessingWorkItem { doc /* @S221 */ }
    item def ProductPackageItem { doc /* @S178 */ }
    item def ProvenanceItem { doc /* @S173 */ }
    item def RoutineEphemeridesItem { doc /* @S141 */ }
    item def RoutingReadinessItem { doc /* @S079 */ }
    item def SecurityExceptionTicketItem { doc /* @S074 */ }
    item def SessionIdentifierItem { doc /* @S153 */ }
    item def SpacecraftModeItem { doc /* @S082 */ }
    item def SpacecraftTelemetryItem { doc /* @S013 */ }
    item def TheCalibrationPatchBundleItem { doc /* @S162 */ }
    item def TheEphemerisDeltaNoteItem { doc /* @S240 */ }
    item def TheProductHoldListItem { doc /* @S239 */ }
    item def TheStarTrackerMaskFileItem { doc /* @S206 */ }
    item def TheStorageWatermarkSnapshotItem { doc /* @S241 */ }
    item def ThermalMarginsItem { doc /* @S082 */ }
    item def TimeSynchronizationItem { doc /* @S068 */ }
    item def TimingAlarmsItem { doc /* @S072 */ }
    item def TimingReferencesItem { doc /* @S079 */ }
    item def VisibilityAssumptionsItem { doc /* @S106 */ }
    item def VisibilityPredictionsItem { doc /* @S040 */ }
    part def Activities { doc /* @S114 */ }
    part def Anomalies { doc /* @S099 */ }
    part def Anomaly { doc /* @S212 */ }
    part def AnomalyDeclaration { doc /* @S235 */ }
    part def Antenna { doc /* @S047 */ }
    part def AntennaSiteEquipment { doc /* @S070 */ }
    part def ApplicablePolicy { doc /* @S196 */ }
    part def ArchiveAdmission { doc /* @S178 */ }
    part def ArchiveAvailability { doc /* @S244 */ }
    part def ArchiveOperationsQueue { doc /* @S194 */ }
    part def ArchivedDownlinkContext { doc /* @S198 */ }
    part def AttitudeConstraints { doc /* @S097 */ }
    part def AttitudeGeometrySupport { doc /* @S138 */ }
    part def AutomatedConsumers { doc /* @S166 */ }
    part def BackupProcessingCluster { doc /* @S004,S066,S150,S173,S221,S241 */ }
    part def BudgetForRealTimeCommandAndTelemetryTraffic { doc /* @S063 */ }
    part def CalibrationAnalysis { doc /* @S094 */ }
    part def CalibrationChange { doc /* @S164 */ }
    part def CalibrationImprovements { doc /* @S192 */ }
    part def CataloguePublication { doc /* @S180 */ }
    part def CatalogueRecords { doc /* @S197 */ }
    part def ChainOfCustodyEntry { doc /* @S214 */ }
    part def ChecksumEvidence { doc /* @S178 */ }
    part def ClockBias { doc /* @S071 */ }
    part def CollisionAssessment { doc /* @S135 */ }
    part def CommandEngineeringWorkflow { doc /* @S118 */ }
    part def CommandRequest { doc /* @S242 */ }
    part def CommandStack { doc /* @S126,S143 */ }
    part def CommandStackValidation { doc /* @S120 */ }
    part def CommandTiming { doc /* @S097 */ }
    part def CommandValidationGateway { doc /* @S004,S012,S119,S121,S143,S206,S242 */ }
    part def CommandValidationTimeliness { doc /* @S244 */ }
    part def CommandingDiscipline { doc /* @S235 */ }
    part def ConfigurationIdentifier { doc /* @S206 */ }
    part def ConsoleDisplays { doc /* @S083 */ }
    part def ConsoleLead { doc /* @S084,S085 */ }
    part def ConsoleOperator { doc /* @S095 */ }
    part def ConstraintChecking { doc /* @S115 */ }
    part def Contact { doc /* @S090 */ }
    part def ContactGeometry { doc /* @S116 */ }
    part def ContactSuccessRate { doc /* @S244 */ }
    part def ControlledOperationalActivity { doc /* @S077 */ }
    part def CoordinateFrame { doc /* @S140 */ }
    part def CorrelationRules { doc /* @S075 */ }
    part def CybersecurityDesk { doc /* @S023,S074,S076,S125,S170,S200,S204,S212,S238 */ }
    part def DataDownlinkPriorities { doc /* @S093 */ }
    part def DegradedLinkConditions { doc /* @S085 */ }
    part def DownlinkAllocationChange { doc /* @S049 */ }
    part def DownloadServices { doc /* @S184 */ }
    part def DownstreamProcessing { doc /* @S048 */ }
    part def DownstreamProcessingFunctions { doc /* @S013 */ }
    part def DownstreamProcessors { doc /* @S153 */ }
    part def DraftSchedule { doc /* @S108,S109 */ }
    part def DynamicOrbitSolutions { doc /* @S134 */ }
    part def EncryptionOverhead { doc /* @S063 */ }
    part def EngineeringAnalysis { doc /* @S013 */ }
    part def EngineeringTeams { doc /* @S218 */ }
    part def EquipmentStatus { doc /* @S087 */ }
    part def ExternalInterfaces { doc /* @S199 */ }
    part def ExternalUsers { doc /* @S104 */ }
    part def FirewallInspectionTime { doc /* @S063 */ }
    part def FirstOperationalReportingCycle { doc /* @S250 */ }
    part def FlightDynamicsDelivery { doc /* @S140 */ }
    part def FlightDynamicsFacility { doc /* @S004,S008,S040,S068,S106,S132,S139,S141,S142,S147,S148,S194,S206,S231 */ }
    part def FlightDynamicsTeam { doc /* @S021,S071,S088,S097,S116,S131,S134,S136,S144,S210,S236,S240 */ }
    part def ForecastIcing { doc /* @S044 */ }
    part def GeneralRelease { doc /* @S164 */ }
    part def GenerationTime { doc /* @S140 */ }
    part def GroundNetworkManagementPractices { doc /* @S050 */ }
    part def GroundNetworkManager { doc /* @S019,S038,S044,S060,S067,S076,S112,S113,S209,S234 */ }
    part def GroundSegment { doc /* @S002,S004,S005,S219 */ }
    part def HeavyPrecipitation { doc /* @S046 */ }
    part def HelpDeskResponsiveness { doc /* @S244 */ }
    part def HighWinds { doc /* @S047 */ }
    part def HumanAuthorization { doc /* @S025 */ }
    part def ImmutableStagingStorage { doc /* @S153 */ }
    part def IncidentLead { doc /* @S225 */ }
    part def IngestWorkflow { doc /* @S152 */ }
    part def InstrumentMode { doc /* @S124 */ }
    part def InstrumentModeChanges { doc /* @S093 */ }
    part def IntegratedDayInTheLifeRehearsal { doc /* @S235 */ }
    part def IntegrityCheck { doc /* @S206 */ }
    part def Interfaces { doc /* @S003 */ }
    part def KirunaXBandAntenna { doc /* @S005,S055,S078 */ }
    part def Label { doc /* @S125 */ }
    part def LateOperationalRequests { doc /* @S105 */ }
    part def LateOrUnevenDelivery { doc /* @S064 */ }
    part def LaterProcessing { doc /* @S149 */ }
    part def Level1AProcessing { doc /* @S156 */ }
    part def Level1BProcessing { doc /* @S156 */ }
    part def Level2Processing { doc /* @S157 */ }
    part def LiveMonitoringPeriod { doc /* @S077 */ }
    part def LocalConstraints { doc /* @S043 */ }
    part def LocalInfrastructure { doc /* @S053 */ }
    part def LocalStationTeams { doc /* @S042 */ }
    part def LongTermArchive { doc /* @S004,S065,S149,S174,S178,S180,S187,S196,S201,S241,S243 */ }
    part def MaintenanceCondition { doc /* @S060 */ }
    part def MandatoryChecks { doc /* @S167 */ }
    part def ManeuverRecommendationPackage { doc /* @S137 */ }
    part def ManeuverScreening { doc /* @S133 */ }
    part def MeasuredBuildup { doc /* @S044 */ }
    part def Measurements { doc /* @S129 */ }
    part def Metadata { doc /* @S160 */ }
    part def MissionControlCenter { doc /* @S004,S032,S043,S056,S068,S077,S079,S093,S096,S099,S100,S140,S141,S175,S203,S217,S230 */ }
    part def MissionControlCenterConsoles { doc /* @S082 */ }
    part def MissionManagement { doc /* @S176 */ }
    part def MissionPlanning { doc /* @S101 */ }
    part def MissionPlanningSystem { doc /* @S004,S011,S034,S099,S102,S107,S114,S118,S141,S142,S207,S216,S240 */ }
    part def MonitoredEvent { doc /* @S074 */ }
    part def NavigationProducts { doc /* @S008 */ }
    part def NetworkControlSystem { doc /* @S004,S010,S033,S056,S072,S079,S148,S170,S171,S205,S233 */ }
    part def NorthSBandAntenna { doc /* @S005,S028,S054 */ }
    part def Null { doc /* @S065,S066,S067,S068,S069,S071,S072,S073,S074,S075,S076,S214,S215,S217,S218,S221,S222,S223,S224,S225,S226 */ }
    part def ObservationRequests { doc /* @S101,S104 */ }
    part def OnboardEvent { doc /* @S091 */ }
    part def OperationalImpacts { doc /* @S137 */ }
    part def OperationalKeyPerformanceIndicators { doc /* @S244,S246 */ }
    part def OperationalReadinessReview { doc /* @S227 */ }
    part def OperationalUseStatement { doc /* @S140 */ }
    part def Operations { doc /* @S013 */ }
    part def OperationsCrew { doc /* @S100 */ }
    part def OperationsStaff { doc /* @S201 */ }
    part def OperationsUsers { doc /* @S127 */ }
    part def Operator { doc /* @S167 */ }
    part def OperatorApprovalState { doc /* @S206 */ }
    part def OperatorDisplay { doc /* @S154 */ }
    part def OperatorDisplays { doc /* @S070 */ }
    part def Operators { doc /* @S083,S098,S213 */ }
    part def OrbitDeterminationEngine { doc /* @S004,S014,S041,S089,S123,S128,S130,S131,S138,S145,S207 */ }
    part def OrbitGeometry { doc /* @S031 */ }
    part def OrbitUpdates { doc /* @S192 */ }
    part def OrbitalUncertainty { doc /* @S116 */ }
    part def OtherGroundFunctions { doc /* @S008 */ }
    part def Pass { doc /* @S079 */ }
    part def PassPreparation { doc /* @S235 */ }
    part def PassReconstruction { doc /* @S090 */ }
    part def PayloadCalibrationTeam { doc /* @S022,S094,S117,S147,S161,S162,S193,S211,S237 */ }
    part def PayloadDownlinkTraffic { doc /* @S055 */ }
    part def PayloadProcessingFacility { doc /* @S004,S009,S049,S110,S141,S151,S178,S215,S232 */ }
    part def PhysicalTopology { doc /* @S053 */ }
    part def PlannedCalibrationActivities { doc /* @S117 */ }
    part def PlannedSupport { doc /* @S113 */ }
    part def PlanningCycle { doc /* @S106 */ }
    part def PlanningProcess { doc /* @S040 */ }
    part def PostBurnAssessmentSteps { doc /* @S097 */ }
    part def PostPassClosureStep { doc /* @S077 */ }
    part def PreviousAcquisitions { doc /* @S124 */ }
    part def PrimaryMonthlyServiceReview { doc /* @S246 */ }
    part def PrimaryProcessingCluster { doc /* @S004,S065,S150,S155,S172,S220 */ }
    part def PrimaryRoutingPolicyPoint { doc /* @S056 */ }
    part def ProcessingLevel { doc /* @S158 */ }
    part def ProcessorCorrections { doc /* @S192 */ }
    part def Product { doc /* @S167 */ }
    part def ProductLatency { doc /* @S244 */ }
    part def ProductQualityDispositionTime { doc /* @S244 */ }
    part def ProductQualityService { doc /* @S004,S015,S124,S130,S162,S165,S168,S173,S181,S195,S239 */ }
    part def Products { doc /* @S182 */ }
    part def ProtectedAccessRouters { doc /* @S054 */ }
    part def ProtectiveActions { doc /* @S076 */ }
    part def Provenance { doc /* @S173 */ }
    part def QualityInvestigations { doc /* @S192 */ }
    part def RateControls { doc /* @S184 */ }
    part def RawTransfer { doc /* @S152 */ }
    part def ReadinessCheck { doc /* @S077 */ }
    part def ReadinessReviewBoard { doc /* @S228 */ }
    part def ReceivedStream { doc /* @S081 */ }
    part def ReceptionGaps { doc /* @S093 */ }
    part def Recovery { doc /* @S176 */ }
    part def RecoveryReporting { doc /* @S235 */ }
    part def RedundantCapabilities { doc /* @S026 */ }
    part def ReferenceClocks { doc /* @S068 */ }
    part def RegisteredUsers { doc /* @S185 */ }
    part def Rehearsals { doc /* @S249 */ }
    part def ReleaseBlockingDefects { doc /* @S168 */ }
    part def RequestedGeometry { doc /* @S124 */ }
    part def ResponsibleTeams { doc /* @S226 */ }
    part def RetentionExceptions { doc /* @S191 */ }
    part def RoutineMissionService { doc /* @S227 */ }
    part def RoutineOperations { doc /* @S243 */ }
    part def RoutineProduction { doc /* @S177 */ }
    part def RoutineReporting { doc /* @S245 */ }
    part def RoutingIssues { doc /* @S087 */ }
    part def SchedulingService { doc /* @S172 */ }
    part def ScreeningRules { doc /* @S136 */ }
    part def SecurityMonitoring { doc /* @S226 */ }
    part def SecurityOrContinuityAnomaly { doc /* @S216 */ }
    part def SentinelVale { doc /* @S001 */ }
    part def SouthSBandAntenna { doc /* @S005,S029,S054 */ }
    part def SpacecraftConfigurationChanges { doc /* @S099 */ }
    part def SpacecraftOperationsTeam { doc /* @S020,S072,S082,S097,S105,S113,S137,S146,S198,S209,S235 */ }
    part def SpacecraftSystemsEngineer { doc /* @S086 */ }
    part def StationDeliveryFiles { doc /* @S152 */ }
    part def StationOperators { doc /* @S043 */ }
    part def StationOutages { doc /* @S099 */ }
    part def SubsystemSpecialists { doc /* @S095 */ }
    part def SupportTeams { doc /* @S249 */ }
    part def SvalbardXBandAntenna { doc /* @S005,S031,S055,S078 */ }
    part def Telemetry { doc /* @S098 */ }
    part def TelemetryCompleteness { doc /* @S244 */ }
    part def TelemetryEngineer { doc /* @S085 */ }
    part def TelemetryFrames { doc /* @S070 */ }
    part def TelemetryIngestService { doc /* @S004,S013,S048,S080,S081,S086,S153,S198 */ }
    part def TelemetryReception { doc /* @S218 */ }
    part def TelemetrySurveillance { doc /* @S235 */ }
    part def TimingConstraints { doc /* @S137 */ }
    part def TrackingArcs { doc /* @S129 */ }
    part def TrackingExpectations { doc /* @S097 */ }
    part def TrackingRecords { doc /* @S070 */ }
    part def TrafficSupportingTheOrbitDeterminationEngine { doc /* @S064 */ }
    part def UnresolvedAnomalyAge { doc /* @S244 */ }
    part def UnsafeOutdoorConditions { doc /* @S047 */ }
    part def UpdatedStateVectors { doc /* @S144 */ }
    part def UserServicesPortal { doc /* @S004,S018,S104,S181,S183,S201,S225,S239 */ }
    part def Users { doc /* @S195 */ }
    part def ValidationEvidence { doc /* @S193 */ }
    part def ValidityInterval { doc /* @S140 */ }
    part def Weather { doc /* @S087 */ }
    part def WideAreaConnectivityDesign { doc /* @S052 */ }
    part system {
        part activities : Activities {
            perform action a0 { doc /* compete for the same spacecraft resource, ground station resource, or operational staffing interval @S114 */ }
        }
        part anomalies : Anomalies {
            perform action a0 { doc /* require adjustment of future contacts or payload activities @S099 */ }
        }
        part anomaly : Anomaly {
            perform action a0 { doc /* includes suspicious authentication, unexpected data movement, unexplained service behavior, or evidence of tampering @S212 */ }
        }
        part anomalyDeclaration : AnomalyDeclaration;
        part antenna : Antenna {
            exhibit state modes {
                state s0 { doc /* unavailable for service @S047 */ }
            }
        }
        part antennaSiteEquipment : AntennaSiteEquipment {
            perform action a0 { doc /* validates time against independent local references before contact start @S070 */ }
        }
        part applicablePolicy : ApplicablePolicy {
            perform action a0 { doc /* allows consolidation after a defined comparison period @S196 */ }
        }
        part archiveAdmission : ArchiveAdmission {
            perform action a0 { doc /* begins only after Payload Processing Facility has delivered the product package, associated quality metadata, and checksum evidence required by the configured acceptance rule @S178 */ }
        }
        part archiveAvailability : ArchiveAvailability;
        part archiveOperationsQueue : ArchiveOperationsQueue;
        part archivedDownlinkContext : ArchivedDownlinkContext {
            perform action a0 { doc /* can support anomaly reconstruction @S198 */ }
        }
        part attitudeConstraints : AttitudeConstraints {
            perform action a0 { doc /* remain consistent @S097 */ }
        }
        part attitudeGeometrySupport : AttitudeGeometrySupport {
            perform action a0 { doc /* translates the predicted orbit into Sun angle, Earth limb, lunar exclusion, target visibility, and antenna pointing information for daily operations @S138 */ }
        }
        part automatedConsumers : AutomatedConsumers {
            perform action a0 { doc /* can reject, warn, or accept data consistently @S166 */ }
        }
        part backupProcessingCluster : BackupProcessingCluster {
            perform action a0 { doc /* receives lower routing preference during normal operations @S066 */ }
            perform action a1 { doc /* supports product generation with the same validation checks and distribution rules @S150 */ }
            perform action a2 { doc /* writes provenance that identifies the fallback execution path @S173 */ }
            perform action a3 { doc /* uses the Storage Watermark Snapshot @S241 */ }
            perform action a4 { doc /* verify that recovery capacity is sufficient @S241 */ }
            perform action a5 { doc /* accepts routine standby responsibility @S241 */ }
            exhibit state modes {
                state s0 { doc /* normal operations @S066 */ }
            }
        }
        part budgetForRealTimeCommandAndTelemetryTraffic : BudgetForRealTimeCommandAndTelemetryTraffic;
        part calibrationAnalysis : CalibrationAnalysis {
            perform action a0 { doc /* identifies an approved update for payload processing behavior @S094 */ }
        }
        part calibrationChange : CalibrationChange {
            perform action a0 { doc /* alters radiometric scale, geometric alignment, or saturation behavior @S164 */ }
        }
        part calibrationImprovements : CalibrationImprovements {
            perform action a0 { doc /* materially change product fitness for use @S192 */ }
        }
        part cataloguePublication : CataloguePublication {
            perform action a0 { doc /* can proceed without exposing internal storage paths @S180 */ }
            perform action a1 { doc /* exposing internal storage paths @S180 */ }
        }
        part catalogueRecords : CatalogueRecords {
            perform action a0 { doc /* show processing baseline, sensing time, publication time, quality status, and replacement relationships for each released product @S197 */ }
        }
        part chainOfCustodyEntry : ChainOfCustodyEntry {
            perform action a0 { doc /* identifies the collector, collection time, source system, and reason for capture @S214 */ }
        }
        part checksumEvidence : ChecksumEvidence;
        part clockBias : ClockBias {
            perform action a0 { doc /* can appear as an apparent measurement error @S071 */ }
        }
        part collisionAssessment : CollisionAssessment {
            perform action a0 { doc /* uses externally supplied conjunction data together with the current covariance @S135 */ }
            perform action a1 { doc /* estimate miss distance, encounter geometry, and probability of collision @S135 */ }
        }
        part commandEngineeringWorkflow : CommandEngineeringWorkflow;
        part commandRequest : CommandRequest {
            exhibit state modes {
                state s0 { doc /* approved authorization state @S242 */ }
            }
        }
        part commandStack : CommandStack {
            perform action a0 { doc /* proceed @S143 */ }
        }
        part commandStackValidation : CommandStackValidation {
            perform action a0 { doc /* checks syntax, timing, parameter ranges, sequencing rules, spacecraft mode compatibility, and consistency with the approved schedule baseline @S120 */ }
        }
        part commandTiming : CommandTiming {
            perform action a0 { doc /* remain consistent @S097 */ }
        }
        part commandValidationGateway : CommandValidationGateway {
            perform action a0 { doc /* provides the formal barrier between planning outputs and command release @S012 */ }
            perform action a1 { doc /* enforces rule checks @S012 */ }
            perform action a2 { doc /* performs independent validation of command stacks @S119 */ }
            perform action a3 { doc /* rejects command stacks that contain unapproved manual edits, missing provenance, expired configuration references, or activities outside the planning authority window @S121 */ }
            perform action a4 { doc /* checks maneuver command parameters against the screened burn plan @S143 */ }
            perform action a5 { doc /* allowing the command stack to proceed @S143 */ }
            perform action a6 { doc /* accepts the mask file @S206 */ }
            perform action a7 { doc /* rejects any command request that lacks the approved authorization state, validation result, and operator acknowledgment required for routine service @S242 */ }
        }
        part commandValidationTimeliness : CommandValidationTimeliness;
        part commandingDiscipline : CommandingDiscipline;
        part configurationIdentifier : ConfigurationIdentifier {
            perform action a0 { doc /* match the active security baseline @S206 */ }
        }
        part consoleDisplays : ConsoleDisplays {
            perform action a0 { doc /* emphasize deviations from expected state rather than raw parameter volume @S083 */ }
        }
        part consoleLead : ConsoleLead {
            perform action a0 { doc /* declaring pass status @S084 */ }
            perform action a1 { doc /* authorizing planned command execution through the Command Validation Gateway @S084 */ }
            perform action a2 { doc /* pausing the activity when telemetry does not match the expected configuration @S084 */ }
        }
        part consoleOperator : ConsoleOperator {
            perform action a0 { doc /* declares an off-nominal condition @S095 */ }
        }
        part constraintChecking : ConstraintChecking {
            perform action a0 { doc /* includes slew time, sun-angle limits, power balance, thermal recovery time, recorder capacity, command load size, and required separation between incompatible activities @S115 */ }
        }
        part contact : Contact {
            perform action a0 { doc /* closes @S090 */ }
        }
        part contactGeometry : ContactGeometry {
            perform action a0 { doc /* could reduce the execution margin for a planned acquisition or downlink @S116 */ }
        }
        part contactSuccessRate : ContactSuccessRate;
        part controlledOperationalActivity : ControlledOperationalActivity;
        part coordinateFrame : CoordinateFrame;
        part correlationRules : CorrelationRules {
            perform action a0 { doc /* emphasize changes that could affect mission continuity, including unexpected route advertisements, repeated authentication failures, unscheduled remote access, and unexplained increases in encrypted traffic volume @S075 */ }
        }
        part cybersecurityDesk : CybersecurityDesk {
            perform action a0 { doc /* provides continuous security monitoring, operational security guidance, and escalation support for events that could affect mission services @S023 */ }
            perform action a1 { doc /* sends a Security Exception Ticket @S074 */ }
            perform action a2 { doc /* coordinate @S076 */ }
            perform action a3 { doc /* blocking traffic @S076 */ }
            perform action a4 { doc /* reviews command preparation exceptions @S125 */ }
            perform action a5 { doc /* reviews public interface changes before deployment @S200 */ }
            perform action a6 { doc /* confirm authentication, logging, and abuse-control requirements are satisfied @S200 */ }
            perform action a7 { doc /* reviews privileged access daily @S204 */ }
            perform action a8 { doc /* challenges dormant, shared, or unexplained accounts @S204 */ }
            perform action a9 { doc /* assumes coordination authority @S212 */ }
            perform action a10 { doc /* participates in the final exercise by validating alert routing, privileged access review, and incident coordination with operations management @S238 */ }
            perform action a11 { doc /* validating alert routing, privileged access review, and incident coordination with operations management @S238 */ }
        }
        part dataDownlinkPriorities : DataDownlinkPriorities {
            perform action a0 { doc /* could affect downstream processing @S093 */ }
        }
        part degradedLinkConditions : DegradedLinkConditions {
            perform action a0 { doc /* could affect command confidence @S085 */ }
        }
        part downlinkAllocationChange : DownlinkAllocationChange {
            perform action a0 { doc /* alters expected processing load or delivery timing @S049 */ }
        }
        part downloadServices : DownloadServices {
            perform action a0 { doc /* support resumable transfer, integrity verification, and rate controls that protect mission operations from excessive external demand @S184 */ }
        }
        part downstreamProcessing : DownstreamProcessing {
            perform action a0 { doc /* can distinguish planned gaps from station-side interruptions @S048 */ }
        }
        part downstreamProcessingFunctions : DownstreamProcessingFunctions;
        part downstreamProcessors : DownstreamProcessors;
        part draftSchedule : DraftSchedule {
            perform action a0 { doc /* covers payload imaging, recorder management, housekeeping activities, and expected support from the North S-Band Antenna and South S-Band Antenna @S108 */ }
            perform action a1 { doc /* accounts for downlink opportunities through the Kiruna X-Band Antenna and Svalbard X-Band Antenna @S109 */ }
        }
        part dynamicOrbitSolutions : DynamicOrbitSolutions {
            exhibit state modes {
                state s0 { doc /* stable @S134 */ }
            }
        }
        part encryptionOverhead : EncryptionOverhead;
        part engineeringAnalysis : EngineeringAnalysis;
        part engineeringTeams : EngineeringTeams {
            perform action a0 { doc /* focus on stabilizing observability and protecting evidence @S218 */ }
            perform action a1 { doc /* stabilizing observability @S218 */ }
            perform action a2 { doc /* protecting evidence @S218 */ }
        }
        part equipmentStatus : EquipmentStatus {
            perform action a0 { doc /* affect a contact @S087 */ }
        }
        part externalInterfaces : ExternalInterfaces {
            perform action a0 { doc /* expose catalogue search, subscription notification, product ordering, and download status using versioned service contracts @S199 */ }
        }
        part externalUsers : ExternalUsers {
            perform action a0 { doc /* can distinguish accepted requests from those still awaiting technical review @S104 */ }
        }
        part firewallInspectionTime : FirewallInspectionTime;
        part firstOperationalReportingCycle : FirstOperationalReportingCycle {
            exhibit state modes {
                state s0 { doc /* stabilization period @S250 */ }
            }
        }
        part flightDynamicsDelivery : FlightDynamicsDelivery;
        part flightDynamicsFacility : FlightDynamicsFacility {
            perform action a0 { doc /* provides orbit analysis, maneuver planning support, access prediction, and navigation products required by other ground functions @S008 */ }
            perform action a1 { doc /* provides visibility predictions and antenna pointing support products to the planning process @S040 */ }
            perform action a2 { doc /* provides orbit predictions and visibility assumptions @S106 */ }
            perform action a3 { doc /* maintains the authoritative orbit catalog for the ground segment @S132 */ }
            perform action a4 { doc /* records the modeling assumptions applied to each accepted solution @S132 */ }
            perform action a5 { doc /* sends the Star Tracker Mask File @S139 */ }
            perform action a6 { doc /* verifying predicted bright-object exclusions against the current attitude plan @S139 */ }
            perform action a7 { doc /* distributes routine ephemerides and event predictions through controlled interfaces used by the Mission Control Center, Mission Planning System, and Payload Processing Facility @S141 */ }
            perform action a8 { doc /* publishes orbit quality state changes to the archive operations queue @S194 */ }
            perform action a9 { doc /* provides readiness evidence showing that orbit products, maneuver screening, and conjunction coordination can be performed within the committed planning cycle @S231 */ }
        }
        part flightDynamicsTeam : FlightDynamicsTeam {
            perform action a0 { doc /* owns flight dynamics analysis, orbit maintenance recommendations, and operational coordination for navigation-related constraints @S021 */ }
            perform action a1 { doc /* monitors timing quality alongside orbit support metrics @S071 */ }
            perform action a2 { doc /* uses tracking measurements and validated time tags from the contact @S088 */ }
            perform action a3 { doc /* support orbit assessment at the Flight Dynamics Facility @S088 */ }
            perform action a4 { doc /* coordinate closely before orbit-control activities @S097 */ }
            perform action a5 { doc /* reviews cases where orbital uncertainty or contact geometry could reduce the execution margin for a planned acquisition or downlink @S116 */ }
            perform action a6 { doc /* uses the residual report @S131 */ }
            perform action a7 { doc /* separate station-related tracking biases from dynamic model errors @S131 */ }
            perform action a8 { doc /* accepting an orbit solution @S131 */ }
            perform action a9 { doc /* computes expected state change, execution tolerance, recovery strategy, and the earliest time when the solution can be declared stable @S134 */ }
            perform action a10 { doc /* maintains screening rules that distinguish routine catalog monitoring from events requiring immediate operator notification @S136 */ }
            perform action a11 { doc /* produces the Ephemeris Delta Note @S144 */ }
            perform action a12 { doc /* assesses orbit and timing effects @S210 */ }
            perform action a13 { doc /* conducts a separate rehearsal for missed tracking data and late orbit update availability @S236 */ }
            perform action a14 { doc /* confirm that planning products remain usable under degraded conditions @S236 */ }
        }
        part forecastIcing : ForecastIcing {
            perform action a0 { doc /* threatens tracking performance @S044 */ }
        }
        part generalRelease : GeneralRelease {
            perform action a0 { doc /* resumes @S164 */ }
        }
        part generationTime : GenerationTime;
        part groundNetworkManagementPractices : GroundNetworkManagementPractices {
            perform action a0 { doc /* emphasize advance coordination, disciplined change approval, continuous monitoring during contacts, and post-contact reconciliation against the approved schedule @S050 */ }
        }
        part groundNetworkManager : GroundNetworkManager {
            perform action a0 { doc /* coordinates availability of the antenna assets @S019 */ }
            perform action a1 { doc /* confirms that scheduled contact opportunities are compatible with station readiness and maintenance constraints @S019 */ }
            perform action a2 { doc /* arbitrates unresolved contact conflicts @S038 */ }
            perform action a3 { doc /* verifies that station commitments remain consistent with maintenance windows and staffing limits @S038 */ }
            perform action a4 { doc /* issues the Antenna Deicing Notice @S044 */ }
            perform action a5 { doc /* determines that a maintenance condition could cause route oscillation @S060 */ }
            perform action a6 { doc /* verifies carrier performance @S067 */ }
            perform action a7 { doc /* checks routing state, packet loss, queue depth, and security inspection delays @S067 */ }
            perform action a8 { doc /* declaring a mission-impacting network condition @S067 */ }
            perform action a9 { doc /* coordinate @S076 */ }
            perform action a10 { doc /* blocking traffic @S076 */ }
            perform action a11 { doc /* confirms that planned station use is compatible with network maintenance windows @S112 */ }
            perform action a12 { doc /* leads triage for antenna, link, and site-service indicators @S209 */ }
            perform action a13 { doc /* accepts the antenna readiness baseline only when the North S-Band Antenna, South S-Band Antenna, Kiruna X-Band Antenna, and Svalbard X-Band Antenna have current maintenance clearances @S234 */ }
        }
        part groundSegment : GroundSegment {
            perform action a0 { doc /* plan spacecraft activities @S002 */ }
            perform action a1 { doc /* acquire mission data @S002 */ }
            perform action a2 { doc /* maintain safe spacecraft operations @S002 */ }
            perform action a3 { doc /* generate user products @S002 */ }
            perform action a4 { doc /* preserve mission records @S002 */ }
            perform action a5 { doc /* provide controlled access to services @S002 */ }
            perform action a6 { doc /* prioritizes spacecraft safety contacts, time-critical telemetry capture, core orbit support, and protection of unrecoverable payload data @S219 */ }
            exhibit state modes {
                state s0 { doc /* essential-service mode @S219 */ }
            }
        }
        part heavyPrecipitation : HeavyPrecipitation {
            perform action a0 { doc /* reduce the link margin below the approved operating threshold @S046 */ }
        }
        part helpDeskResponsiveness : HelpDeskResponsiveness;
        part highWinds : HighWinds {
            perform action a0 { doc /* can still make an antenna unavailable for service @S047 */ }
        }
        part humanAuthorization : HumanAuthorization;
        part immutableStagingStorage : ImmutableStagingStorage;
        part incidentLead : IncidentLead {
            perform action a0 { doc /* approves release @S225 */ }
        }
        part ingestWorkflow : IngestWorkflow {
            perform action a0 { doc /* verifies file size, sequence continuity, checksum, and acquisition time @S152 */ }
        }
        part instrumentMode : InstrumentMode {
            perform action a0 { doc /* is unlikely to meet quality objectives @S124 */ }
        }
        part instrumentModeChanges : InstrumentModeChanges {
            perform action a0 { doc /* could affect downstream processing @S093 */ }
        }
        part integratedDayInTheLifeRehearsal : IntegratedDayInTheLifeRehearsal;
        part integrityCheck : IntegrityCheck {
            perform action a0 { doc /* match the active security baseline @S206 */ }
        }
        part interfaces : Interfaces;
        part kirunaXBandAntenna : KirunaXBandAntenna {
            perform action a0 { doc /* use dual wide area paths toward the Payload Processing Facility @S055 */ }
            perform action a1 { doc /* support high-rate telemetry reception when the visibility geometry and data volume justify their use @S078 */ }
        }
        part label : Label;
        part lateOperationalRequests : LateOperationalRequests {
            perform action a0 { doc /* affect spacecraft attitude, thermal margin, stored command capacity, or contact preparation @S105 */ }
        }
        part lateOrUnevenDelivery : LateOrUnevenDelivery {
            perform action a0 { doc /* can reduce the usefulness of contact assessment products @S064 */ }
        }
        part laterProcessing : LaterProcessing {
            perform action a0 { doc /* can reproduce the operational context @S149 */ }
        }
        part level1AProcessing : Level1AProcessing {
            perform action a0 { doc /* reconstructs detector samples @S156 */ }
            perform action a1 { doc /* appends engineering context @S156 */ }
        }
        part level1BProcessing : Level1BProcessing {
            perform action a0 { doc /* applies radiometric calibration and sensor model parameters @S156 */ }
        }
        part level2Processing : Level2Processing {
            perform action a0 { doc /* applies geolocation, atmospheric screening where applicable, and gridding rules defined in the active product specification @S157 */ }
        }
        part liveMonitoringPeriod : LiveMonitoringPeriod;
        part localConstraints : LocalConstraints {
            perform action a0 { doc /* could affect an approved contact @S043 */ }
        }
        part localInfrastructure : LocalInfrastructure {
            perform action a0 { doc /* permits @S053 */ }
        }
        part localStationTeams : LocalStationTeams {
            perform action a0 { doc /* are responsible for antenna pre-pass configuration, frequency standard verification, time correlation checks, safety interlocks, and logging of any local anomalies @S042 */ }
            perform action a1 { doc /* logging of any local anomalies @S042 */ }
        }
        part longTermArchive : LongTermArchive {
            perform action a0 { doc /* retains released orbit products, covariance data, maneuver records, and quality decisions @S149 */ }
            perform action a1 { doc /* sends the Storage Watermark Snapshot @S174 */ }
            perform action a2 { doc /* stores object content separately from searchable metadata @S180 */ }
            perform action a3 { doc /* retains raw acquisition data for the life of the mission and for the post-mission preservation period defined in the archive policy @S187 */ }
            perform action a4 { doc /* preserves the replaced product version @S196 */ }
            perform action a5 { doc /* cannot meet a restore or publication commitment @S201 */ }
            perform action a6 { doc /* preserves the accepted archive baseline @S243 */ }
            perform action a7 { doc /* confirms that retrieval tests meet the service objective @S243 */ }
        }
        part maintenanceCondition : MaintenanceCondition {
            perform action a0 { doc /* could cause route oscillation @S060 */ }
        }
        part mandatoryChecks : MandatoryChecks {
            perform action a0 { doc /* fail @S167 */ }
        }
        part maneuverRecommendationPackage : ManeuverRecommendationPackage;
        part maneuverScreening : ManeuverScreening {
            perform action a0 { doc /* evaluates orbit maintenance options against fuel use, ground contact visibility, payload outage constraints, and post-burn tracking opportunities @S133 */ }
        }
        part measuredBuildup : MeasuredBuildup {
            perform action a0 { doc /* threatens tracking performance @S044 */ }
        }
        part measurements : Measurements {
            perform action a0 { doc /* meet quality and timing criteria @S129 */ }
        }
        part metadata : Metadata {
            perform action a0 { doc /* distinguish operational output from test output and reprocessed output @S160 */ }
        }
        part missionControlCenter : MissionControlCenter {
            perform action a0 { doc /* maintains the operational contact schedule @S032 */ }
            perform action a1 { doc /* uses it as the controlling reference for console staffing, command readiness, and telemetry coverage @S032 */ }
            perform action a2 { doc /* hosts the primary routing policy point @S056 */ }
            perform action a3 { doc /* treats every scheduled contact as a controlled operational activity with a defined readiness check, live monitoring period, and post-pass closure step @S077 */ }
            perform action a4 { doc /* coordinates with the Payload Processing Facility @S093 */ }
            perform action a5 { doc /* begins with the console lead @S096 */ }
            perform action a6 { doc /* moves to the responsible discipline lead @S096 */ }
            perform action a7 { doc /* reaches mission management @S096 */ }
            perform action a8 { doc /* records unresolved actions, open engineering questions, and expected specialist responses @S100 */ }
            perform action a9 { doc /* requires that each flight dynamics delivery include a validity interval, coordinate frame, generation time, and operational use statement @S140 */ }
            perform action a10 { doc /* maintains the authority boundary for routine spacecraft operations @S203 */ }
            perform action a11 { doc /* confirms that elevated access is tied to an approved shift role and a time-limited operational need @S203 */ }
            perform action a12 { doc /* are declared by the Mission Control Center after consultation with the affected technical leads @S217 */ }
            perform action a13 { doc /* demonstrates continuous console coverage for the agreed service hours @S230 */ }
            perform action a14 { doc /* proves that shift handover logs contain the state needed by the incoming controller @S230 */ }
        }
        part missionControlCenterConsoles : MissionControlCenterConsoles;
        part missionManagement : MissionManagement {
            perform action a0 { doc /* approves a different backlog rule @S176 */ }
        }
        part missionPlanning : MissionPlanning {
            perform action a0 { doc /* begins @S101 */ }
        }
        part missionPlanningSystem : MissionPlanningSystem {
            perform action a0 { doc /* converts approved imaging demand and spacecraft constraints into executable activity plans for routine operations @S011 */ }
            perform action a1 { doc /* receives operational constraints from mission control @S099 */ }
            perform action a2 { doc /* assembling candidate observation timelines and associated ground contact activities @S102 */ }
            perform action a3 { doc /* combines request priority, instrument availability, contact opportunities, onboard storage margin, and downlink capacity into a draft activity schedule @S107 */ }
            perform action a4 { doc /* flags conflicts when two activities compete for the same spacecraft resource, ground station resource, or operational staffing interval @S114 */ }
            perform action a5 { doc /* exports a command preparation package to the command engineering workflow at the Mission Control Center @S118 */ }
            perform action a6 { doc /* uses accepted orbit files @S142 */ }
            perform action a7 { doc /* align imaging requests, contact opportunities, recorder margins, and downlink windows @S142 */ }
            perform action a8 { doc /* treats the retroreflector window as a constrained planning input @S207 */ }
            perform action a9 { doc /* prevents its use outside the approved scheduling interval @S207 */ }
            perform action a10 { doc /* suspends automatic schedule publication @S216 */ }
            perform action a11 { doc /* applies the delta note during schedule validation @S240 */ }
            perform action a12 { doc /* ensure that contact and activity timing remains consistent with the latest operational constraint @S240 */ }
        }
        part monitoredEvent : MonitoredEvent {
            perform action a0 { doc /* requires temporary deviation from the approved security baseline @S074 */ }
        }
        part navigationProducts : NavigationProducts;
        part networkControlSystem : NetworkControlSystem {
            perform action a0 { doc /* monitors communications availability @S010 */ }
            perform action a1 { doc /* routes operational traffic @S010 */ }
            perform action a2 { doc /* provides status awareness for ground connectivity supporting the mission @S010 */ }
            perform action a3 { doc /* distributes station allocations @S033 */ }
            perform action a4 { doc /* confirms antenna readiness states @S033 */ }
            perform action a5 { doc /* records the actual start and end times of each contact @S033 */ }
            perform action a6 { doc /* maintains operational visibility of circuit state, path selection, and active maintenance windows @S056 */ }
            perform action a7 { doc /* confirms that the alarm is not caused by a known maintenance interval or a failed local reference check @S072 */ }
            perform action a8 { doc /* provides the Mission Control Center with antenna status, link configuration, timing references, and routing readiness @S079 */ }
            perform action a9 { doc /* uses antenna pointing predictions derived from the accepted ephemeris @S148 */ }
            perform action a10 { doc /* prepare scheduled contacts @S148 */ }
            perform action a11 { doc /* verify tracking readiness @S148 */ }
            perform action a12 { doc /* uses the Security Exception Ticket @S170 */ }
            perform action a13 { doc /* restrict affected transfer paths @S170 */ }
            perform action a14 { doc /* preserve the last validated routing configuration @S171 */ }
            perform action a15 { doc /* reject unreviewed changes @S171 */ }
            perform action a16 { doc /* enforces approved routing paths between ground stations, processing services, and external interfaces @S205 */ }
            perform action a17 { doc /* records configuration changes in the operational log @S205 */ }
            perform action a18 { doc /* records rehearsal outcomes for planned maintenance, station loss, degraded routing, and restoration of nominal connectivity after a simulated outage @S233 */ }
            exhibit state modes {
                state s0 { doc /* degraded routing @S233 */ }
                state s1 { doc /* nominal connectivity @S233 */ }
            }
        }
        part northSBandAntenna : NorthSBandAntenna {
            perform action a0 { doc /* provides the nominal early-pass command uplink and low-rate telemetry return for contacts that require conservative link margins @S028 */ }
            perform action a1 { doc /* connect to the Mission Control Center through protected access routers @S054 */ }
        }
        part nullPart : Null {
            perform action a0 { doc /* are rate limited during active contacts @S065 */ }
            perform action a1 { doc /* cannot starve operational telemetry or control-plane monitoring @S065 */ }
            perform action a2 { doc /* are tested routinely @S066 */ }
            perform action a3 { doc /* does not expose stale firewall rules or asymmetric return routes @S066 */ }
            perform action a4 { doc /* is exceeded @S067 */ }
            perform action a5 { doc /* is provided from redundant reference clocks at the Mission Control Center and the Flight Dynamics Facility @S068 */ }
            perform action a6 { doc /* sized to cover credible external timing outages @S068 */ }
            perform action a7 { doc /* cover credible external timing outages @S068 */ }
            perform action a8 { doc /* is used inside data centers and processing enclaves @S069 */ }
            perform action a9 { doc /* is required for correlation @S069 */ }
            perform action a10 { doc /* is used for general server and workstation timekeeping @S069 */ }
            perform action a11 { doc /* is not separated from actual tracking performance @S071 */ }
            perform action a12 { doc /* are forwarded to the Spacecraft Operations Team @S072 */ }
            perform action a13 { doc /* is not caused by a known maintenance interval or a failed local reference check @S072 */ }
            perform action a14 { doc /* is applied at each site through network sensors, endpoint telemetry, privileged-access logging, and configuration compliance checks @S073 */ }
            perform action a15 { doc /* are reviewed during every operational shift @S073 */ }
            perform action a16 { doc /* could affect mission continuity @S075 */ }
            perform action a17 { doc /* is stored in write-protected case storage with a chain of custody entry @S214 */ }
            perform action a18 { doc /* cannot be proven during an active anomaly investigation @S215 */ }
            perform action a19 { doc /* are recorded with the operational objective, expected duration, and exit criteria @S217 */ }
            perform action a20 { doc /* is stopped @S218 */ }
            perform action a21 { doc /* is transferred to Backup Processing Cluster @S221 */ }
            perform action a22 { doc /* have been verified @S221 */ }
            perform action a23 { doc /* is coordinated through Ground Network Manager @S222 */ }
            perform action a24 { doc /* are placed in the recovery plan according to current availability and the spacecraft contact priority @S223 */ }
            perform action a25 { doc /* is reconciled @S224 */ }
            perform action a26 { doc /* is restored @S224 */ }
            perform action a27 { doc /* is accepted @S226 */ }
            perform action a28 { doc /* is verified @S226 */ }
            perform action a29 { doc /* are reconciled @S226 */ }
            exhibit state modes {
                state s0 { doc /* contingency operations @S076 */ }
                state s1 { doc /* monitor-only mode @S218 */ }
                state s2 { doc /* normal service status @S224 */ }
            }
        }
        part observationRequests : ObservationRequests {
            perform action a0 { doc /* arrive through the User Services Portal or from internal operations channels at the Mission Control Center @S101 */ }
            perform action a1 { doc /* awaiting technical review @S104 */ }
            exhibit state modes {
                state s0 { doc /* accepted @S104 */ }
                state s1 { doc /* awaiting technical review @S104 */ }
            }
        }
        part onboardEvent : OnboardEvent {
            perform action a0 { doc /* occurred outside the timeline @S091 */ }
        }
        part operationalImpacts : OperationalImpacts;
        part operationalKeyPerformanceIndicators : OperationalKeyPerformanceIndicators {
            perform action a0 { doc /* moves outside the watch band @S246 */ }
        }
        part operationalReadinessReview : OperationalReadinessReview {
            perform action a0 { doc /* confirms that ground procedures, staffing rosters, monitoring views, and escalation paths are under configuration control @S227 */ }
        }
        part operationalUseStatement : OperationalUseStatement;
        part operations : Operations;
        part operationsCrew : OperationsCrew {
            perform action a0 { doc /* can maintain continuity without relying on informal handover @S100 */ }
        }
        part operationsStaff : OperationsStaff {
            perform action a0 { doc /* open the normal incident process @S201 */ }
        }
        part operationsUsers : OperationsUsers {
            perform action a0 { doc /* work from a common predicted trajectory @S127 */ }
        }
        part operator : Operator {
            perform action a0 { doc /* opens a blocking review @S167 */ }
        }
        part operatorApprovalState : OperatorApprovalState {
            perform action a0 { doc /* match the active security baseline @S206 */ }
        }
        part operatorDisplay : OperatorDisplay {
            perform action a0 { doc /* shows whether recovery, retransmission, or discard is required @S154 */ }
        }
        part operatorDisplays : OperatorDisplays {
            perform action a0 { doc /* remain comparable across locations @S070 */ }
        }
        part operators : Operators {
            perform action a0 { doc /* must identify safety trends while a contact is still available @S083 */ }
            perform action a1 { doc /* preserve the command state @S098 */ }
            perform action a2 { doc /* avoid discretionary commanding @S098 */ }
            perform action a3 { doc /* request specialist review @S098 */ }
            perform action a4 { doc /* changing spacecraft configuration @S098 */ }
            perform action a5 { doc /* preserve volatile logs, current configuration state, operator console history, and relevant message identifiers @S213 */ }
            perform action a6 { doc /* restarting services @S213 */ }
            perform action a7 { doc /* changing routing @S213 */ }
        }
        part orbitDeterminationEngine : OrbitDeterminationEngine {
            perform action a0 { doc /* supports routine orbit maintenance @S014 */ }
            perform action a1 { doc /* processing tracking inputs @S014 */ }
            perform action a2 { doc /* producing controlled orbit knowledge for planning and product generation @S014 */ }
            perform action a3 { doc /* produces the Doppler Residual Report after each qualified tracking pass @S041 */ }
            perform action a4 { doc /* support navigation trend assessment @S041 */ }
            perform action a5 { doc /* supports routine state updates @S089 */ }
            perform action a6 { doc /* provides the basis for predicting future visibility periods, maneuver planning constraints, and antenna pointing expectations @S089 */ }
            perform action a7 { doc /* provides the current orbital solution used to confirm time-tagged events, contact visibility, and any attitude-dependent observation geometry @S123 */ }
            perform action a8 { doc /* fits dynamic orbit solutions using radiometric tracking, spacecraft telemetry timing, force models, and the latest approved maneuver history @S128 */ }
            perform action a9 { doc /* using radiometric tracking, spacecraft telemetry timing, force models, and the latest approved maneuver history @S128 */ }
            perform action a10 { doc /* produces the Laser Retroreflector Window from the refined orbit solution and the approved station geometry constraints @S145 */ }
        }
        part orbitGeometry : OrbitGeometry {
            perform action a0 { doc /* gives longer visibility or lower elevation loss @S031 */ }
        }
        part orbitUpdates : OrbitUpdates {
            perform action a0 { doc /* materially change product fitness for use @S192 */ }
        }
        part orbitalUncertainty : OrbitalUncertainty {
            perform action a0 { doc /* could reduce the execution margin for a planned acquisition or downlink @S116 */ }
        }
        part otherGroundFunctions : OtherGroundFunctions;
        part pass : Pass {
            perform action a0 { doc /* begins @S079 */ }
        }
        part passPreparation : PassPreparation;
        part passReconstruction : PassReconstruction {
            perform action a0 { doc /* begins @S090 */ }
            perform action a1 { doc /* combines command history, received telemetry timing, ground station status, and operator log entries into a single operational narrative @S090 */ }
        }
        part payloadCalibrationTeam : PayloadCalibrationTeam {
            perform action a0 { doc /* owns payload performance monitoring, calibration parameter stewardship, and the technical assessment of product quality trends @S022 */ }
            perform action a1 { doc /* sends the Calibration Patch Bundle @S094 */ }
            perform action a2 { doc /* reviews planned calibration activities when they share resources with revenue observations or affect instrument configuration states @S117 */ }
            perform action a3 { doc /* obtains predicted viewing geometry from flight dynamics products @S147 */ }
            perform action a4 { doc /* interpret instrument trends @S147 */ }
            perform action a5 { doc /* plan calibration activities @S147 */ }
            perform action a6 { doc /* maintains the approved calibration baseline @S161 */ }
            perform action a7 { doc /* reviews trend evidence @S161 */ }
            perform action a8 { doc /* may request a reprocessing campaign when validation evidence shows a systematic radiometric or geometric issue @S193 */ }
            perform action a9 { doc /* assesses product integrity @S211 */ }
            perform action a10 { doc /* validates that calibration operations are represented in the rehearsal schedule and that product quality decisions can be traced to approved engineering criteria @S237 */ }
        }
        part payloadDownlinkTraffic : PayloadDownlinkTraffic {
            perform action a0 { doc /* can continue during a single carrier outage @S055 */ }
        }
        part payloadProcessingFacility : PayloadProcessingFacility {
            perform action a0 { doc /* provides the operational environment for payload data processing, calibration control, product assessment, and distribution staging @S009 */ }
            perform action a1 { doc /* coordinates with Primary Processing Cluster and Backup Processing Cluster @S049 */ }
            perform action a2 { doc /* receives planning metadata needed to prepare downstream processing expectations @S110 */ }
            perform action a3 { doc /* prepare downstream processing expectations @S110 */ }
            perform action a4 { doc /* without treating the planning schedule as a commitment to deliver products @S110 */ }
            perform action a5 { doc /* deliver products @S110 */ }
            perform action a6 { doc /* transforming downlinked payload telemetry into image products that are traceable to the source telemetry and to the processing configuration used at execution time @S151 */ }
            perform action a7 { doc /* has delivered the product package, associated quality metadata, and checksum evidence required by the configured acceptance rule @S178 */ }
            perform action a8 { doc /* quarantine suspect input and derived output @S215 */ }
            perform action a9 { doc /* demonstrates that science product generation can be sustained during representative contact patterns without manual intervention beyond approved operator actions @S232 */ }
        }
        part physicalTopology : PhysicalTopology {
            perform action a0 { doc /* uses redundant terrestrial circuits between the Mission Control Center, the Flight Dynamics Facility, the Payload Processing Facility, and the Long Term Archive, with diverse carrier entrances where local infrastructure permits @S053 */ }
        }
        part plannedCalibrationActivities : PlannedCalibrationActivities {
            perform action a0 { doc /* share resources with revenue observations @S117 */ }
            perform action a1 { doc /* affect instrument configuration states @S117 */ }
        }
        part plannedSupport : PlannedSupport {
            perform action a0 { doc /* can proceed without adding contingency contact margin @S113 */ }
        }
        part planningCycle : PlanningCycle {
            perform action a0 { doc /* uses to determine feasible imaging windows and ground contacts @S106 */ }
            perform action a1 { doc /* determine feasible imaging windows and ground contacts @S106 */ }
        }
        part planningProcess : PlanningProcess;
        part postBurnAssessmentSteps : PostBurnAssessmentSteps {
            perform action a0 { doc /* remain consistent @S097 */ }
        }
        part postPassClosureStep : PostPassClosureStep;
        part previousAcquisitions : PreviousAcquisitions {
            perform action a0 { doc /* indicate that a requested geometry or instrument mode is unlikely to meet quality objectives @S124 */ }
        }
        part primaryMonthlyServiceReview : PrimaryMonthlyServiceReview {
            perform action a0 { doc /* compares actual performance against the accepted baseline @S246 */ }
            perform action a1 { doc /* records trend explanations for any measure that moves outside the watch band @S246 */ }
        }
        part primaryProcessingCluster : PrimaryProcessingCluster {
            perform action a0 { doc /* Transfers from the Primary Processing Cluster to the Long Term Archive @S065 */ }
            perform action a1 { doc /* generates Level 0 products @S155 */ }
            perform action a2 { doc /* removing transfer framing @S155 */ }
            perform action a3 { doc /* ordering source packets @S155 */ }
            perform action a4 { doc /* preserving instrument time tags without radiometric or geometric correction @S155 */ }
            perform action a5 { doc /* cannot meet the processing window @S172 */ }
            perform action a6 { doc /* can pause nonessential production queues @S220 */ }
            perform action a7 { doc /* reserve compute capacity for validated recovery runs from known-good inputs @S220 */ }
            exhibit state modes {
                state s0 { doc /* unavailable @S150 */ }
            }
        }
        part primaryRoutingPolicyPoint : PrimaryRoutingPolicyPoint;
        part processingLevel : ProcessingLevel {
            perform action a0 { doc /* records software build identifiers, calibration baseline identifiers, and ancillary input versions @S158 */ }
        }
        part processorCorrections : ProcessorCorrections {
            perform action a0 { doc /* materially change product fitness for use @S192 */ }
        }
        part product : Product {
            exhibit state modes {
                state s0 { doc /* delivery hold state @S167 */ }
            }
        }
        part productLatency : ProductLatency;
        part productQualityDispositionTime : ProductQualityDispositionTime;
        part productQualityService : ProductQualityService {
            perform action a0 { doc /* performs automated and analyst-supported checks on generated products @S015 */ }
            perform action a1 { doc /* may add planning feedback when previous acquisitions indicate that a requested geometry or instrument mode is unlikely to meet quality objectives @S124 */ }
            perform action a2 { doc /* checks each orbit solution for frame consistency, covariance reasonableness, time-tag continuity, and agreement with recent contact predictions @S130 */ }
            perform action a3 { doc /* uses the patch bundle @S162 */ }
            perform action a4 { doc /* update calibration applicability checks @S162 */ }
            perform action a5 { doc /* assigns quality flags for missing source packets, timing discontinuity, saturation, cloud screening uncertainty, geolocation residuals, and processing fallback @S165 */ }
            perform action a6 { doc /* produces the Product Hold List @S168 */ }
            perform action a7 { doc /* treats that marker as an input to its quality decision @S173 */ }
            perform action a8 { doc /* has set the public quality status @S181 */ }
            perform action a9 { doc /* records the reason for any reprocessing decision @S195 */ }
        }
        part products : Products {
            exhibit state modes {
                state s0 { doc /* operational review @S182 */ }
            }
        }
        part protectedAccessRouters : ProtectedAccessRouters {
            perform action a0 { doc /* keep command and telemetry traffic separate from site administration traffic @S054 */ }
        }
        part protectiveActions : ProtectiveActions {
            perform action a0 { doc /* do not unintentionally interrupt a spacecraft contact @S076 */ }
            perform action a1 { doc /* prevent recovery of processing services @S076 */ }
        }
        part provenance : Provenance {
            perform action a0 { doc /* identifies the fallback execution path @S173 */ }
        }
        part qualityInvestigations : QualityInvestigations {
            perform action a0 { doc /* materially change product fitness for use @S192 */ }
        }
        part rateControls : RateControls {
            perform action a0 { doc /* protect mission operations from excessive external demand @S184 */ }
        }
        part rawTransfer : RawTransfer {
            perform action a0 { doc /* starts @S152 */ }
        }
        part readinessCheck : ReadinessCheck;
        part readinessReviewBoard : ReadinessReviewBoard {
            perform action a0 { doc /* verifies that each open action from launch and commissioning has an owner, a due date, and an accepted residual risk statement where closure is not required before service start @S228 */ }
        }
        part receivedStream : ReceivedStream;
        part receptionGaps : ReceptionGaps {
            perform action a0 { doc /* could affect downstream processing @S093 */ }
        }
        part recovery : Recovery {
            perform action a0 { doc /* prioritizes products with contractual latency commitments @S176 */ }
            perform action a1 { doc /* processes remaining scenes in acquisition order unless mission management approves a different backlog rule @S176 */ }
        }
        part recoveryReporting : RecoveryReporting;
        part redundantCapabilities : RedundantCapabilities {
            perform action a0 { doc /* can support the required mission service levels @S026 */ }
        }
        part referenceClocks : ReferenceClocks;
        part registeredUsers : RegisteredUsers {
            perform action a0 { doc /* receive authorization scopes based on mission policy, contractual access rights, and applicable data licensing constraints @S185 */ }
        }
        part rehearsals : Rehearsals {
            perform action a0 { doc /* meet their objectives @S249 */ }
        }
        part releaseBlockingDefects : ReleaseBlockingDefects;
        part requestedGeometry : RequestedGeometry {
            perform action a0 { doc /* is unlikely to meet quality objectives @S124 */ }
        }
        part responsibleTeams : ResponsibleTeams {
            perform action a0 { doc /* have signed the incident record @S226 */ }
        }
        part retentionExceptions : RetentionExceptions {
            perform action a0 { doc /* require traceability to the approving authority, the affected product classes, and the expected operational impact @S191 */ }
        }
        part routineMissionService : RoutineMissionService {
            perform action a0 { doc /* begins @S227 */ }
        }
        part routineOperations : RoutineOperations {
            exhibit state modes {
                state s0 { doc /* stable @S243 */ }
            }
        }
        part routineProduction : RoutineProduction {
            perform action a0 { doc /* has completed @S177 */ }
        }
        part routineReporting : RoutineReporting {
            perform action a0 { doc /* does not depend on informal judgment @S245 */ }
        }
        part routingIssues : RoutingIssues {
            perform action a0 { doc /* affect a contact @S087 */ }
        }
        part schedulingService : SchedulingService {
            perform action a0 { doc /* assigns eligible jobs to the Backup Processing Cluster using the same container image and rule set @S172 */ }
            perform action a1 { doc /* using the same container image and rule set @S172 */ }
        }
        part screeningRules : ScreeningRules {
            perform action a0 { doc /* distinguish routine catalog monitoring from events requiring immediate operator notification @S136 */ }
        }
        part securityMonitoring : SecurityMonitoring {
            perform action a0 { doc /* has returned to the approved baseline @S226 */ }
        }
        part securityOrContinuityAnomaly : SecurityOrContinuityAnomaly {
            perform action a0 { doc /* could invalidate contact commitments @S216 */ }
            perform action a1 { doc /* conflict with manual recovery actions @S216 */ }
        }
        part sentinelVale : SentinelVale {
            perform action a0 { doc /* provide routine land, coastal, and cryosphere imaging products with predictable latency and documented data quality @S001 */ }
        }
        part southSBandAntenna : SouthSBandAntenna {
            perform action a0 { doc /* provides the alternate S-band path @S029 */ }
            perform action a1 { doc /* connect to the Mission Control Center through protected access routers @S054 */ }
        }
        part spacecraftConfigurationChanges : SpacecraftConfigurationChanges {
            perform action a0 { doc /* require adjustment of future contacts or payload activities @S099 */ }
        }
        part spacecraftOperationsTeam : SpacecraftOperationsTeam {
            perform action a0 { doc /* owns spacecraft safety execution, contact conduct, command authorization support, and operational decision making during nominal and contingency conditions @S020 */ }
            perform action a1 { doc /* monitors spacecraft mode, power state, thermal margins, attitude indicators, command counters, onboard storage, and fault protection messages from the Mission Control Center consoles @S082 */ }
            perform action a2 { doc /* coordinate closely before orbit-control activities @S097 */ }
            perform action a3 { doc /* reviews late operational requests @S105 */ }
            perform action a4 { doc /* uses the Antenna Deicing Notice to assess whether planned support can proceed without adding contingency contact margin @S113 */ }
            perform action a5 { doc /* assess whether planned support can proceed without adding contingency contact margin @S113 */ }
            perform action a6 { doc /* receives a maneuver recommendation package that includes timing constraints and operational impacts @S137 */ }
            perform action a7 { doc /* receives maneuver recommendations with enough lead time to rehearse commanding, verify contingency actions, and coordinate contact coverage @S146 */ }
            perform action a8 { doc /* rehearse commanding @S146 */ }
            perform action a9 { doc /* verify contingency actions @S146 */ }
            perform action a10 { doc /* coordinate contact coverage @S146 */ }
            perform action a11 { doc /* uses the Pass Replay Packet @S198 */ }
            perform action a12 { doc /* confirm that archived downlink context can support anomaly reconstruction @S198 */ }
            perform action a13 { doc /* leads triage for spacecraft safety indicators @S209 */ }
            perform action a14 { doc /* conducts at least one integrated day-in-the-life rehearsal that includes pass preparation, commanding discipline, telemetry surveillance, anomaly declaration, and recovery reporting @S235 */ }
        }
        part spacecraftSystemsEngineer : SpacecraftSystemsEngineer {
            perform action a0 { doc /* interprets health telemetry @S086 */ }
            perform action a1 { doc /* confirms that subsystem states remain within flight rules @S086 */ }
            perform action a2 { doc /* records any anomaly context needed by subsystem specialists @S086 */ }
        }
        part stationDeliveryFiles : StationDeliveryFiles {
            perform action a0 { doc /* arrive with an accompanying manifest @S152 */ }
        }
        part stationOperators : StationOperators {
            perform action a0 { doc /* notify the Mission Control Center when local constraints could affect an approved contact, including equipment warm-up limits, access restrictions, or unexpected maintenance activity @S043 */ }
        }
        part stationOutages : StationOutages {
            perform action a0 { doc /* require adjustment of future contacts or payload activities @S099 */ }
        }
        part subsystemSpecialists : SubsystemSpecialists {
            perform action a0 { doc /* are not expected to staff every live contact @S095 */ }
            perform action a1 { doc /* must be reachable during planned critical activities and whenever a console operator declares an off-nominal condition @S095 */ }
            exhibit state modes {
                state s0 { doc /* reachable @S095 */ }
            }
        }
        part supportTeams : SupportTeams {
            perform action a0 { doc /* confirm on-call coverage @S249 */ }
        }
        part svalbardXBandAntenna : SvalbardXBandAntenna {
            perform action a0 { doc /* extends northern contact opportunities @S031 */ }
            perform action a1 { doc /* use dual wide area paths toward the Payload Processing Facility @S055 */ }
            perform action a2 { doc /* support high-rate telemetry reception when the visibility geometry and data volume justify their use @S078 */ }
        }
        part telemetry : Telemetry {
            perform action a0 { doc /* indicates a possible onboard fault @S098 */ }
        }
        part telemetryCompleteness : TelemetryCompleteness;
        part telemetryEngineer : TelemetryEngineer {
            perform action a0 { doc /* verifies reception quality, frame loss, latency, and stream continuity @S085 */ }
            perform action a1 { doc /* advises the console lead when degraded link conditions could affect command confidence @S085 */ }
        }
        part telemetryFrames : TelemetryFrames {
            perform action a0 { doc /* remain comparable across locations @S070 */ }
        }
        part telemetryIngestService : TelemetryIngestService {
            perform action a0 { doc /* receives spacecraft telemetry from scheduled contacts @S013 */ }
            perform action a1 { doc /* makes it available to operations, engineering analysis, and downstream processing functions @S013 */ }
            perform action a2 { doc /* receives contact status and data-flow indicators @S048 */ }
            perform action a3 { doc /* accepts real-time frames @S080 */ }
            perform action a4 { doc /* validates basic framing and time continuity @S080 */ }
            perform action a5 { doc /* records reception metadata needed for later operational review @S080 */ }
            perform action a6 { doc /* produces the Pass Replay Packet @S081 */ }
            perform action a7 { doc /* writes accepted raw data to immutable staging storage @S153 */ }
            perform action a8 { doc /* records the session identifier used by downstream processors @S153 */ }
        }
        part telemetryReception : TelemetryReception {
            perform action a0 { doc /* continues where safe @S218 */ }
        }
        part telemetrySurveillance : TelemetrySurveillance;
        part timingConstraints : TimingConstraints;
        part trackingArcs : TrackingArcs;
        part trackingExpectations : TrackingExpectations {
            perform action a0 { doc /* remain consistent @S097 */ }
        }
        part trackingRecords : TrackingRecords {
            perform action a0 { doc /* remain comparable across locations @S070 */ }
        }
        part trafficSupportingTheOrbitDeterminationEngine : TrafficSupportingTheOrbitDeterminationEngine {
            perform action a0 { doc /* supporting the Orbit Determination Engine @S064 */ }
        }
        part unresolvedAnomalyAge : UnresolvedAnomalyAge;
        part unsafeOutdoorConditions : UnsafeOutdoorConditions {
            perform action a0 { doc /* can still make an antenna unavailable for service @S047 */ }
        }
        part updatedStateVectors : UpdatedStateVectors {
            perform action a0 { doc /* change predicted acquisition times or imaging geometry beyond agreed thresholds @S144 */ }
        }
        part userServicesPortal : UserServicesPortal {
            perform action a0 { doc /* provides the controlled external interface for product search, ordering, status communication, and user support workflows @S018 */ }
            perform action a1 { doc /* records the request state @S104 */ }
            perform action a2 { doc /* provides search, preview, order, and download functions through a browser interface and documented machine interfaces @S183 */ }
            perform action a3 { doc /* displays a service status message @S201 */ }
            perform action a4 { doc /* communicates confirmed service impacts in operational terms @S225 */ }
            perform action a5 { doc /* avoids publishing speculative root cause information before the incident lead approves release @S225 */ }
            perform action a6 { doc /* publishing speculative root cause information @S225 */ }
            perform action a7 { doc /* uses the Product Hold List @S239 */ }
            perform action a8 { doc /* prevent release of affected products until the applicable hold condition has been cleared @S239 */ }
        }
        part users : Users {
            perform action a0 { doc /* can distinguish scientific updates from operational recovery actions @S195 */ }
        }
        part validationEvidence : ValidationEvidence {
            perform action a0 { doc /* shows a systematic radiometric or geometric issue @S193 */ }
        }
        part validityInterval : ValidityInterval;
        part weather : Weather {
            perform action a0 { doc /* affect a contact @S087 */ }
        }
        part wideAreaConnectivityDesign : WideAreaConnectivityDesign {
            perform action a0 { doc /* extends the ground network management practices from the scheduling domain into continuous transport control across all operational sites @S052 */ }
        }
        flow f0 of NavigationProductsItem from flightDynamicsFacility to otherGroundFunctions { doc /* @S008 */ }
        flow f1 of SpacecraftTelemetryItem from telemetryIngestService to operations { doc /* @S013 */ }
        flow f2 of SpacecraftTelemetryItem from telemetryIngestService to engineeringAnalysis { doc /* @S013 */ }
        flow f3 of SpacecraftTelemetryItem from telemetryIngestService to downstreamProcessingFunctions { doc /* @S013 */ }
        flow f4 of VisibilityPredictionsItem from flightDynamicsFacility to planningProcess { doc /* @S040 */ }
        flow f5 of AntennaPointingSupportProductsItem from flightDynamicsFacility to planningProcess { doc /* @S040 */ }
        flow f6 of LocalConstraintsItem from stationOperators to missionControlCenter { doc /* @S043 */ }
        flow f7 of NullItem from primaryProcessingCluster to longTermArchive { doc /* @S065 */ }
        flow f8 of TimeSynchronizationItem from referenceClocks to nullPart { doc /* @S068 */ }
        flow f9 of TimingAlarmsItem from nullPart to spacecraftOperationsTeam { doc /* @S072 */ }
        flow f10 of SecurityExceptionTicketItem from cybersecurityDesk to nullPart { doc /* @S074 */ }
        flow f11 of AntennaStatusItem from networkControlSystem to missionControlCenter { doc /* @S079 */ }
        flow f12 of LinkConfigurationItem from networkControlSystem to missionControlCenter { doc /* @S079 */ }
        flow f13 of TimingReferencesItem from networkControlSystem to missionControlCenter { doc /* @S079 */ }
        flow f14 of RoutingReadinessItem from networkControlSystem to missionControlCenter { doc /* @S079 */ }
        flow f15 of SpacecraftModeItem from missionControlCenterConsoles to spacecraftOperationsTeam { doc /* @S082 */ }
        flow f16 of PowerStateItem from missionControlCenterConsoles to spacecraftOperationsTeam { doc /* @S082 */ }
        flow f17 of ThermalMarginsItem from missionControlCenterConsoles to spacecraftOperationsTeam { doc /* @S082 */ }
        flow f18 of AttitudeIndicatorsItem from missionControlCenterConsoles to spacecraftOperationsTeam { doc /* @S082 */ }
        flow f19 of CommandCountersItem from missionControlCenterConsoles to spacecraftOperationsTeam { doc /* @S082 */ }
        flow f20 of OnboardStorageItem from missionControlCenterConsoles to spacecraftOperationsTeam { doc /* @S082 */ }
        flow f21 of FaultProtectionMessagesItem from missionControlCenterConsoles to spacecraftOperationsTeam { doc /* @S082 */ }
        flow f22 of DeviationsFromExpectedStateItem from consoleDisplays to operators { doc /* @S083 */ }
        flow f23 of DegradedLinkConditionsItem from telemetryEngineer to consoleLead { doc /* @S085 */ }
        flow f24 of HealthTelemetryItem from telemetryIngestService to spacecraftSystemsEngineer { doc /* @S086 */ }
        flow f25 of OperationalConstraintsItem from missionControlCenter to missionPlanningSystem { doc /* @S099 */ }
        flow f26 of OrbitPredictionsItem from flightDynamicsFacility to planningCycle { doc /* @S106 */ }
        flow f27 of VisibilityAssumptionsItem from flightDynamicsFacility to planningCycle { doc /* @S106 */ }
        flow f28 of AntennaDeicingNoticeItem from groundNetworkManager to spacecraftOperationsTeam { doc /* @S113 */ }
        flow f29 of CommandPreparationPackageItem from missionPlanningSystem to commandEngineeringWorkflow { doc /* @S118 */ }
        flow f30 of DynamicOrbitSolutionsItem from orbitDeterminationEngine to productQualityService { doc /* @S130 */ }
        flow f31 of DopplerResidualReportItem from orbitDeterminationEngine to flightDynamicsTeam { doc /* @S131 */ }
        flow f32 of DynamicOrbitSolutionsItem from orbitDeterminationEngine to flightDynamicsTeam { doc /* @S131 */ }
        flow f33 of PredictedOrbitItem from orbitDeterminationEngine to attitudeGeometrySupport { doc /* @S138 */ }
        flow f34 of RoutineEphemeridesItem from flightDynamicsFacility to missionControlCenter { doc /* @S141 */ }
        flow f35 of EventPredictionsItem from flightDynamicsFacility to missionControlCenter { doc /* @S141 */ }
        flow f36 of RoutineEphemeridesItem from flightDynamicsFacility to missionPlanningSystem { doc /* @S141 */ }
        flow f37 of EventPredictionsItem from flightDynamicsFacility to missionPlanningSystem { doc /* @S141 */ }
        flow f38 of RoutineEphemeridesItem from flightDynamicsFacility to payloadProcessingFacility { doc /* @S141 */ }
        flow f39 of EventPredictionsItem from flightDynamicsFacility to payloadProcessingFacility { doc /* @S141 */ }
        flow f40 of AcceptedOrbitFilesItem from flightDynamicsFacility to missionPlanningSystem { doc /* @S142 */ }
        flow f41 of PredictedViewingGeometryItem from flightDynamicsFacility to payloadCalibrationTeam { doc /* @S147 */ }
        flow f42 of AntennaPointingPredictionsItem from flightDynamicsFacility to networkControlSystem { doc /* @S148 */ }
        flow f43 of AcceptedRawDataItem from telemetryIngestService to immutableStagingStorage { doc /* @S153 */ }
        flow f44 of SessionIdentifierItem from telemetryIngestService to downstreamProcessors { doc /* @S153 */ }
        flow f45 of ProvenanceItem from backupProcessingCluster to productQualityService { doc /* @S173 */ }
        flow f46 of ProductPackageItem from payloadProcessingFacility to longTermArchive { doc /* @S178 */ }
        flow f47 of AssociatedQualityMetadataItem from payloadProcessingFacility to longTermArchive { doc /* @S178 */ }
        flow f48 of ChecksumEvidenceItem from payloadProcessingFacility to longTermArchive { doc /* @S178 */ }
        flow f49 of OrbitQualityStateChangesItem from flightDynamicsFacility to archiveOperationsQueue { doc /* @S194 */ }
        flow f50 of PassReplayPacketItem from telemetryIngestService to spacecraftOperationsTeam { doc /* @S198 */ }
        flow f51 of LaserRetroreflectorWindowItem from orbitDeterminationEngine to missionPlanningSystem { doc /* @S207 */ }
        flow f52 of ProcessingWorkItem from nullPart to backupProcessingCluster { doc /* @S221 */ }
        flow f53 of ConfirmedServiceImpactsItem from userServicesPortal to nullPart { doc /* @S225 */ }
        flow f54 of TheCalibrationPatchBundleItem from payloadCalibrationTeam to productQualityService { doc /* joined @S094,S162 */ }
        flow f55 of ASecurityExceptionTicketItem from cybersecurityDesk to networkControlSystem { doc /* joined @S074,S170 */ }
        flow f56 of TheStarTrackerMaskFileItem from flightDynamicsFacility to commandValidationGateway { doc /* joined @S139,S206 */ }
        flow f57 of TheProductHoldListItem from productQualityService to userServicesPortal { doc /* joined @S168,S239 */ }
        flow f58 of TheEphemerisDeltaNoteItem from flightDynamicsTeam to missionPlanningSystem { doc /* joined @S144,S240 */ }
        flow f59 of TheStorageWatermarkSnapshotItem from longTermArchive to backupProcessingCluster { doc /* joined @S174,S241 */ }
    }
    requirement def R0 { doc /* interfaces are required for operations @S003 */ subject s : Interfaces; }
    requirement def R1 { doc /* navigation products required by other ground functions @S008 */ subject s : NavigationProducts; }
    requirement def R2 { doc /* human authorization remains required for spacecraft commanding and major configuration changes @S025 */ subject s : HumanAuthorization; }
    requirement def R3 { doc /* sub-millisecond alignment is required for correlation @S069 */ subject s : Null; }
    requirement def R4 { doc /* the received stream must be reconstructed for engineering review @S081 */ subject s : ReceivedStream; }
    requirement def R5 { doc /* operators must identify safety trends while a contact is still available @S083 */ subject s : Operators; }
    requirement def R6 { doc /* they must be reachable during planned critical activities and whenever a console operator declares an off-nominal condition @S095 */ subject s : SubsystemSpecialists; }
    requirement def R7 { doc /* Final approval requires concurrence from the Mission Control Center and the Spacecraft Operations Team before any command stack is placed in the queue for the next authorized uplink opportunity. @S126 */ subject s : CommandStack; }
    requirement def R8 { doc /* Bluebell requires that each flight dynamics delivery include a validity interval, coordinate frame, generation time, and operational use statement. @S140 */ subject s : FlightDynamicsDelivery; }
    requirement def R9 { doc /* release blocking defects must be tracked across scenes and processing levels @S168 */ subject s : ReleaseBlockingDefects; }
    requirement def R10 { doc /* Lantern shall preserve the last validated routing configuration and reject unreviewed changes while payload product transfers are active. @S171 */ subject s : NetworkControlSystem; }
    requirement def R11 { doc /* checksum evidence required by the configured acceptance rule @S178 */ subject s : ChecksumEvidence; }
    requirement def R12 { doc /* Retention exceptions require traceability to the approving authority, the affected product classes, and the expected operational impact. @S191 */ subject s : RetentionExceptions; }
    requirement def R13 { doc /* Forgehouse must quarantine suspect input and derived output when product lineage cannot be proven during an active anomaly investigation. @S215 */ subject s : PayloadProcessingFacility; }
    requirement def R14 { doc /* the approved authorization state, validation result, and operator acknowledgment required for routine service @S242 */ subject s : CommandRequest; }
}
