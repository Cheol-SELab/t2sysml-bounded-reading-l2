package L2Model {
    item def AcceptedRawDataItem { doc /* @S153 */ }
    item def AccessPredictionItem { doc /* @S008 */ }
    item def AntennaDeicingNoticeItem { doc /* @S113 */ }
    item def AntennaPointingSupportProductsItem { doc /* @S040 */ }
    item def AntennaStatusItem { doc /* @S079 */ }
    item def AssociatedQualityMetadataItem { doc /* @S178 */ }
    item def CalibrationPatchBundleItem { doc /* @S162 */ }
    item def CatalogueRecordsItem { doc /* @S181 */ }
    item def ChecksumEvidenceItem { doc /* @S178 */ }
    item def CommandPreparationPackageItem { doc /* @S118 */ }
    item def ConfigurationChangesItem { doc /* @S205 */ }
    item def ControlledOrbitKnowledgeItem { doc /* @S014 */ }
    item def DeviationsFromExpectedStateItem { doc /* @S083 */ }
    item def EventPredictionsItem { doc /* @S141 */ }
    item def LinkConfigurationItem { doc /* @S079 */ }
    item def LocalConstraintsItem { doc /* @S043 */ }
    item def ManeuverPlanningSupportItem { doc /* @S008 */ }
    item def ManeuverRecommendationsItem { doc /* @S146 */ }
    item def NavigationProductsItem { doc /* @S008 */ }
    item def OperationalConstraintsItem { doc /* @S099 */ }
    item def OrbitAnalysisItem { doc /* @S008 */ }
    item def OrbitPredictionsItem { doc /* @S106 */ }
    item def OrbitQualityStateChangesItem { doc /* @S194 */ }
    item def ProductPackageItem { doc /* @S178 */ }
    item def ProvenanceItem { doc /* @S173 */ }
    item def RoutineEphemeridesItem { doc /* @S141 */ }
    item def RoutingReadinessItem { doc /* @S079 */ }
    item def SecurityExceptionTicketItem { doc /* @S170 */ }
    item def SpacecraftTelemetryItem { doc /* @S013 */ }
    item def StarTrackerMaskFileItem { doc /* @S206 */ }
    item def StorageWatermarkSnapshotItem { doc /* @S241 */ }
    item def TimingReferencesItem { doc /* @S079 */ }
    item def VisibilityAssumptionsItem { doc /* @S106 */ }
    item def VisibilityPredictionsItem { doc /* @S040 */ }
    item def WhetherRecoveryRetransmissionOrDiscardIsRequiredItem { doc /* @S154 */ }
    part def AccountableOwners { doc /* @S249 */ }
    part def ActiveProductSpecification { doc /* @S157 */ }
    part def Activities { doc /* @S114 */ }
    part def Anomalies { doc /* @S099 */ }
    part def AnomalyDeclaration { doc /* @S235 */ }
    part def Antenna { doc /* @S047 */ }
    part def AntennaAllocation { doc /* @S222 */ }
    part def AntennaSiteEquipment { doc /* @S070 */ }
    part def ApplicablePolicy { doc /* @S196 */ }
    part def ArchiveAdmission { doc /* @S178 */ }
    part def ArchiveAvailability { doc /* @S244 */ }
    part def ArchiveOperationsQueue { doc /* @S194 */ }
    part def ArchivedDownlinkContext { doc /* @S198 */ }
    part def AttitudeConstraints { doc /* @S097 */ }
    part def AttitudeGeometrySupport { doc /* @S138 */ }
    part def AutomatedConsumers { doc /* @S166 */ }
    part def BackupProcessingCluster { doc /* @S004,S066,S150,S173,S221,S241,S247 */ }
    part def BulkMovement { doc /* @S065 */ }
    part def CalibrationAnalysis { doc /* @S094 */ }
    part def CalibrationChanges { doc /* @S164 */ }
    part def CalibrationImprovements { doc /* @S192 */ }
    part def CatalogueMetadata { doc /* @S189 */ }
    part def CataloguePublication { doc /* @S180 */ }
    part def CatalogueRecords { doc /* @S197 */ }
    part def ChainOfCustodyEntry { doc /* @S214 */ }
    part def Changes { doc /* @S075 */ }
    part def Checksums { doc /* @S189 */ }
    part def ClockBias { doc /* @S071 */ }
    part def CollisionAssessment { doc /* @S135 */ }
    part def CommandEngineeringWorkflow { doc /* @S118 */ }
    part def CommandLoadSize { doc /* @S115 */ }
    part def CommandRequest { doc /* @S242 */ }
    part def CommandStack { doc /* @S143 */ }
    part def CommandStackValidation { doc /* @S120 */ }
    part def CommandTiming { doc /* @S097 */ }
    part def CommandValidationGateway { doc /* @S004,S012,S119,S121,S143,S206,S242 */ }
    part def CommandValidationTimeliness { doc /* @S244 */ }
    part def CommandingDiscipline { doc /* @S235 */ }
    part def ConfigurationBaselines { doc /* @S248 */ }
    part def ConfigurationControlPrinciples { doc /* @S027 */ }
    part def ConfigurationIdentifier { doc /* @S206 */ }
    part def ConsoleDisplays { doc /* @S083 */ }
    part def ConsoleLead { doc /* @S084 */ }
    part def ConsoleOperator { doc /* @S095 */ }
    part def ConstraintChecking { doc /* @S115 */ }
    part def ContactSchedules { doc /* @S222 */ }
    part def ContactSuccessRate { doc /* @S244 */ }
    part def Contacts { doc /* @S028,S090 */ }
    part def ContinuousSecurityMonitoring { doc /* @S226 */ }
    part def ContractualLatency { doc /* @S188 */ }
    part def ControlledOperationalActivity { doc /* @S077 */ }
    part def CoordinateFrame { doc /* @S140 */ }
    part def CorrelationRules { doc /* @S075 */ }
    part def CybersecurityDesk { doc /* @S023,S074,S076,S125,S170,S200,S204,S212,S238 */ }
    part def DataDownlinkPriorities { doc /* @S093 */ }
    part def DataVolume { doc /* @S078 */ }
    part def DegradedLinkConditions { doc /* @S085 */ }
    part def Demand { doc /* @S188 */ }
    part def DownlinkAllocationChange { doc /* @S049 */ }
    part def DownloadServices { doc /* @S184 */ }
    part def DownstreamProcessing { doc /* @S048 */ }
    part def DownstreamProcessingFunctions { doc /* @S013 */ }
    part def DownstreamProcessors { doc /* @S153 */ }
    part def DraftSchedule { doc /* @S108,S109 */ }
    part def EngineeringAnalysis { doc /* @S013,S091 */ }
    part def EngineeringTeams { doc /* @S218 */ }
    part def EquipmentStatus { doc /* @S087 */ }
    part def EscalationFromTheMissionControlCenter { doc /* @S096 */ }
    part def EscalationPaths { doc /* @S227 */ }
    part def Events { doc /* @S023,S136 */ }
    part def ExternalInterfaces { doc /* @S199 */ }
    part def ExternalUsers { doc /* @S104 */ }
    part def Failover { doc /* @S066 */ }
    part def FinalApproval { doc /* @S126 */ }
    part def FirewallState { doc /* @S222 */ }
    part def FlightDynamicsDelivery { doc /* @S140 */ }
    part def FlightDynamicsFacility { doc /* @S004,S008,S040,S068,S106,S132,S139,S141,S146,S148,S194,S206,S231 */ }
    part def FlightDynamicsTeam { doc /* @S021,S071,S088,S097,S116,S131,S134,S136,S144,S210,S236 */ }
    part def ForecastIcing { doc /* @S044 */ }
    part def GeneralRelease { doc /* @S164 */ }
    part def GenerationTime { doc /* @S140 */ }
    part def GroundConnectivity { doc /* @S010 */ }
    part def GroundNetworkManagementPractices { doc /* @S050 */ }
    part def GroundNetworkManager { doc /* @S019,S038,S044,S060,S067,S076,S087,S112,S113,S209,S234 */ }
    part def GroundProcedures { doc /* @S227 */ }
    part def GroundSegment { doc /* @S002,S004,S005,S218,S219,S224 */ }
    part def Handover { doc /* @S249 */ }
    part def HeavyPrecipitation { doc /* @S046 */ }
    part def HelpDeskResponsiveness { doc /* @S244 */ }
    part def HighWinds { doc /* @S047 */ }
    part def HoldoverCapability { doc /* @S068 */ }
    part def HousekeepingActivities { doc /* @S108 */ }
    part def HumanAuthorization { doc /* @S025 */ }
    part def ImmutableStagingStorage { doc /* @S153 */ }
    part def IncidentLead { doc /* @S225 */ }
    part def IngestWorkflow { doc /* @S152 */ }
    part def InstrumentModeChanges { doc /* @S093 */ }
    part def IntegratedDayInTheLifeRehearsal { doc /* @S235 */ }
    part def IntegrityCheck { doc /* @S206 */ }
    part def Interfaces { doc /* @S003 */ }
    part def KirunaXBandAntenna { doc /* @S005,S055,S078 */ }
    part def LateOperationalRequests { doc /* @S105 */ }
    part def LateOrUnevenDelivery { doc /* @S064 */ }
    part def LaterProcessing { doc /* @S149 */ }
    part def Level1AProcessing { doc /* @S156 */ }
    part def Level1BProcessing { doc /* @S156 */ }
    part def Level2Processing { doc /* @S157 */ }
    part def Level2Products { doc /* @S188 */ }
    part def LiveMonitoringPeriod { doc /* @S077 */ }
    part def LocalConstraints { doc /* @S043 */ }
    part def LocalInfrastructure { doc /* @S053 */ }
    part def LocalStationTeams { doc /* @S042 */ }
    part def LongTermArchive { doc /* @S004,S065,S149,S174,S178,S179,S180,S181,S187,S188,S189,S190,S192,S194,S196,S201,S224,S241,S243 */ }
    part def MaintenanceCondition { doc /* @S060 */ }
    part def MandatoryChecks { doc /* @S167 */ }
    part def ManeuverRecommendationPackage { doc /* @S137 */ }
    part def ManeuverScreening { doc /* @S133 */ }
    part def Measure { doc /* @S246 */ }
    part def MeasuredBuildup { doc /* @S044 */ }
    part def Measurements { doc /* @S129 */ }
    part def Metadata { doc /* @S160 */ }
    part def MissionControlCenter { doc /* @S004,S032,S043,S056,S068,S077,S079,S093,S099,S100,S140,S141,S175,S203,S217,S230 */ }
    part def MissionManagement { doc /* @S176,S182,S186 */ }
    part def MissionPlanning { doc /* @S101 */ }
    part def MissionPlanningSystem { doc /* @S004,S011,S034,S099,S102,S107,S114,S118,S141,S142,S207,S216,S240 */ }
    part def MonitoredEvent { doc /* @S074 */ }
    part def MonitoringViews { doc /* @S227 */ }
    part def NetworkControlSystem { doc /* @S004,S010,S033,S056,S072,S079,S148,S170,S171,S205,S233 */ }
    part def NetworkRouting { doc /* @S222 */ }
    part def NorthSBandAntenna { doc /* @S005,S028,S054 */ }
    part def ObservationRequests { doc /* @S101,S104 */ }
    part def OffNominalCondition { doc /* @S096 */ }
    part def OnboardEvent { doc /* @S091 */ }
    part def OpenAction { doc /* @S228 */ }
    part def OperationalEvidence { doc /* @S017 */ }
    part def OperationalImpacts { doc /* @S137 */ }
    part def OperationalKeyPerformanceIndicators { doc /* @S244,S245 */ }
    part def OperationalLog { doc /* @S205 */ }
    part def OperationalReadinessReview { doc /* @S227 */ }
    part def OperationalReportingCycle { doc /* @S250 */ }
    part def OperationalUseStatement { doc /* @S140 */ }
    part def Operations { doc /* @S013,S243 */ }
    part def OperationsCrew { doc /* @S100 */ }
    part def OperationsStaff { doc /* @S201 */ }
    part def OperationsUsers { doc /* @S127 */ }
    part def Operator { doc /* @S167 */ }
    part def OperatorApprovalState { doc /* @S206 */ }
    part def OperatorDisplay { doc /* @S154 */ }
    part def Operators { doc /* @S083,S098,S213 */ }
    part def OrbitDeterminationEngine { doc /* @S004,S014,S041,S089,S123,S128,S145 */ }
    part def OrbitGeometry { doc /* @S031 */ }
    part def OrbitSolution { doc /* @S134 */ }
    part def OrbitStateManagement { doc /* @S127 */ }
    part def OrbitUpdates { doc /* @S192 */ }
    part def OtherGroundFunctions { doc /* @S008 */ }
    part def Pass { doc /* @S079 */ }
    part def PassPreparation { doc /* @S235 */ }
    part def PassReconstruction { doc /* @S090 */ }
    part def PayloadCalibrationTeam { doc /* @S022,S094,S117,S147,S161,S162,S193,S211,S237 */ }
    part def PayloadDownlinkTraffic { doc /* @S055 */ }
    part def PayloadImaging { doc /* @S108 */ }
    part def PayloadProcessingFacility { doc /* @S004,S009,S049,S110,S141,S151,S152,S178,S215,S232 */ }
    part def PersistentIdentifier { doc /* @S179 */ }
    part def PhysicalTopology { doc /* @S053 */ }
    part def PlannedCalibrationActivities { doc /* @S117 */ }
    part def PlannedSupport { doc /* @S113 */ }
    part def Planning { doc /* @S014,S040 */ }
    part def PlanningCycle { doc /* @S106 */ }
    part def PostBurnAssessmentSteps { doc /* @S097 */ }
    part def PostPassClosureStep { doc /* @S077 */ }
    part def PowerBalance { doc /* @S115 */ }
    part def PredictedRisk { doc /* @S137 */ }
    part def PreviousAcquisitions { doc /* @S124 */ }
    part def PrimaryMonthlyServiceReview { doc /* @S246 */ }
    part def PrimaryProcessingCluster { doc /* @S004,S065,S150,S155,S172,S220,S247 */ }
    part def ProcessingLevel { doc /* @S158 */ }
    part def ProcessorCorrections { doc /* @S192 */ }
    part def ProductGeneration { doc /* @S014 */ }
    part def ProductLatency { doc /* @S244 */ }
    part def ProductQualityDispositionTime { doc /* @S244 */ }
    part def ProductQualityService { doc /* @S004,S015,S124,S130,S162,S165,S168,S173,S181,S195 */ }
    part def Products { doc /* @S167,S182 */ }
    part def ProtectedAccessRouters { doc /* @S054 */ }
    part def ProtectiveActions { doc /* @S076 */ }
    part def Provenance { doc /* @S173 */ }
    part def QualityInvestigations { doc /* @S192 */ }
    part def RateControls { doc /* @S184 */ }
    part def RawSegments { doc /* @S154 */ }
    part def RawTransfer { doc /* @S152 */ }
    part def ReadinessCheck { doc /* @S077 */ }
    part def ReadinessEvidence { doc /* @S231 */ }
    part def ReadinessReviewBoard { doc /* @S228 */ }
    part def ReceivedStream { doc /* @S081 */ }
    part def ReceptionGaps { doc /* @S093 */ }
    part def RecorderCapacity { doc /* @S115 */ }
    part def RecorderManagement { doc /* @S108 */ }
    part def Recovery { doc /* @S176 */ }
    part def RecoveryReporting { doc /* @S235 */ }
    part def RedundantCapabilities { doc /* @S026 */ }
    part def RedundantReferenceClocks { doc /* @S068 */ }
    part def RegisteredUsers { doc /* @S185 */ }
    part def Rehearsals { doc /* @S249 */ }
    part def ReleaseBlockingDefects { doc /* @S168 */ }
    part def ReprocessingDependence { doc /* @S188 */ }
    part def RequiredSeparationBetweenIncompatibleActivities { doc /* @S115 */ }
    part def ResponsibleTeams { doc /* @S226 */ }
    part def RestoreProcedures { doc /* @S189 */ }
    part def RetentionExceptions { doc /* @S191 */ }
    part def RetrievalTests { doc /* @S243 */ }
    part def RoutineMissionService { doc /* @S227 */ }
    part def RoutineProduction { doc /* @S177 */ }
    part def RoutineReporting { doc /* @S245 */ }
    part def RoutingIssues { doc /* @S087 */ }
    part def SchedulingService { doc /* @S172 */ }
    part def ScreeningRules { doc /* @S136 */ }
    part def SecurityOrContinuityAnomaly { doc /* @S216 */ }
    part def SentinelVale { doc /* @S001 */ }
    part def SiteDegradation { doc /* @S221 */ }
    part def SlewTime { doc /* @S115 */ }
    part def SouthSBandAntenna { doc /* @S005,S029,S054 */ }
    part def Spacecraft { doc /* @S013 */ }
    part def SpacecraftConfigurationChanges { doc /* @S099 */ }
    part def SpacecraftOperationsTeam { doc /* @S020,S072,S082,S097,S105,S113,S137,S146,S198,S209,S235 */ }
    part def SpacecraftSystemsEngineer { doc /* @S086 */ }
    part def StaffingRosters { doc /* @S227 */ }
    part def StandardLevel1Products { doc /* @S188 */ }
    part def StationDeliveryFiles { doc /* @S152 */ }
    part def StationOperators { doc /* @S043 */ }
    part def StationOutages { doc /* @S099 */ }
    part def SubMillisecondAlignment { doc /* @S069 */ }
    part def SubsystemSpecialists { doc /* @S095 */ }
    part def SunAngleLimits { doc /* @S115 */ }
    part def SupportTeams { doc /* @S249 */ }
    part def SvalbardXBandAntenna { doc /* @S005,S031,S055,S078 */ }
    part def Telemetry { doc /* @S084,S098 */ }
    part def TelemetryCompleteness { doc /* @S244 */ }
    part def TelemetryEngineer { doc /* @S085 */ }
    part def TelemetryIngestService { doc /* @S004,S013,S048,S080,S081,S153,S154 */ }
    part def TelemetryReception { doc /* @S218 */ }
    part def TelemetrySurveillance { doc /* @S235 */ }
    part def ThermalRecoveryTime { doc /* @S115 */ }
    part def TimingConstraints { doc /* @S137 */ }
    part def TrackingArcs { doc /* @S129 */ }
    part def TrackingExpectations { doc /* @S097 */ }
    part def TrafficSupportingTheOrbitDeterminationEngine { doc /* @S064 */ }
    part def UnresolvedAnomalyAge { doc /* @S244 */ }
    part def UnsafeOutdoorConditions { doc /* @S047 */ }
    part def UpdatedStateVectors { doc /* @S144 */ }
    part def UserServicesPortal { doc /* @S004,S018,S104,S181,S183,S201,S225,S239 */ }
    part def Users { doc /* @S195 */ }
    part def ValidationEvidence { doc /* @S193 */ }
    part def ValidityInterval { doc /* @S140 */ }
    part def VisibilityGeometry { doc /* @S078 */ }
    part def Weather { doc /* @S087 */ }
    part def WideAreaConnectivityDesign { doc /* @S052 */ }
    part system {
        part accountableOwners : AccountableOwners {
            perform action a0 { doc /* are acknowledged by accountable owners @S249 */ }
        }
        part activeProductSpecification : ActiveProductSpecification {
            perform action a0 { doc /* defined in the active product specification @S157 */ }
        }
        part activities : Activities {
            perform action a0 { doc /* compete for the same spacecraft resource, ground station resource, or operational staffing interval @S114 */ }
        }
        part anomalies : Anomalies {
            perform action a0 { doc /* require adjustment of future contacts or payload activities @S099 */ }
        }
        part anomalyDeclaration : AnomalyDeclaration;
        part antenna : Antenna {
            exhibit state modes {
                state s0 { doc /* unavailable for service @S047 */ }
            }
        }
        part antennaAllocation : AntennaAllocation {
            exhibit state modes {
                state s0 { doc /* consistent @S222 */ }
            }
        }
        part antennaSiteEquipment : AntennaSiteEquipment {
            perform action a0 { doc /* validates time against independent local references before contact start @S070 */ }
        }
        part applicablePolicy : ApplicablePolicy {
            perform action a0 { doc /* allows consolidation after a defined comparison period @S196 */ }
        }
        part archiveAdmission : ArchiveAdmission {
            perform action a0 { doc /* begins @S178 */ }
        }
        part archiveAvailability : ArchiveAvailability;
        part archiveOperationsQueue : ArchiveOperationsQueue;
        part archivedDownlinkContext : ArchivedDownlinkContext {
            perform action a0 { doc /* can support anomaly reconstruction @S198 */ }
        }
        part attitudeConstraints : AttitudeConstraints {
            perform action a0 { doc /* remain consistent @S097 */ }
        }
        part attitudeGeometrySupport : AttitudeGeometrySupport {
            perform action a0 { doc /* translates the predicted orbit into Sun angle, Earth limb, lunar exclusion, target visibility, and antenna pointing information for daily operations @S138 */ }
        }
        part automatedConsumers : AutomatedConsumers {
            perform action a0 { doc /* can reject @S166 */ }
            perform action a1 { doc /* warn @S166 */ }
            perform action a2 { doc /* accept data consistently @S166 */ }
        }
        part backupProcessingCluster : BackupProcessingCluster {
            perform action a0 { doc /* receives lower routing preference during normal operations @S066 */ }
            perform action a1 { doc /* supports product generation with the same validation checks and distribution rules @S150 */ }
            perform action a2 { doc /* writes provenance that identifies the fallback execution path @S173 */ }
            perform action a3 { doc /* uses the Storage Watermark Snapshot @S241 */ }
            perform action a4 { doc /* verify that recovery capacity is sufficient @S241 */ }
            perform action a5 { doc /* accepts routine standby responsibility @S241 */ }
            perform action a6 { doc /* are baselined with approved software versions, processing configurations, capacity reservations, monitoring checks, and rollback instructions @S247 */ }
        }
        part bulkMovement : BulkMovement {
            perform action a0 { doc /* cannot starve operational telemetry or control-plane monitoring @S065 */ }
        }
        part calibrationAnalysis : CalibrationAnalysis {
            perform action a0 { doc /* identifies an approved update for payload processing behavior @S094 */ }
        }
        part calibrationChanges : CalibrationChanges {
            perform action a0 { doc /* alters radiometric scale, geometric alignment, or saturation behavior @S164 */ }
        }
        part calibrationImprovements : CalibrationImprovements {
            perform action a0 { doc /* materially change product fitness for use @S192 */ }
        }
        part catalogueMetadata : CatalogueMetadata {
            exhibit state modes {
                state s0 { doc /* available @S189 */ }
            }
        }
        part cataloguePublication : CataloguePublication {
            perform action a0 { doc /* can proceed without exposing internal storage paths @S180 */ }
            perform action a1 { doc /* exposing internal storage paths @S180 */ }
        }
        part catalogueRecords : CatalogueRecords {
            perform action a0 { doc /* show processing baseline, sensing time, publication time, quality status, and replacement relationships for each released product @S197 */ }
        }
        part chainOfCustodyEntry : ChainOfCustodyEntry {
            perform action a0 { doc /* identifies the collector, collection time, source system, and reason for capture @S214 */ }
        }
        part changes : Changes {
            perform action a0 { doc /* could affect mission continuity @S075 */ }
        }
        part checksums : Checksums {
            exhibit state modes {
                state s0 { doc /* available @S189 */ }
            }
        }
        part clockBias : ClockBias {
            perform action a0 { doc /* can appear as an apparent measurement error @S071 */ }
        }
        part collisionAssessment : CollisionAssessment {
            perform action a0 { doc /* uses externally supplied conjunction data together with the current covariance @S135 */ }
            perform action a1 { doc /* estimate miss distance, encounter geometry, and probability of collision @S135 */ }
        }
        part commandEngineeringWorkflow : CommandEngineeringWorkflow;
        part commandLoadSize : CommandLoadSize;
        part commandRequest : CommandRequest;
        part commandStack : CommandStack {
            perform action a0 { doc /* proceed @S143 */ }
        }
        part commandStackValidation : CommandStackValidation {
            perform action a0 { doc /* checks syntax, timing, parameter ranges, sequencing rules, spacecraft mode compatibility, and consistency with the approved schedule baseline @S120 */ }
        }
        part commandTiming : CommandTiming {
            perform action a0 { doc /* remain consistent @S097 */ }
        }
        part commandValidationGateway : CommandValidationGateway {
            perform action a0 { doc /* provides the formal barrier between planning outputs and command release @S012 */ }
            perform action a1 { doc /* enforces rule checks @S012 */ }
            perform action a2 { doc /* performs independent validation of command stacks @S119 */ }
            perform action a3 { doc /* rejects command stacks that contain unapproved manual edits, missing provenance, expired configuration references, or activities outside the planning authority window @S121 */ }
            perform action a4 { doc /* checks maneuver command parameters against the screened burn plan @S143 */ }
            perform action a5 { doc /* allowing the command stack to proceed @S143 */ }
            perform action a6 { doc /* accepts the mask file @S206 */ }
            perform action a7 { doc /* rejects any command request that lacks the approved authorization state, validation result, and operator acknowledgment required for routine service @S242 */ }
        }
        part commandValidationTimeliness : CommandValidationTimeliness;
        part commandingDiscipline : CommandingDiscipline;
        part configurationBaselines : ConfigurationBaselines {
            perform action a0 { doc /* are frozen at readiness review entry @S248 */ }
            perform action a1 { doc /* changed only through approved change control @S248 */ }
        }
        part configurationControlPrinciples : ConfigurationControlPrinciples {
            perform action a0 { doc /* apply to command, telemetry, and processing services @S027 */ }
        }
        part configurationIdentifier : ConfigurationIdentifier {
            perform action a0 { doc /* match the active security baseline @S206 */ }
        }
        part consoleDisplays : ConsoleDisplays {
            perform action a0 { doc /* emphasize deviations from expected state rather than raw parameter volume @S083 */ }
        }
        part consoleLead : ConsoleLead {
            perform action a0 { doc /* declaring pass status @S084 */ }
            perform action a1 { doc /* authorizing planned command execution through the Command Validation Gateway @S084 */ }
            perform action a2 { doc /* pausing the activity @S084 */ }
        }
        part consoleOperator : ConsoleOperator {
            perform action a0 { doc /* declares an off-nominal condition @S095 */ }
        }
        part constraintChecking : ConstraintChecking;
        part contactSchedules : ContactSchedules {
            exhibit state modes {
                state s0 { doc /* consistent @S222 */ }
            }
        }
        part contactSuccessRate : ContactSuccessRate;
        part contacts : Contacts {
            perform action a0 { doc /* closes @S090 */ }
        }
        part continuousSecurityMonitoring : ContinuousSecurityMonitoring {
            perform action a0 { doc /* has returned to the approved baseline @S226 */ }
        }
        part contractualLatency : ContractualLatency {
            perform action a0 { doc /* justifies low-latency access @S188 */ }
        }
        part controlledOperationalActivity : ControlledOperationalActivity;
        part coordinateFrame : CoordinateFrame;
        part correlationRules : CorrelationRules {
            perform action a0 { doc /* emphasize changes that could affect mission continuity, including unexpected route advertisements, repeated authentication failures, unscheduled remote access, and unexplained increases in encrypted traffic volume @S075 */ }
        }
        part cybersecurityDesk : CybersecurityDesk {
            perform action a0 { doc /* provides continuous security monitoring, operational security guidance, and escalation support for events that could affect mission services @S023 */ }
            perform action a1 { doc /* sends a Security Exception Ticket when a monitored event requires temporary deviation from the approved security baseline @S074 */ }
            perform action a2 { doc /* coordinate @S076 */ }
            perform action a3 { doc /* blocking traffic @S076 */ }
            perform action a4 { doc /* reviews command preparation exceptions @S125 */ }
            perform action a5 { doc /* reviews public interface changes before deployment @S200 */ }
            perform action a6 { doc /* confirm authentication, logging, and abuse-control requirements are satisfied @S200 */ }
            perform action a7 { doc /* reviews privileged access daily @S204 */ }
            perform action a8 { doc /* challenges dormant, shared, or unexplained accounts @S204 */ }
            perform action a9 { doc /* assumes coordination authority @S212 */ }
            perform action a10 { doc /* participates in the final exercise @S238 */ }
            perform action a11 { doc /* validating alert routing, privileged access review, and incident coordination with operations management @S238 */ }
        }
        part dataDownlinkPriorities : DataDownlinkPriorities {
            perform action a0 { doc /* could affect downstream processing @S093 */ }
        }
        part dataVolume : DataVolume {
            perform action a0 { doc /* justify their use @S078 */ }
        }
        part degradedLinkConditions : DegradedLinkConditions {
            perform action a0 { doc /* could affect command confidence @S085 */ }
        }
        part demand : Demand {
            perform action a0 { doc /* justifies low-latency access @S188 */ }
        }
        part downlinkAllocationChange : DownlinkAllocationChange {
            perform action a0 { doc /* alters expected processing load or delivery timing @S049 */ }
        }
        part downloadServices : DownloadServices {
            perform action a0 { doc /* support resumable transfer, integrity verification, and rate controls that protect mission operations from excessive external demand @S184 */ }
        }
        part downstreamProcessing : DownstreamProcessing {
            perform action a0 { doc /* can distinguish planned gaps from station-side interruptions @S048 */ }
        }
        part downstreamProcessingFunctions : DownstreamProcessingFunctions;
        part downstreamProcessors : DownstreamProcessors {
            perform action a0 { doc /* used by downstream processors @S153 */ }
        }
        part draftSchedule : DraftSchedule {
            perform action a0 { doc /* covers payload imaging, recorder management, housekeeping activities, and expected support from the North S-Band Antenna and South S-Band Antenna @S108 */ }
            perform action a1 { doc /* also accounts for downlink opportunities through the Kiruna X-Band Antenna and Svalbard X-Band Antenna @S109 */ }
        }
        part engineeringAnalysis : EngineeringAnalysis;
        part engineeringTeams : EngineeringTeams {
            perform action a0 { doc /* focus on stabilizing observability and protecting evidence @S218 */ }
            perform action a1 { doc /* stabilizing observability @S218 */ }
            perform action a2 { doc /* protecting evidence @S218 */ }
        }
        part equipmentStatus : EquipmentStatus {
            perform action a0 { doc /* affect a contact @S087 */ }
        }
        part escalationFromTheMissionControlCenter : EscalationFromTheMissionControlCenter {
            perform action a0 { doc /* begins with the console lead @S096 */ }
            perform action a1 { doc /* moves to the responsible discipline lead @S096 */ }
            perform action a2 { doc /* reaches mission management @S096 */ }
        }
        part escalationPaths : EscalationPaths {
            exhibit state modes {
                state s0 { doc /* under configuration control @S227 */ }
            }
        }
        part events : Events {
            perform action a0 { doc /* could affect mission services @S023 */ }
            perform action a1 { doc /* requiring immediate operator notification @S136 */ }
        }
        part externalInterfaces : ExternalInterfaces {
            perform action a0 { doc /* expose catalogue search, subscription notification, product ordering, and download status using versioned service contracts @S199 */ }
            perform action a1 { doc /* using versioned service contracts @S199 */ }
        }
        part externalUsers : ExternalUsers {
            perform action a0 { doc /* can distinguish accepted requests from those still awaiting technical review @S104 */ }
        }
        part failover : Failover {
            perform action a0 { doc /* does not expose stale firewall rules or asymmetric return routes @S066 */ }
        }
        part finalApproval : FinalApproval {
            perform action a0 { doc /* requires concurrence from the Mission Control Center and the Spacecraft Operations Team @S126 */ }
        }
        part firewallState : FirewallState {
            exhibit state modes {
                state s0 { doc /* consistent @S222 */ }
            }
        }
        part flightDynamicsDelivery : FlightDynamicsDelivery {
            perform action a0 { doc /* include a validity interval, coordinate frame, generation time, and operational use statement @S140 */ }
        }
        part flightDynamicsFacility : FlightDynamicsFacility {
            perform action a0 { doc /* provides orbit analysis, maneuver planning support, access prediction, and navigation products required by other ground functions @S008 */ }
            perform action a1 { doc /* provides visibility predictions and antenna pointing support products to the planning process @S040 */ }
            perform action a2 { doc /* provides orbit predictions and visibility assumptions @S106 */ }
            perform action a3 { doc /* maintains the authoritative orbit catalog for the ground segment @S132 */ }
            perform action a4 { doc /* records the modeling assumptions applied to each accepted solution @S132 */ }
            perform action a5 { doc /* sends the Star Tracker Mask File @S139 */ }
            perform action a6 { doc /* verifying predicted bright-object exclusions against the current attitude plan @S139 */ }
            perform action a7 { doc /* distributes routine ephemerides and event predictions through controlled interfaces used by the Mission Control Center, Mission Planning System, and Payload Processing Facility @S141 */ }
            perform action a8 { doc /* derived from the accepted ephemeris @S148 */ }
            perform action a9 { doc /* publishes orbit quality state changes to the archive operations queue @S194 */ }
            perform action a10 { doc /* provides readiness evidence showing that orbit products, maneuver screening, and conjunction coordination can be performed within the committed planning cycle @S231 */ }
        }
        part flightDynamicsTeam : FlightDynamicsTeam {
            perform action a0 { doc /* owns flight dynamics analysis, orbit maintenance recommendations, and operational coordination for navigation-related constraints @S021 */ }
            perform action a1 { doc /* monitors timing quality alongside orbit support metrics @S071 */ }
            perform action a2 { doc /* uses tracking measurements and validated time tags from the contact @S088 */ }
            perform action a3 { doc /* support orbit assessment at the Flight Dynamics Facility @S088 */ }
            perform action a4 { doc /* coordinate closely before orbit-control activities @S097 */ }
            perform action a5 { doc /* reviews cases where orbital uncertainty or contact geometry could reduce the execution margin for a planned acquisition or downlink @S116 */ }
            perform action a6 { doc /* uses the residual report @S131 */ }
            perform action a7 { doc /* separate station-related tracking biases from dynamic model errors @S131 */ }
            perform action a8 { doc /* accepting an orbit solution @S131 */ }
            perform action a9 { doc /* computes expected state change, execution tolerance, recovery strategy, and the earliest time when the solution can be declared stable @S134 */ }
            perform action a10 { doc /* maintains screening rules that distinguish routine catalog monitoring from events requiring immediate operator notification @S136 */ }
            perform action a11 { doc /* produces the Ephemeris Delta Note @S144 */ }
            perform action a12 { doc /* assesses orbit and timing effects @S210 */ }
            perform action a13 { doc /* conducts a separate rehearsal for missed tracking data and late orbit update availability @S236 */ }
            perform action a14 { doc /* confirm that planning products remain usable under degraded conditions @S236 */ }
        }
        part forecastIcing : ForecastIcing {
            perform action a0 { doc /* threatens tracking performance @S044 */ }
        }
        part generalRelease : GeneralRelease {
            perform action a0 { doc /* resumes @S164 */ }
        }
        part generationTime : GenerationTime;
        part groundConnectivity : GroundConnectivity {
            perform action a0 { doc /* supporting the mission @S010 */ }
        }
        part groundNetworkManagementPractices : GroundNetworkManagementPractices {
            perform action a0 { doc /* emphasize advance coordination, disciplined change approval, continuous monitoring during contacts, and post-contact reconciliation against the approved schedule @S050 */ }
        }
        part groundNetworkManager : GroundNetworkManager {
            perform action a0 { doc /* coordinates availability of the antenna assets @S019 */ }
            perform action a1 { doc /* confirms that scheduled contact opportunities are compatible with station readiness and maintenance constraints @S019 */ }
            perform action a2 { doc /* arbitrates unresolved contact conflicts @S038 */ }
            perform action a3 { doc /* verifies that station commitments remain consistent with maintenance windows and staffing limits @S038 */ }
            perform action a4 { doc /* issues the Antenna Deicing Notice when forecast icing or measured buildup threatens tracking performance @S044 */ }
            perform action a5 { doc /* determines that a maintenance condition could cause route oscillation @S060 */ }
            perform action a6 { doc /* verifies carrier performance @S067 */ }
            perform action a7 { doc /* checks routing state, packet loss, queue depth, and security inspection delays @S067 */ }
            perform action a8 { doc /* declaring a mission-impacting network condition @S067 */ }
            perform action a9 { doc /* coordinate @S076 */ }
            perform action a10 { doc /* blocking traffic @S076 */ }
            perform action a11 { doc /* remains accountable for antenna assignment, ground link availability, and coordination with site operations @S087 */ }
            perform action a12 { doc /* confirms that planned station use is compatible with network maintenance windows @S112 */ }
            perform action a13 { doc /* leads triage for antenna, link, and site-service indicators @S209 */ }
            perform action a14 { doc /* accepts the antenna readiness baseline only when the North S-Band Antenna, South S-Band Antenna, Kiruna X-Band Antenna, and Svalbard X-Band Antenna have current maintenance clearances @S234 */ }
        }
        part groundProcedures : GroundProcedures {
            exhibit state modes {
                state s0 { doc /* under configuration control @S227 */ }
            }
        }
        part groundSegment : GroundSegment {
            perform action a0 { doc /* plan spacecraft activities @S002 */ }
            perform action a1 { doc /* acquire mission data @S002 */ }
            perform action a2 { doc /* maintain safe spacecraft operations @S002 */ }
            perform action a3 { doc /* generate user products @S002 */ }
            perform action a4 { doc /* preserve mission records @S002 */ }
            perform action a5 { doc /* provide controlled access to services @S002 */ }
            perform action a6 { doc /* prioritizes spacecraft safety contacts, time-critical telemetry capture, core orbit support, and protection of unrecoverable payload data @S219 */ }
            exhibit state modes {
                state s0 { doc /* degraded operations @S224 */ }
                state s1 { doc /* essential-service mode @S219 */ }
                state s2 { doc /* monitor-only mode @S218 */ }
            }
        }
        part handover : Handover {
            perform action a0 { doc /* is authorized when acceptance evidence is complete, rehearsals meet their objectives, open risks are acknowledged by accountable owners, and support teams confirm on-call coverage @S249 */ }
        }
        part heavyPrecipitation : HeavyPrecipitation {
            perform action a0 { doc /* reduce the link margin below the approved operating threshold @S046 */ }
        }
        part helpDeskResponsiveness : HelpDeskResponsiveness;
        part highWinds : HighWinds {
            perform action a0 { doc /* can still make an antenna unavailable for service @S047 */ }
        }
        part holdoverCapability : HoldoverCapability {
            perform action a0 { doc /* cover credible external timing outages @S068 */ }
        }
        part housekeepingActivities : HousekeepingActivities;
        part humanAuthorization : HumanAuthorization;
        part immutableStagingStorage : ImmutableStagingStorage;
        part incidentLead : IncidentLead {
            perform action a0 { doc /* approves release @S225 */ }
        }
        part ingestWorkflow : IngestWorkflow {
            perform action a0 { doc /* verifies file size, sequence continuity, checksum, and acquisition time @S152 */ }
        }
        part instrumentModeChanges : InstrumentModeChanges {
            perform action a0 { doc /* could affect downstream processing @S093 */ }
        }
        part integratedDayInTheLifeRehearsal : IntegratedDayInTheLifeRehearsal;
        part integrityCheck : IntegrityCheck {
            perform action a0 { doc /* match the active security baseline @S206 */ }
        }
        part interfaces : Interfaces;
        part kirunaXBandAntenna : KirunaXBandAntenna {
            perform action a0 { doc /* use dual wide area paths toward the Payload Processing Facility @S055 */ }
            perform action a1 { doc /* support high-rate telemetry reception @S078 */ }
        }
        part lateOperationalRequests : LateOperationalRequests {
            perform action a0 { doc /* affect spacecraft attitude, thermal margin, stored command capacity, or contact preparation @S105 */ }
        }
        part lateOrUnevenDelivery : LateOrUnevenDelivery {
            perform action a0 { doc /* can reduce the usefulness of contact assessment products @S064 */ }
        }
        part laterProcessing : LaterProcessing {
            perform action a0 { doc /* can reproduce the operational context @S149 */ }
        }
        part level1AProcessing : Level1AProcessing {
            perform action a0 { doc /* reconstructs detector samples @S156 */ }
            perform action a1 { doc /* appends engineering context @S156 */ }
        }
        part level1BProcessing : Level1BProcessing {
            perform action a0 { doc /* applies radiometric calibration and sensor model parameters @S156 */ }
        }
        part level2Processing : Level2Processing {
            perform action a0 { doc /* applies geolocation, atmospheric screening where applicable, and gridding rules defined in the active product specification @S157 */ }
        }
        part level2Products : Level2Products {
            exhibit state modes {
                state s0 { doc /* online @S188 */ }
            }
        }
        part liveMonitoringPeriod : LiveMonitoringPeriod;
        part localConstraints : LocalConstraints {
            perform action a0 { doc /* could affect an approved contact @S043 */ }
        }
        part localInfrastructure : LocalInfrastructure {
            perform action a0 { doc /* permits @S053 */ }
        }
        part localStationTeams : LocalStationTeams {
            perform action a0 { doc /* logging of any local anomalies @S042 */ }
        }
        part longTermArchive : LongTermArchive {
            perform action a0 { doc /* retains released orbit products, covariance data, maneuver records, and quality decisions @S149 */ }
            perform action a1 { doc /* sends the Storage Watermark Snapshot @S174 */ }
            perform action a2 { doc /* is assigned a persistent identifier @S179 */ }
            perform action a3 { doc /* stores object content separately from searchable metadata @S180 */ }
            perform action a4 { doc /* are published to User Services Portal @S181 */ }
            perform action a5 { doc /* retains raw acquisition data for the life of the mission and for the post-mission preservation period defined in the archive policy @S187 */ }
            perform action a6 { doc /* are retained online @S188 */ }
            perform action a7 { doc /* may be moved to lower-cost storage @S189 */ }
            perform action a8 { doc /* is performed only against superseded temporary products, expired working copies, or objects covered by an approved disposal rule @S190 */ }
            perform action a9 { doc /* is triggered when calibration improvements, processor corrections, orbit updates, or quality investigations materially change product fitness for use @S192 */ }
            perform action a10 { doc /* are updated @S194 */ }
            perform action a11 { doc /* preserves the replaced product version @S196 */ }
            perform action a12 { doc /* cannot meet a restore or publication commitment @S201 */ }
            perform action a13 { doc /* preserves the accepted archive baseline @S243 */ }
            perform action a14 { doc /* confirms that retrieval tests meet the service objective @S243 */ }
            exhibit state modes {
                state s0 { doc /* custody reference @S224 */ }
            }
        }
        part maintenanceCondition : MaintenanceCondition {
            perform action a0 { doc /* could cause route oscillation @S060 */ }
        }
        part mandatoryChecks : MandatoryChecks {
            perform action a0 { doc /* fail @S167 */ }
        }
        part maneuverRecommendationPackage : ManeuverRecommendationPackage {
            perform action a0 { doc /* includes timing constraints and operational impacts @S137 */ }
        }
        part maneuverScreening : ManeuverScreening {
            perform action a0 { doc /* evaluates orbit maintenance options against fuel use, ground contact visibility, payload outage constraints, and post-burn tracking opportunities @S133 */ }
        }
        part measure : Measure {
            perform action a0 { doc /* moves outside the watch band @S246 */ }
        }
        part measuredBuildup : MeasuredBuildup {
            perform action a0 { doc /* threatens tracking performance @S044 */ }
        }
        part measurements : Measurements {
            perform action a0 { doc /* meet quality and timing criteria @S129 */ }
        }
        part metadata : Metadata {
            perform action a0 { doc /* distinguish operational output from test output and reprocessed output @S160 */ }
        }
        part missionControlCenter : MissionControlCenter {
            perform action a0 { doc /* maintains the operational contact schedule @S032 */ }
            perform action a1 { doc /* uses it as the controlling reference for console staffing, command readiness, and telemetry coverage @S032 */ }
            perform action a2 { doc /* hosts the primary routing policy point @S056 */ }
            perform action a3 { doc /* treats every scheduled contact as a controlled operational activity with a defined readiness check, live monitoring period, and post-pass closure step @S077 */ }
            perform action a4 { doc /* coordinates with the Payload Processing Facility @S093 */ }
            perform action a5 { doc /* records unresolved actions, open engineering questions, and expected specialist responses @S100 */ }
            perform action a6 { doc /* requires that each flight dynamics delivery include a validity interval, coordinate frame, generation time, and operational use statement @S140 */ }
            perform action a7 { doc /* used by the Mission Control Center, Mission Planning System, and Payload Processing Facility @S141 */ }
            perform action a8 { doc /* maintains the authority boundary for routine spacecraft operations @S203 */ }
            perform action a9 { doc /* confirms that elevated access is tied to an approved shift role and a time-limited operational need @S203 */ }
            perform action a10 { doc /* are declared by the Mission Control Center @S217 */ }
            perform action a11 { doc /* demonstrates continuous console coverage for the agreed service hours @S230 */ }
            perform action a12 { doc /* proves that shift handover logs contain the state needed by the incoming controller @S230 */ }
        }
        part missionManagement : MissionManagement {
            perform action a0 { doc /* approves a different backlog rule @S176 */ }
            perform action a1 { doc /* is cleared @S182 */ }
            perform action a2 { doc /* is allowed only for product classes that have been approved for open dissemination by mission management @S186 */ }
            perform action a3 { doc /* have been approved for open dissemination by mission management @S186 */ }
        }
        part missionPlanning : MissionPlanning {
            perform action a0 { doc /* begins @S101 */ }
        }
        part missionPlanningSystem : MissionPlanningSystem {
            perform action a0 { doc /* converts approved imaging demand and spacecraft constraints into executable activity plans for routine operations @S011 */ }
            perform action a1 { doc /* receives operational constraints from mission control @S099 */ }
            perform action a2 { doc /* assembling candidate observation timelines and associated ground contact activities @S102 */ }
            perform action a3 { doc /* combines request priority, instrument availability, contact opportunities, onboard storage margin, and downlink capacity into a draft activity schedule @S107 */ }
            perform action a4 { doc /* flags conflicts @S114 */ }
            perform action a5 { doc /* exports a command preparation package to the command engineering workflow at the Mission Control Center @S118 */ }
            perform action a6 { doc /* used by the Mission Control Center, Mission Planning System, and Payload Processing Facility @S141 */ }
            perform action a7 { doc /* uses accepted orbit files @S142 */ }
            perform action a8 { doc /* align imaging requests, contact opportunities, recorder margins, and downlink windows @S142 */ }
            perform action a9 { doc /* treats the retroreflector window as a constrained planning input @S207 */ }
            perform action a10 { doc /* prevents its use outside the approved scheduling interval @S207 */ }
            perform action a11 { doc /* suspends automatic schedule publication @S216 */ }
            perform action a12 { doc /* applies the delta note during schedule validation @S240 */ }
            perform action a13 { doc /* ensure that contact and activity timing remains consistent with the latest operational constraint @S240 */ }
        }
        part monitoredEvent : MonitoredEvent {
            perform action a0 { doc /* requires temporary deviation from the approved security baseline @S074 */ }
        }
        part monitoringViews : MonitoringViews {
            exhibit state modes {
                state s0 { doc /* under configuration control @S227 */ }
            }
        }
        part networkControlSystem : NetworkControlSystem {
            perform action a0 { doc /* monitors communications availability @S010 */ }
            perform action a1 { doc /* routes operational traffic @S010 */ }
            perform action a2 { doc /* provides status awareness for ground connectivity supporting the mission @S010 */ }
            perform action a3 { doc /* distributes station allocations @S033 */ }
            perform action a4 { doc /* confirms antenna readiness states @S033 */ }
            perform action a5 { doc /* records the actual start and end times of each contact @S033 */ }
            perform action a6 { doc /* maintains operational visibility of circuit state, path selection, and active maintenance windows @S056 */ }
            perform action a7 { doc /* confirms that the alarm is not caused by a known maintenance interval or a failed local reference check @S072 */ }
            perform action a8 { doc /* provides the Mission Control Center with antenna status, link configuration, timing references, and routing readiness @S079 */ }
            perform action a9 { doc /* uses antenna pointing predictions derived from the accepted ephemeris @S148 */ }
            perform action a10 { doc /* prepare scheduled contacts @S148 */ }
            perform action a11 { doc /* verify tracking readiness @S148 */ }
            perform action a12 { doc /* uses the Security Exception Ticket @S170 */ }
            perform action a13 { doc /* restrict affected transfer paths @S170 */ }
            perform action a14 { doc /* shall preserve the last validated routing configuration @S171 */ }
            perform action a15 { doc /* reject unreviewed changes @S171 */ }
            perform action a16 { doc /* enforces approved routing paths between ground stations, processing services, and external interfaces @S205 */ }
            perform action a17 { doc /* records configuration changes in the operational log @S205 */ }
            perform action a18 { doc /* records rehearsal outcomes for planned maintenance, station loss, degraded routing, and restoration of nominal connectivity after a simulated outage @S233 */ }
            exhibit state modes {
                state s0 { doc /* degraded routing @S233 */ }
                state s1 { doc /* nominal connectivity @S233 */ }
            }
        }
        part networkRouting : NetworkRouting {
            exhibit state modes {
                state s0 { doc /* consistent @S222 */ }
            }
        }
        part northSBandAntenna : NorthSBandAntenna {
            perform action a0 { doc /* provides the nominal early-pass command uplink and low-rate telemetry return for contacts that require conservative link margins @S028 */ }
            perform action a1 { doc /* connect to the Mission Control Center through protected access routers @S054 */ }
        }
        part observationRequests : ObservationRequests {
            perform action a0 { doc /* arrive through the User Services Portal or from internal operations channels at the Mission Control Center @S101 */ }
            perform action a1 { doc /* awaiting technical review @S104 */ }
            exhibit state modes {
                state s0 { doc /* accepted @S104 */ }
                state s1 { doc /* awaiting technical review @S104 */ }
            }
        }
        part offNominalCondition : OffNominalCondition {
            perform action a0 { doc /* threatens spacecraft safety, contact continuity, or recovery schedule @S096 */ }
        }
        part onboardEvent : OnboardEvent {
            perform action a0 { doc /* occurred outside the timeline @S091 */ }
        }
        part openAction : OpenAction;
        part operationalEvidence : OperationalEvidence;
        part operationalImpacts : OperationalImpacts;
        part operationalKeyPerformanceIndicators : OperationalKeyPerformanceIndicators {
            perform action a0 { doc /* include contact success rate, telemetry completeness, command validation timeliness, product latency, product quality disposition time, archive availability, help desk responsiveness, and unresolved anomaly age @S244 */ }
            perform action a1 { doc /* has an assigned data source, sampling interval, review owner, threshold, and corrective action trigger @S245 */ }
        }
        part operationalLog : OperationalLog;
        part operationalReadinessReview : OperationalReadinessReview {
            perform action a0 { doc /* confirms that ground procedures, staffing rosters, monitoring views, and escalation paths are under configuration control @S227 */ }
        }
        part operationalReportingCycle : OperationalReportingCycle {
            perform action a0 { doc /* is treated as a stabilization period @S250 */ }
        }
        part operationalUseStatement : OperationalUseStatement;
        part operations : Operations {
            exhibit state modes {
                state s0 { doc /* stable @S243 */ }
            }
        }
        part operationsCrew : OperationsCrew {
            perform action a0 { doc /* can maintain continuity without relying on informal handover @S100 */ }
            perform action a1 { doc /* relying on informal handover @S100 */ }
        }
        part operationsStaff : OperationsStaff {
            perform action a0 { doc /* open the normal incident process @S201 */ }
        }
        part operationsUsers : OperationsUsers {
            perform action a0 { doc /* work from a common predicted trajectory @S127 */ }
        }
        part operator : Operator {
            perform action a0 { doc /* opens a blocking review @S167 */ }
        }
        part operatorApprovalState : OperatorApprovalState {
            perform action a0 { doc /* match the active security baseline @S206 */ }
        }
        part operatorDisplay : OperatorDisplay {
            perform action a0 { doc /* shows whether recovery, retransmission, or discard is required @S154 */ }
            perform action a1 { doc /* is required @S154 */ }
        }
        part operators : Operators {
            perform action a0 { doc /* must identify safety trends while a contact is still available @S083 */ }
            perform action a1 { doc /* preserve the command state @S098 */ }
            perform action a2 { doc /* avoid discretionary commanding @S098 */ }
            perform action a3 { doc /* request specialist review @S098 */ }
            perform action a4 { doc /* changing spacecraft configuration @S098 */ }
            perform action a5 { doc /* preserve volatile logs, current configuration state, operator console history, and relevant message identifiers @S213 */ }
            perform action a6 { doc /* restarting services @S213 */ }
            perform action a7 { doc /* changing routing @S213 */ }
        }
        part orbitDeterminationEngine : OrbitDeterminationEngine {
            perform action a0 { doc /* supports routine orbit maintenance @S014 */ }
            perform action a1 { doc /* processing tracking inputs @S014 */ }
            perform action a2 { doc /* producing controlled orbit knowledge for planning and product generation @S014 */ }
            perform action a3 { doc /* produces the Doppler Residual Report after each qualified tracking pass @S041 */ }
            perform action a4 { doc /* support navigation trend assessment @S041 */ }
            perform action a5 { doc /* supports routine state updates @S089 */ }
            perform action a6 { doc /* provides the basis for predicting future visibility periods, maneuver planning constraints, and antenna pointing expectations @S089 */ }
            perform action a7 { doc /* provides the current orbital solution used to confirm time-tagged events, contact visibility, and any attitude-dependent observation geometry @S123 */ }
            perform action a8 { doc /* fits dynamic orbit solutions using radiometric tracking, spacecraft telemetry timing, force models, and the latest approved maneuver history @S128 */ }
            perform action a9 { doc /* using radiometric tracking, spacecraft telemetry timing, force models, and the latest approved maneuver history @S128 */ }
            perform action a10 { doc /* produces the Laser Retroreflector Window from the refined orbit solution and the approved station geometry constraints @S145 */ }
        }
        part orbitGeometry : OrbitGeometry {
            perform action a0 { doc /* gives longer visibility or lower elevation loss @S031 */ }
        }
        part orbitSolution : OrbitSolution {
            exhibit state modes {
                state s0 { doc /* stable @S134 */ }
            }
        }
        part orbitStateManagement : OrbitStateManagement {
            perform action a0 { doc /* remains under continuous control @S127 */ }
        }
        part orbitUpdates : OrbitUpdates {
            perform action a0 { doc /* materially change product fitness for use @S192 */ }
        }
        part otherGroundFunctions : OtherGroundFunctions;
        part pass : Pass {
            perform action a0 { doc /* begins @S079 */ }
        }
        part passPreparation : PassPreparation;
        part passReconstruction : PassReconstruction {
            perform action a0 { doc /* begins @S090 */ }
            perform action a1 { doc /* combines command history, received telemetry timing, ground station status, and operator log entries into a single operational narrative @S090 */ }
        }
        part payloadCalibrationTeam : PayloadCalibrationTeam {
            perform action a0 { doc /* owns payload performance monitoring, calibration parameter stewardship, and the technical assessment of product quality trends @S022 */ }
            perform action a1 { doc /* sends the Calibration Patch Bundle @S094 */ }
            perform action a2 { doc /* reviews planned calibration activities @S117 */ }
            perform action a3 { doc /* obtains predicted viewing geometry from flight dynamics products @S147 */ }
            perform action a4 { doc /* interpret instrument trends @S147 */ }
            perform action a5 { doc /* plan calibration activities @S147 */ }
            perform action a6 { doc /* maintains the approved calibration baseline @S161 */ }
            perform action a7 { doc /* reviews trend evidence @S161 */ }
            perform action a8 { doc /* may request a reprocessing campaign @S193 */ }
            perform action a9 { doc /* assesses product integrity @S211 */ }
            perform action a10 { doc /* validates that calibration operations are represented in the rehearsal schedule and that product quality decisions can be traced to approved engineering criteria @S237 */ }
        }
        part payloadDownlinkTraffic : PayloadDownlinkTraffic {
            perform action a0 { doc /* can continue during a single carrier outage @S055 */ }
        }
        part payloadImaging : PayloadImaging;
        part payloadProcessingFacility : PayloadProcessingFacility {
            perform action a0 { doc /* provides the operational environment for payload data processing, calibration control, product assessment, and distribution staging @S009 */ }
            perform action a1 { doc /* coordinates with Primary Processing Cluster and Backup Processing Cluster when a downlink allocation change alters expected processing load or delivery timing @S049 */ }
            perform action a2 { doc /* receives planning metadata needed to prepare downstream processing expectations without treating the planning schedule as a commitment to deliver products @S110 */ }
            perform action a3 { doc /* prepare downstream processing expectations @S110 */ }
            perform action a4 { doc /* without treating the planning schedule as a commitment to deliver products @S110 */ }
            perform action a5 { doc /* used by the Mission Control Center, Mission Planning System, and Payload Processing Facility @S141 */ }
            perform action a6 { doc /* transforming downlinked payload telemetry into image products that are traceable to the source telemetry and to the processing configuration used at execution time @S151 */ }
            perform action a7 { doc /* used at execution time @S151 */ }
            perform action a8 { doc /* is scheduled @S152 */ }
            perform action a9 { doc /* has delivered the product package, associated quality metadata, and checksum evidence required by the configured acceptance rule @S178 */ }
            perform action a10 { doc /* quarantine suspect input and derived output @S215 */ }
            perform action a11 { doc /* demonstrates that science product generation can be sustained during representative contact patterns without manual intervention beyond approved operator actions @S232 */ }
        }
        part persistentIdentifier : PersistentIdentifier {
            exhibit state modes {
                state s0 { doc /* stable @S179 */ }
            }
        }
        part physicalTopology : PhysicalTopology {
            perform action a0 { doc /* uses redundant terrestrial circuits between the Mission Control Center, the Flight Dynamics Facility, the Payload Processing Facility, and the Long Term Archive, with diverse carrier entrances where local infrastructure permits @S053 */ }
        }
        part plannedCalibrationActivities : PlannedCalibrationActivities {
            perform action a0 { doc /* share resources with revenue observations @S117 */ }
            perform action a1 { doc /* affect instrument configuration states @S117 */ }
        }
        part plannedSupport : PlannedSupport {
            perform action a0 { doc /* can proceed without adding contingency contact margin @S113 */ }
        }
        part planning : Planning;
        part planningCycle : PlanningCycle {
            perform action a0 { doc /* uses to determine feasible imaging windows and ground contacts @S106 */ }
            perform action a1 { doc /* determine feasible imaging windows and ground contacts @S106 */ }
        }
        part postBurnAssessmentSteps : PostBurnAssessmentSteps {
            perform action a0 { doc /* remain consistent @S097 */ }
        }
        part postPassClosureStep : PostPassClosureStep;
        part powerBalance : PowerBalance;
        part predictedRisk : PredictedRisk {
            perform action a0 { doc /* exceeds the mission threshold @S137 */ }
        }
        part previousAcquisitions : PreviousAcquisitions {
            perform action a0 { doc /* indicate that a requested geometry or instrument mode is unlikely to meet quality objectives @S124 */ }
        }
        part primaryMonthlyServiceReview : PrimaryMonthlyServiceReview {
            perform action a0 { doc /* compares actual performance against the accepted baseline @S246 */ }
            perform action a1 { doc /* records trend explanations for any measure that moves outside the watch band @S246 */ }
        }
        part primaryProcessingCluster : PrimaryProcessingCluster {
            perform action a0 { doc /* generates Level 0 products @S155 */ }
            perform action a1 { doc /* removing transfer framing @S155 */ }
            perform action a2 { doc /* ordering source packets @S155 */ }
            perform action a3 { doc /* preserving instrument time tags without radiometric or geometric correction @S155 */ }
            perform action a4 { doc /* cannot meet the processing window @S172 */ }
            perform action a5 { doc /* can pause nonessential production queues @S220 */ }
            perform action a6 { doc /* reserve compute capacity for validated recovery runs from known-good inputs @S220 */ }
            perform action a7 { doc /* are baselined with approved software versions, processing configurations, capacity reservations, monitoring checks, and rollback instructions @S247 */ }
            exhibit state modes {
                state s0 { doc /* unavailable @S150 */ }
            }
        }
        part processingLevel : ProcessingLevel {
            perform action a0 { doc /* records software build identifiers, calibration baseline identifiers, and ancillary input versions @S158 */ }
        }
        part processorCorrections : ProcessorCorrections {
            perform action a0 { doc /* materially change product fitness for use @S192 */ }
        }
        part productGeneration : ProductGeneration;
        part productLatency : ProductLatency;
        part productQualityDispositionTime : ProductQualityDispositionTime;
        part productQualityService : ProductQualityService {
            perform action a0 { doc /* performs automated and analyst-supported checks on generated products @S015 */ }
            perform action a1 { doc /* may add planning feedback @S124 */ }
            perform action a2 { doc /* checks each orbit solution for frame consistency, covariance reasonableness, time-tag continuity, and agreement with recent contact predictions @S130 */ }
            perform action a3 { doc /* uses the patch bundle @S162 */ }
            perform action a4 { doc /* update calibration applicability checks @S162 */ }
            perform action a5 { doc /* assigns quality flags for missing source packets, timing discontinuity, saturation, cloud screening uncertainty, geolocation residuals, and processing fallback @S165 */ }
            perform action a6 { doc /* produces the Product Hold List @S168 */ }
            perform action a7 { doc /* treats that marker as an input to its quality decision @S173 */ }
            perform action a8 { doc /* has set the public quality status @S181 */ }
            perform action a9 { doc /* has been evaluated @S181 */ }
            perform action a10 { doc /* records the reason for any reprocessing decision @S195 */ }
        }
        part products : Products {
            exhibit state modes {
                state s0 { doc /* delivery hold state @S167 */ }
                state s1 { doc /* discoverable only to authorized mission staff @S182 */ }
                state s2 { doc /* operational review @S182 */ }
            }
        }
        part protectedAccessRouters : ProtectedAccessRouters {
            perform action a0 { doc /* keep command and telemetry traffic separate from site administration traffic @S054 */ }
        }
        part protectiveActions : ProtectiveActions {
            perform action a0 { doc /* do not unintentionally interrupt a spacecraft contact @S076 */ }
            perform action a1 { doc /* prevent recovery of processing services @S076 */ }
        }
        part provenance : Provenance {
            perform action a0 { doc /* identifies the fallback execution path @S173 */ }
        }
        part qualityInvestigations : QualityInvestigations {
            perform action a0 { doc /* materially change product fitness for use @S192 */ }
        }
        part rateControls : RateControls {
            perform action a0 { doc /* protect mission operations from excessive external demand @S184 */ }
        }
        part rawSegments : RawSegments {
            exhibit state modes {
                state s0 { doc /* Corrupted @S154 */ }
                state s1 { doc /* incomplete @S154 */ }
            }
        }
        part rawTransfer : RawTransfer {
            perform action a0 { doc /* starts @S152 */ }
        }
        part readinessCheck : ReadinessCheck;
        part readinessEvidence : ReadinessEvidence {
            perform action a0 { doc /* showing that orbit products, maneuver screening, and conjunction coordination can be performed within the committed planning cycle @S231 */ }
        }
        part readinessReviewBoard : ReadinessReviewBoard {
            perform action a0 { doc /* verifies that each open action from launch and commissioning has an owner, a due date, and an accepted residual risk statement where closure is not required before service start @S228 */ }
        }
        part receivedStream : ReceivedStream;
        part receptionGaps : ReceptionGaps {
            perform action a0 { doc /* could affect downstream processing @S093 */ }
        }
        part recorderCapacity : RecorderCapacity;
        part recorderManagement : RecorderManagement;
        part recovery : Recovery {
            perform action a0 { doc /* prioritizes products with contractual latency commitments @S176 */ }
            perform action a1 { doc /* processes remaining scenes in acquisition order @S176 */ }
        }
        part recoveryReporting : RecoveryReporting;
        part redundantCapabilities : RedundantCapabilities {
            perform action a0 { doc /* can support the required mission service levels @S026 */ }
        }
        part redundantReferenceClocks : RedundantReferenceClocks;
        part registeredUsers : RegisteredUsers {
            perform action a0 { doc /* receive authorization scopes based on mission policy, contractual access rights, and applicable data licensing constraints @S185 */ }
        }
        part rehearsals : Rehearsals {
            perform action a0 { doc /* meet their objectives @S249 */ }
        }
        part releaseBlockingDefects : ReleaseBlockingDefects;
        part reprocessingDependence : ReprocessingDependence {
            perform action a0 { doc /* justifies low-latency access @S188 */ }
        }
        part requiredSeparationBetweenIncompatibleActivities : RequiredSeparationBetweenIncompatibleActivities;
        part responsibleTeams : ResponsibleTeams {
            perform action a0 { doc /* have signed the incident record @S226 */ }
        }
        part restoreProcedures : RestoreProcedures {
            exhibit state modes {
                state s0 { doc /* available @S189 */ }
            }
        }
        part retentionExceptions : RetentionExceptions;
        part retrievalTests : RetrievalTests {
            perform action a0 { doc /* meet the service objective @S243 */ }
        }
        part routineMissionService : RoutineMissionService {
            perform action a0 { doc /* begins @S227 */ }
        }
        part routineProduction : RoutineProduction {
            perform action a0 { doc /* has completed @S177 */ }
        }
        part routineReporting : RoutineReporting {
            perform action a0 { doc /* does not depend on informal judgment @S245 */ }
        }
        part routingIssues : RoutingIssues {
            perform action a0 { doc /* affect a contact @S087 */ }
        }
        part schedulingService : SchedulingService {
            perform action a0 { doc /* assigns eligible jobs to the Backup Processing Cluster @S172 */ }
            perform action a1 { doc /* using the same container image and rule set @S172 */ }
        }
        part screeningRules : ScreeningRules {
            perform action a0 { doc /* distinguish routine catalog monitoring from events requiring immediate operator notification @S136 */ }
        }
        part securityOrContinuityAnomaly : SecurityOrContinuityAnomaly {
            perform action a0 { doc /* could invalidate contact commitments @S216 */ }
            perform action a1 { doc /* conflict with manual recovery actions @S216 */ }
        }
        part sentinelVale : SentinelVale {
            perform action a0 { doc /* provide routine land, coastal, and cryosphere imaging products with predictable latency and documented data quality @S001 */ }
        }
        part siteDegradation : SiteDegradation {
            perform action a0 { doc /* persists @S221 */ }
        }
        part slewTime : SlewTime;
        part southSBandAntenna : SouthSBandAntenna {
            perform action a0 { doc /* provides the alternate S-band path @S029 */ }
            perform action a1 { doc /* connect to the Mission Control Center through protected access routers @S054 */ }
        }
        part spacecraft : Spacecraft;
        part spacecraftConfigurationChanges : SpacecraftConfigurationChanges {
            perform action a0 { doc /* require adjustment of future contacts or payload activities @S099 */ }
        }
        part spacecraftOperationsTeam : SpacecraftOperationsTeam {
            perform action a0 { doc /* owns spacecraft safety execution, contact conduct, command authorization support, and operational decision making during nominal and contingency conditions @S020 */ }
            perform action a1 { doc /* monitors spacecraft mode, power state, thermal margins, attitude indicators, command counters, onboard storage, and fault protection messages from the Mission Control Center consoles @S082 */ }
            perform action a2 { doc /* coordinate closely before orbit-control activities @S097 */ }
            perform action a3 { doc /* reviews late operational requests @S105 */ }
            perform action a4 { doc /* uses the Antenna Deicing Notice to assess whether planned support can proceed without adding contingency contact margin @S113 */ }
            perform action a5 { doc /* assess whether planned support can proceed without adding contingency contact margin @S113 */ }
            perform action a6 { doc /* receives a maneuver recommendation package that includes timing constraints and operational impacts @S137 */ }
            perform action a7 { doc /* receives maneuver recommendations with enough lead time to rehearse commanding, verify contingency actions, and coordinate contact coverage @S146 */ }
            perform action a8 { doc /* rehearse commanding @S146 */ }
            perform action a9 { doc /* verify contingency actions @S146 */ }
            perform action a10 { doc /* coordinate contact coverage @S146 */ }
            perform action a11 { doc /* uses the Pass Replay Packet @S198 */ }
            perform action a12 { doc /* confirm that archived downlink context can support anomaly reconstruction @S198 */ }
            perform action a13 { doc /* leads triage for spacecraft safety indicators @S209 */ }
            perform action a14 { doc /* conducts at least one integrated day-in-the-life rehearsal that includes pass preparation, commanding discipline, telemetry surveillance, anomaly declaration, and recovery reporting @S235 */ }
        }
        part spacecraftSystemsEngineer : SpacecraftSystemsEngineer {
            perform action a0 { doc /* interprets health telemetry @S086 */ }
            perform action a1 { doc /* confirms that subsystem states remain within flight rules @S086 */ }
            perform action a2 { doc /* records any anomaly context needed by subsystem specialists @S086 */ }
        }
        part staffingRosters : StaffingRosters {
            exhibit state modes {
                state s0 { doc /* under configuration control @S227 */ }
            }
        }
        part standardLevel1Products : StandardLevel1Products {
            exhibit state modes {
                state s0 { doc /* online @S188 */ }
            }
        }
        part stationDeliveryFiles : StationDeliveryFiles {
            perform action a0 { doc /* arrive with an accompanying manifest @S152 */ }
        }
        part stationOperators : StationOperators {
            perform action a0 { doc /* notify the Mission Control Center when local constraints could affect an approved contact, including equipment warm-up limits, access restrictions, or unexpected maintenance activity @S043 */ }
        }
        part stationOutages : StationOutages {
            perform action a0 { doc /* require adjustment of future contacts or payload activities @S099 */ }
        }
        part subMillisecondAlignment : SubMillisecondAlignment;
        part subsystemSpecialists : SubsystemSpecialists {
            perform action a0 { doc /* are not expected to staff every live contact @S095 */ }
            perform action a1 { doc /* must be reachable during planned critical activities and whenever a console operator declares an off-nominal condition @S095 */ }
        }
        part sunAngleLimits : SunAngleLimits;
        part supportTeams : SupportTeams {
            perform action a0 { doc /* confirm on-call coverage @S249 */ }
        }
        part svalbardXBandAntenna : SvalbardXBandAntenna {
            perform action a0 { doc /* extends northern contact opportunities @S031 */ }
            perform action a1 { doc /* use dual wide area paths toward the Payload Processing Facility @S055 */ }
            perform action a2 { doc /* support high-rate telemetry reception @S078 */ }
        }
        part telemetry : Telemetry {
            perform action a0 { doc /* does not match the expected configuration @S084 */ }
            perform action a1 { doc /* indicates a possible onboard fault @S098 */ }
        }
        part telemetryCompleteness : TelemetryCompleteness;
        part telemetryEngineer : TelemetryEngineer {
            perform action a0 { doc /* verifies reception quality, frame loss, latency, and stream continuity @S085 */ }
            perform action a1 { doc /* advises the console lead when degraded link conditions could affect command confidence @S085 */ }
        }
        part telemetryIngestService : TelemetryIngestService {
            perform action a0 { doc /* receives spacecraft telemetry from scheduled contacts @S013 */ }
            perform action a1 { doc /* makes it available to operations, engineering analysis, and downstream processing functions @S013 */ }
            perform action a2 { doc /* receives contact status and data-flow indicators @S048 */ }
            perform action a3 { doc /* accepts real-time frames @S080 */ }
            perform action a4 { doc /* validates basic framing and time continuity @S080 */ }
            perform action a5 { doc /* records reception metadata needed for later operational review @S080 */ }
            perform action a6 { doc /* produces the Pass Replay Packet @S081 */ }
            perform action a7 { doc /* writes accepted raw data to immutable staging storage @S153 */ }
            perform action a8 { doc /* records the session identifier used by downstream processors @S153 */ }
            perform action a9 { doc /* are isolated from the nominal queue @S154 */ }
        }
        part telemetryReception : TelemetryReception {
            perform action a0 { doc /* continues where safe @S218 */ }
        }
        part telemetrySurveillance : TelemetrySurveillance;
        part thermalRecoveryTime : ThermalRecoveryTime;
        part timingConstraints : TimingConstraints;
        part trackingArcs : TrackingArcs {
            perform action a0 { doc /* include measurements associated with the North S-Band Antenna, South S-Band Antenna, Kiruna X-Band Antenna, and Svalbard X-Band Antenna @S129 */ }
        }
        part trackingExpectations : TrackingExpectations {
            perform action a0 { doc /* remain consistent @S097 */ }
        }
        part trafficSupportingTheOrbitDeterminationEngine : TrafficSupportingTheOrbitDeterminationEngine {
            perform action a0 { doc /* supporting the Orbit Determination Engine @S064 */ }
        }
        part unresolvedAnomalyAge : UnresolvedAnomalyAge;
        part unsafeOutdoorConditions : UnsafeOutdoorConditions {
            perform action a0 { doc /* can still make an antenna unavailable for service @S047 */ }
        }
        part updatedStateVectors : UpdatedStateVectors {
            perform action a0 { doc /* change predicted acquisition times or imaging geometry beyond agreed thresholds @S144 */ }
        }
        part userServicesPortal : UserServicesPortal {
            perform action a0 { doc /* provides the controlled external interface for product search, ordering, status communication, and user support workflows @S018 */ }
            perform action a1 { doc /* records the request state @S104 */ }
            perform action a2 { doc /* provides search, preview, order, and download functions through a browser interface and documented machine interfaces @S183 */ }
            perform action a3 { doc /* displays a service status message @S201 */ }
            perform action a4 { doc /* communicates confirmed service impacts in operational terms @S225 */ }
            perform action a5 { doc /* avoids publishing speculative root cause information @S225 */ }
            perform action a6 { doc /* publishing speculative root cause information @S225 */ }
            perform action a7 { doc /* uses the Product Hold List @S239 */ }
            perform action a8 { doc /* prevent release of affected products until the applicable hold condition has been cleared @S239 */ }
        }
        part users : Users {
            perform action a0 { doc /* can distinguish scientific updates from operational recovery actions @S195 */ }
        }
        part validationEvidence : ValidationEvidence {
            perform action a0 { doc /* shows a systematic radiometric or geometric issue @S193 */ }
        }
        part validityInterval : ValidityInterval;
        part visibilityGeometry : VisibilityGeometry {
            perform action a0 { doc /* justify their use @S078 */ }
        }
        part weather : Weather {
            perform action a0 { doc /* affect a contact @S087 */ }
        }
        part wideAreaConnectivityDesign : WideAreaConnectivityDesign {
            perform action a0 { doc /* extends the ground network management practices from the scheduling domain into continuous transport control across all operational sites @S052 */ }
        }
        flow f0 of OrbitAnalysisItem from flightDynamicsFacility to otherGroundFunctions { doc /* @S008 */ }
        flow f1 of ManeuverPlanningSupportItem from flightDynamicsFacility to otherGroundFunctions { doc /* @S008 */ }
        flow f2 of AccessPredictionItem from flightDynamicsFacility to otherGroundFunctions { doc /* @S008 */ }
        flow f3 of NavigationProductsItem from flightDynamicsFacility to otherGroundFunctions { doc /* @S008 */ }
        flow f4 of SpacecraftTelemetryItem from spacecraft to telemetryIngestService { doc /* @S013 */ }
        flow f5 of SpacecraftTelemetryItem from telemetryIngestService to operations { doc /* @S013 */ }
        flow f6 of SpacecraftTelemetryItem from telemetryIngestService to engineeringAnalysis { doc /* @S013 */ }
        flow f7 of SpacecraftTelemetryItem from telemetryIngestService to downstreamProcessingFunctions { doc /* @S013 */ }
        flow f8 of ControlledOrbitKnowledgeItem from orbitDeterminationEngine to planning { doc /* @S014 */ }
        flow f9 of ControlledOrbitKnowledgeItem from orbitDeterminationEngine to productGeneration { doc /* @S014 */ }
        flow f10 of VisibilityPredictionsItem from flightDynamicsFacility to planning { doc /* @S040 */ }
        flow f11 of AntennaPointingSupportProductsItem from flightDynamicsFacility to planning { doc /* @S040 */ }
        flow f12 of LocalConstraintsItem from stationOperators to missionControlCenter { doc /* @S043 */ }
        flow f13 of AntennaStatusItem from networkControlSystem to missionControlCenter { doc /* @S079 */ }
        flow f14 of LinkConfigurationItem from networkControlSystem to missionControlCenter { doc /* @S079 */ }
        flow f15 of TimingReferencesItem from networkControlSystem to missionControlCenter { doc /* @S079 */ }
        flow f16 of RoutingReadinessItem from networkControlSystem to missionControlCenter { doc /* @S079 */ }
        flow f17 of DeviationsFromExpectedStateItem from consoleDisplays to operators { doc /* @S083 */ }
        flow f18 of OperationalConstraintsItem from missionControlCenter to missionPlanningSystem { doc /* @S099 */ }
        flow f19 of OrbitPredictionsItem from flightDynamicsFacility to planningCycle { doc /* @S106 */ }
        flow f20 of VisibilityAssumptionsItem from flightDynamicsFacility to planningCycle { doc /* @S106 */ }
        flow f21 of AntennaDeicingNoticeItem from groundNetworkManager to spacecraftOperationsTeam { doc /* @S113 */ }
        flow f22 of CommandPreparationPackageItem from missionPlanningSystem to commandEngineeringWorkflow { doc /* @S118 */ }
        flow f23 of RoutineEphemeridesItem from flightDynamicsFacility to missionControlCenter { doc /* @S141 */ }
        flow f24 of RoutineEphemeridesItem from flightDynamicsFacility to missionPlanningSystem { doc /* @S141 */ }
        flow f25 of RoutineEphemeridesItem from flightDynamicsFacility to payloadProcessingFacility { doc /* @S141 */ }
        flow f26 of EventPredictionsItem from flightDynamicsFacility to missionControlCenter { doc /* @S141 */ }
        flow f27 of EventPredictionsItem from flightDynamicsFacility to missionPlanningSystem { doc /* @S141 */ }
        flow f28 of EventPredictionsItem from flightDynamicsFacility to payloadProcessingFacility { doc /* @S141 */ }
        flow f29 of ManeuverRecommendationsItem from flightDynamicsFacility to spacecraftOperationsTeam { doc /* @S146 */ }
        flow f30 of AcceptedRawDataItem from telemetryIngestService to immutableStagingStorage { doc /* @S153 */ }
        flow f31 of WhetherRecoveryRetransmissionOrDiscardIsRequiredItem from operatorDisplay to operatorDisplay { doc /* @S154 */ }
        flow f32 of CalibrationPatchBundleItem from payloadCalibrationTeam to productQualityService { doc /* @S162 */ }
        flow f33 of SecurityExceptionTicketItem from cybersecurityDesk to networkControlSystem { doc /* @S170 */ }
        flow f34 of ProvenanceItem from backupProcessingCluster to productQualityService { doc /* @S173 */ }
        flow f35 of ProductPackageItem from payloadProcessingFacility to longTermArchive { doc /* @S178 */ }
        flow f36 of AssociatedQualityMetadataItem from payloadProcessingFacility to longTermArchive { doc /* @S178 */ }
        flow f37 of ChecksumEvidenceItem from payloadProcessingFacility to longTermArchive { doc /* @S178 */ }
        flow f38 of CatalogueRecordsItem from longTermArchive to userServicesPortal { doc /* @S181 */ }
        flow f39 of OrbitQualityStateChangesItem from flightDynamicsFacility to archiveOperationsQueue { doc /* @S194 */ }
        flow f40 of ConfigurationChangesItem from networkControlSystem to operationalLog { doc /* @S205 */ }
        flow f41 of StarTrackerMaskFileItem from flightDynamicsFacility to commandValidationGateway { doc /* @S206 */ }
        flow f42 of StorageWatermarkSnapshotItem from longTermArchive to backupProcessingCluster { doc /* @S241 */ }
    }
    requirement def R0 { doc /* interfaces are required for operations @S003 */ subject s : Interfaces; }
    requirement def R1 { doc /* operational evidence required for traceability @S017 */ subject s : OperationalEvidence; }
    requirement def R2 { doc /* human authorization remains required for spacecraft commanding and major configuration changes @S025 */ subject s : HumanAuthorization; }
    requirement def R3 { doc /* contacts that require conservative link margins @S028 */ subject s : Contacts; }
    requirement def R4 { doc /* sub-millisecond alignment is required for correlation @S069 */ subject s : SubMillisecondAlignment; }
    requirement def R5 { doc /* the received stream must be reconstructed for engineering review @S081 */ subject s : ReceivedStream; }
    requirement def R6 { doc /* operators must identify safety trends while a contact is still available @S083 */ subject s : Operators; }
    requirement def R7 { doc /* additional engineering analysis is required @S091 */ subject s : EngineeringAnalysis; }
    requirement def R8 { doc /* they must be reachable during planned critical activities and whenever a console operator declares an off-nominal condition @S095 */ subject s : SubsystemSpecialists; }
    requirement def R9 { doc /* Final approval requires concurrence from the Mission Control Center and the Spacecraft Operations Team before any command stack is placed in the queue for the next authorized uplink opportunity. @S126 */ subject s : FinalApproval; }
    requirement def R10 { doc /* events requiring immediate operator notification @S136 */ subject s : Events; }
    requirement def R11 { doc /* Bluebell requires that each flight dynamics delivery include a validity interval, coordinate frame, generation time, and operational use statement. @S140 */ subject s : FlightDynamicsDelivery; }
    requirement def R12 { doc /* shows whether recovery, retransmission, or discard is required @S154 */ subject s : OperatorDisplay; }
    requirement def R13 { doc /* release blocking defects must be tracked across scenes and processing levels @S168 */ subject s : ReleaseBlockingDefects; }
    requirement def R14 { doc /* Lantern shall preserve the last validated routing configuration and reject unreviewed changes while payload product transfers are active. @S171 */ subject s : NetworkControlSystem; }
    requirement def R15 { doc /* Retention exceptions require traceability to the approving authority, the affected product classes, and the expected operational impact. @S191 */ subject s : RetentionExceptions; }
    requirement def R16 { doc /* Forgehouse must quarantine suspect input and derived output when product lineage cannot be proven during an active anomaly investigation. @S215 */ subject s : PayloadProcessingFacility; }
    requirement def R17 { doc /* closure is not required before service start @S228 */ subject s : OpenAction; }
    requirement def R18 { doc /* the approved authorization state, validation result, and operator acknowledgment required for routine service @S242 */ subject s : CommandRequest; }
}
