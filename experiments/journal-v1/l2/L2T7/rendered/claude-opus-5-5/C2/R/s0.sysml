package L2Model {
    item def AcceptedOrbitFilesItem { doc /* @S142 */ }
    item def AcceptedRawDataItem { doc /* @S153 */ }
    item def AntennaDeicingNoticeItem { doc /* @S113 */ }
    item def AntennaPointingSupportProductsItem { doc /* @S040 */ }
    item def AntennaStatusLinkConfigurationTimingReferencesAndRoutingReadinessItem { doc /* @S079 */ }
    item def CalibrationPatchBundleItem { doc /* @S162 */ }
    item def ChecksumEvidenceItem { doc /* @S178 */ }
    item def CommandPreparationPackageItem { doc /* @S118 */ }
    item def CommandUplinkItem { doc /* @S028 */ }
    item def ContactStatusItem { doc /* @S048 */ }
    item def DataFlowIndicatorsItem { doc /* @S048 */ }
    item def DegradedLinkConditionsAdviceItem { doc /* @S085 */ }
    item def DopplerResidualReportItem { doc /* @S131 */ }
    item def EligibleJobsItem { doc /* @S172 */ }
    item def EphemerisDeltaNoteItem { doc /* @S240 */ }
    item def HighRatePayloadDownlinkItem { doc /* @S030 */ }
    item def LaserRetroreflectorWindowItem { doc /* @S207 */ }
    item def LocalConstraintsItem { doc /* @S043 */ }
    item def LowRateTelemetryItem { doc /* @S028 */ }
    item def ManeuverRecommendationsItem { doc /* @S146 */ }
    item def OperationalConstraintsItem { doc /* @S099 */ }
    item def OrbitPredictionsItem { doc /* @S106 */ }
    item def OrbitQualityStateChangesItem { doc /* @S194 */ }
    item def PayloadDownlinkTrafficItem { doc /* @S055 */ }
    item def PlanningMetadataItem { doc /* @S110 */ }
    item def PredictedViewingGeometryItem { doc /* @S147 */ }
    item def ProductHoldListItem { doc /* @S239 */ }
    item def ProductPackageItem { doc /* @S178 */ }
    item def ProvenanceMarkerItem { doc /* @S173 */ }
    item def QualityMetadataItem { doc /* @S178 */ }
    item def RoutineEphemeridesAndEventPredictionsItem { doc /* @S141 */ }
    item def SecurityExceptionTicketItem { doc /* @S170 */ }
    item def SpacecraftModePowerStateThermalMarginsAttitudeIndicatorsCommandCountersOnboardStorageAndFaultProtectionMessagesItem { doc /* @S082 */ }
    item def SpacecraftTelemetryItem { doc /* @S013 */ }
    item def StarTrackerMaskFileItem { doc /* @S206 */ }
    item def StorageWatermarkSnapshotItem { doc /* @S241 */ }
    item def TransfersItem { doc /* @S065 */ }
    item def VisibilityAssumptionsItem { doc /* @S106 */ }
    item def VisibilityPredictionsItem { doc /* @S040 */ }
    part def AccountableOwners { doc /* @S249 */ }
    part def AntennaSiteEquipment { doc /* @S070 */ }
    part def ArchiveAvailability { doc /* @S244 */ }
    part def ArchiveOperationsQueue { doc /* @S194 */ }
    part def BackupProcessingCluster { doc /* @S004,S016,S066,S150,S172,S173,S241,S247 */ }
    part def CatalogueRecords { doc /* @S197 */ }
    part def CommandStack { doc /* @S126 */ }
    part def CommandValidationGateway { doc /* @S004,S012,S119,S120,S121,S143,S206,S242 */ }
    part def CommandValidationTimeliness { doc /* @S244 */ }
    part def ConsoleLead { doc /* @S084,S085 */ }
    part def ConsoleOperator { doc /* @S095 */ }
    part def ContactSuccessRate { doc /* @S244 */ }
    part def CybersecurityDesk { doc /* @S023,S074,S076,S125,S200,S204,S212,S238 */ }
    part def DownloadServices { doc /* @S184 */ }
    part def DraftActivitySchedule { doc /* @S108,S109 */ }
    part def EngineeringTeams { doc /* @S218 */ }
    part def ExternalInterfaces { doc /* @S199 */ }
    part def FlightDynamicsDelivery { doc /* @S140 */ }
    part def FlightDynamicsFacility { doc /* @S004,S008,S040,S068,S106,S132,S139,S141,S142,S147,S194,S206,S231 */ }
    part def FlightDynamicsTeam { doc /* @S021,S071,S088,S097,S116,S131,S134,S136,S144,S146,S210,S236,S240 */ }
    part def GroundNetworkManager { doc /* @S019,S038,S044,S060,S067,S076,S087,S112,S113,S170,S209,S222,S234 */ }
    part def GroundSegment { doc /* @S002,S004,S005,S218,S219 */ }
    part def GroundStationEstate { doc /* @S027 */ }
    part def HelpDeskResponsiveness { doc /* @S244 */ }
    part def HousekeepingActivities { doc /* @S108 */ }
    part def ImmutableStagingStorage { doc /* @S153 */ }
    part def IncidentLead { doc /* @S225 */ }
    part def KeyPerformanceIndicator { doc /* @S244 */ }
    part def KirunaXBandAntenna { doc /* @S005,S027,S030,S055,S078 */ }
    part def LocalStationTeams { doc /* @S042 */ }
    part def LongTermArchive { doc /* @S004,S017,S065,S149,S160,S174,S178,S180,S187,S196,S241,S243 */ }
    part def MissionControlCenter { doc /* @S004,S007,S032,S043,S056,S068,S077,S079,S082,S083,S093,S099,S100,S118,S141,S175,S203,S217,S230 */ }
    part def MissionManagement { doc /* @S176,S186 */ }
    part def MissionPlanningSystem { doc /* @S004,S011,S034,S040,S099,S102,S107,S110,S114,S118,S141,S142,S207,S216,S240 */ }
    part def NetworkControlSystem { doc /* @S004,S010,S033,S048,S056,S072,S079,S148,S170,S171,S205,S233 */ }
    part def NorthSBandAntenna { doc /* @S005,S027,S028,S054,S078 */ }
    part def OperationalReadinessReview { doc /* @S227 */ }
    part def OperatorDisplay { doc /* @S154 */ }
    part def Operators { doc /* @S098,S213 */ }
    part def OrbitDeterminationEngine { doc /* @S004,S014,S041,S089,S123,S128,S131,S145,S207 */ }
    part def PayloadCalibrationTeam { doc /* @S022,S094,S117,S147,S161,S162,S193,S211,S237 */ }
    part def PayloadImaging { doc /* @S108 */ }
    part def PayloadProcessingFacility { doc /* @S004,S009,S049,S055,S110,S141,S150,S151,S178,S215,S232 */ }
    part def PhysicalTopology { doc /* @S053 */ }
    part def PlanningCycle { doc /* @S106 */ }
    part def PrimaryMonthlyServiceReview { doc /* @S246 */ }
    part def PrimaryProcessingCluster { doc /* @S004,S065,S150,S155,S220,S247 */ }
    part def ProcessingLevel { doc /* @S158 */ }
    part def Product { doc /* @S167 */ }
    part def ProductLatency { doc /* @S244 */ }
    part def ProductQualityDispositionTime { doc /* @S244 */ }
    part def ProductQualityService { doc /* @S004,S015,S124,S130,S162,S165,S168,S173,S181,S195,S239 */ }
    part def ProtectedAccessRouters { doc /* @S054 */ }
    part def ReadinessReviewBoard { doc /* @S228 */ }
    part def RecorderManagement { doc /* @S108 */ }
    part def RedundantReferenceClocks { doc /* @S068 */ }
    part def RedundantTerrestrialCircuits { doc /* @S053 */ }
    part def RegisteredUsers { doc /* @S185 */ }
    part def ResponsibleTeams { doc /* @S226 */ }
    part def SchedulingService { doc /* @S172 */ }
    part def SouthSBandAntenna { doc /* @S005,S027,S029,S054,S078 */ }
    part def Spacecraft { doc /* @S013,S028,S030 */ }
    part def SpacecraftOperationsTeam { doc /* @S020,S072,S082,S083,S097,S105,S113,S137,S146,S198,S209,S235 */ }
    part def SpacecraftSystemsEngineer { doc /* @S086 */ }
    part def StationOperators { doc /* @S043 */ }
    part def SubsystemSpecialists { doc /* @S095 */ }
    part def SupportTeams { doc /* @S249 */ }
    part def SvalbardXBandAntenna { doc /* @S005,S027,S031,S055,S078 */ }
    part def TelemetryCompleteness { doc /* @S244 */ }
    part def TelemetryEngineer { doc /* @S085 */ }
    part def TelemetryIngestService { doc /* @S004,S013,S048,S080,S081,S122,S152,S153 */ }
    part def UnresolvedAnomalyAge { doc /* @S244 */ }
    part def UserServicesPortal { doc /* @S004,S018,S101,S104,S181,S183,S201,S225,S239 */ }
    part def WideAreaConnectivityDesign { doc /* @S052 */ }
    part system {
        part accountableOwners : AccountableOwners {
            perform action a0 { doc /* open risks are acknowledged @S249 */ }
        }
        part antennaSiteEquipment : AntennaSiteEquipment {
            perform action a0 { doc /* validates time against independent local references @S070 */ }
        }
        part archiveAvailability : ArchiveAvailability;
        part archiveOperationsQueue : ArchiveOperationsQueue;
        part backupProcessingCluster : BackupProcessingCluster {
            perform action a0 { doc /* receives lower routing preference during normal operations @S066 */ }
            perform action a1 { doc /* supports product generation with the same validation checks and distribution rules @S150 */ }
            perform action a2 { doc /* writes provenance that identifies the fallback execution path @S173 */ }
            perform action a3 { doc /* uses the Storage Watermark Snapshot to verify that recovery capacity is sufficient @S241 */ }
            perform action a4 { doc /* accepts routine standby responsibility @S241 */ }
            perform action a5 { doc /* are baselined with approved software versions, processing configurations, capacity reservations, monitoring checks, and rollback instructions @S247 */ }
            exhibit state modes {
                state s0 { doc /* controlled failover @S016 */ }
                state s1 { doc /* normal operations @S066 */ }
            }
        }
        part catalogueRecords : CatalogueRecords {
            perform action a0 { doc /* show processing baseline, sensing time, publication time, quality status, and replacement relationships @S197 */ }
        }
        part commandStack : CommandStack;
        part commandValidationGateway : CommandValidationGateway {
            perform action a0 { doc /* provides the formal barrier between planning outputs and command release @S012 */ }
            perform action a1 { doc /* enforces rule checks @S012 */ }
            perform action a2 { doc /* commands are made available for uplink @S012 */ }
            perform action a3 { doc /* performs independent validation of command stacks @S119 */ }
            perform action a4 { doc /* checks syntax, timing, parameter ranges, sequencing rules, spacecraft mode compatibility, and consistency with the approved schedule baseline @S120 */ }
            perform action a5 { doc /* rejects command stacks @S121 */ }
            perform action a6 { doc /* checks maneuver command parameters against the screened burn plan @S143 */ }
            perform action a7 { doc /* allowing the command stack to proceed @S143 */ }
            perform action a8 { doc /* accepts the mask file @S206 */ }
            perform action a9 { doc /* rejects any command request that lacks the approved authorization state, validation result, and operator acknowledgment @S242 */ }
        }
        part commandValidationTimeliness : CommandValidationTimeliness;
        part consoleLead : ConsoleLead {
            perform action a0 { doc /* declaring pass status @S084 */ }
            perform action a1 { doc /* authorizing planned command execution through the Command Validation Gateway @S084 */ }
            perform action a2 { doc /* pausing the activity @S084 */ }
        }
        part consoleOperator : ConsoleOperator {
            perform action a0 { doc /* declares an off-nominal condition @S095 */ }
        }
        part contactSuccessRate : ContactSuccessRate;
        part cybersecurityDesk : CybersecurityDesk {
            perform action a0 { doc /* provides continuous security monitoring, operational security guidance, and escalation support @S023 */ }
            perform action a1 { doc /* sends a Security Exception Ticket @S074 */ }
            perform action a2 { doc /* coordinate before blocking traffic @S076 */ }
            perform action a3 { doc /* reviews command preparation exceptions @S125 */ }
            perform action a4 { doc /* reviews public interface changes @S200 */ }
            perform action a5 { doc /* confirm authentication, logging, and abuse-control requirements are satisfied @S200 */ }
            perform action a6 { doc /* reviews privileged access daily @S204 */ }
            perform action a7 { doc /* challenges dormant, shared, or unexplained accounts @S204 */ }
            perform action a8 { doc /* assumes coordination authority @S212 */ }
            perform action a9 { doc /* participates in the final exercise @S238 */ }
            perform action a10 { doc /* validating alert routing, privileged access review, and incident coordination with operations management @S238 */ }
        }
        part downloadServices : DownloadServices {
            perform action a0 { doc /* support resumable transfer, integrity verification, and rate controls @S184 */ }
        }
        part draftActivitySchedule : DraftActivitySchedule {
            perform action a0 { doc /* accounts for downlink opportunities through the Kiruna X-Band Antenna and Svalbard X-Band Antenna @S109 */ }
        }
        part engineeringTeams : EngineeringTeams {
            perform action a0 { doc /* focus on stabilizing observability and protecting evidence @S218 */ }
        }
        part externalInterfaces : ExternalInterfaces {
            perform action a0 { doc /* expose catalogue search, subscription notification, product ordering, and download status @S199 */ }
        }
        part flightDynamicsDelivery : FlightDynamicsDelivery;
        part flightDynamicsFacility : FlightDynamicsFacility {
            perform action a0 { doc /* provides orbit analysis @S008 */ }
            perform action a1 { doc /* provides maneuver planning support @S008 */ }
            perform action a2 { doc /* provides access prediction @S008 */ }
            perform action a3 { doc /* provides navigation products @S008 */ }
            perform action a4 { doc /* provides visibility predictions and antenna pointing support products to the planning process @S040 */ }
            perform action a5 { doc /* provides orbit predictions and visibility assumptions @S106 */ }
            perform action a6 { doc /* maintains the authoritative orbit catalog @S132 */ }
            perform action a7 { doc /* records the modeling assumptions applied to each accepted solution @S132 */ }
            perform action a8 { doc /* verifying predicted bright-object exclusions against the current attitude plan @S139 */ }
            perform action a9 { doc /* sends the Star Tracker Mask File @S139 */ }
            perform action a10 { doc /* distributes routine ephemerides and event predictions @S141 */ }
            perform action a11 { doc /* publishes orbit quality state changes to the archive operations queue @S194 */ }
            perform action a12 { doc /* provides readiness evidence @S231 */ }
        }
        part flightDynamicsTeam : FlightDynamicsTeam {
            perform action a0 { doc /* owns flight dynamics analysis, orbit maintenance recommendations, and operational coordination for navigation-related constraints @S021 */ }
            perform action a1 { doc /* monitors timing quality alongside orbit support metrics @S071 */ }
            perform action a2 { doc /* uses tracking measurements and validated time tags @S088 */ }
            perform action a3 { doc /* support orbit assessment @S088 */ }
            perform action a4 { doc /* coordinate closely before orbit-control activities @S097 */ }
            perform action a5 { doc /* reviews cases where orbital uncertainty or contact geometry could reduce the execution margin @S116 */ }
            perform action a6 { doc /* uses the residual report to separate station-related tracking biases from dynamic model errors @S131 */ }
            perform action a7 { doc /* accepting an orbit solution @S131 */ }
            perform action a8 { doc /* computes expected state change, execution tolerance, recovery strategy, and the earliest time @S134 */ }
            perform action a9 { doc /* maintains screening rules @S136 */ }
            perform action a10 { doc /* produces the Ephemeris Delta Note @S144 */ }
            perform action a11 { doc /* assesses orbit and timing effects @S210 */ }
            perform action a12 { doc /* conducts a separate rehearsal for missed tracking data and late orbit update availability @S236 */ }
        }
        part groundNetworkManager : GroundNetworkManager {
            perform action a0 { doc /* coordinates availability of the antenna assets @S019 */ }
            perform action a1 { doc /* confirms that scheduled contact opportunities are compatible with station readiness and maintenance constraints @S019 */ }
            perform action a2 { doc /* arbitrates unresolved contact conflicts @S038 */ }
            perform action a3 { doc /* verifies that station commitments remain consistent with maintenance windows and staffing limits @S038 */ }
            perform action a4 { doc /* issues the Antenna Deicing Notice @S044 */ }
            perform action a5 { doc /* determines that a maintenance condition could cause route oscillation @S060 */ }
            perform action a6 { doc /* verifies carrier performance @S067 */ }
            perform action a7 { doc /* checks routing state, packet loss, queue depth, and security inspection delays @S067 */ }
            perform action a8 { doc /* declaring a mission-impacting network condition @S067 */ }
            perform action a9 { doc /* coordinate before blocking traffic @S076 */ }
            perform action a10 { doc /* accountable for antenna assignment, ground link availability, and coordination with site operations @S087 */ }
            perform action a11 { doc /* confirms that planned station use is compatible with network maintenance windows @S112 */ }
            perform action a12 { doc /* leads triage for antenna, link, and site-service indicators @S209 */ }
            perform action a13 { doc /* Cross-site failover is coordinated @S222 */ }
            perform action a14 { doc /* accepts the antenna readiness baseline @S234 */ }
        }
        part groundSegment : GroundSegment {
            perform action a0 { doc /* plan spacecraft activities @S002 */ }
            perform action a1 { doc /* acquire mission data @S002 */ }
            perform action a2 { doc /* maintain safe spacecraft operations @S002 */ }
            perform action a3 { doc /* generate user products @S002 */ }
            perform action a4 { doc /* preserve mission records @S002 */ }
            perform action a5 { doc /* provide controlled access to services @S002 */ }
            perform action a6 { doc /* prioritizes spacecraft safety contacts, time-critical telemetry capture, core orbit support, and protection of unrecoverable payload data @S219 */ }
            exhibit state modes {
                state s0 { doc /* essential-service mode @S219 */ }
                state s1 { doc /* monitor-only mode @S218 */ }
            }
        }
        part groundStationEstate : GroundStationEstate;
        part helpDeskResponsiveness : HelpDeskResponsiveness;
        part housekeepingActivities : HousekeepingActivities;
        part immutableStagingStorage : ImmutableStagingStorage;
        part incidentLead : IncidentLead {
            perform action a0 { doc /* approves release @S225 */ }
        }
        part keyPerformanceIndicator : KeyPerformanceIndicator;
        part kirunaXBandAntenna : KirunaXBandAntenna {
            perform action a0 { doc /* is assigned primarily to high-rate payload downlink during European visibility periods @S030 */ }
            perform action a1 { doc /* is planned with margin for setup, carrier acquisition, and post-contact checks @S030 */ }
            perform action a2 { doc /* use dual wide area paths toward the Payload Processing Facility @S055 */ }
            perform action a3 { doc /* support high-rate telemetry reception @S078 */ }
        }
        part localStationTeams : LocalStationTeams {
            perform action a0 { doc /* antenna pre-pass configuration @S042 */ }
            perform action a1 { doc /* frequency standard verification @S042 */ }
            perform action a2 { doc /* time correlation checks @S042 */ }
            perform action a3 { doc /* safety interlocks @S042 */ }
            perform action a4 { doc /* logging of any local anomalies @S042 */ }
        }
        part longTermArchive : LongTermArchive {
            perform action a0 { doc /* is the authoritative repository for preserved mission data, generated products, processing records, and operational evidence @S017 */ }
            perform action a1 { doc /* retains released orbit products, covariance data, maneuver records, and quality decisions @S149 */ }
            perform action a2 { doc /* sends the Storage Watermark Snapshot @S174 */ }
            perform action a3 { doc /* daily storage assessment @S174 */ }
            perform action a4 { doc /* Archive admission begins @S178 */ }
            perform action a5 { doc /* stores object content separately from searchable metadata @S180 */ }
            perform action a6 { doc /* retains raw acquisition data @S187 */ }
            perform action a7 { doc /* preserves the replaced product version @S196 */ }
            perform action a8 { doc /* preserves the accepted archive baseline @S243 */ }
            perform action a9 { doc /* confirms that retrieval tests meet the service objective @S243 */ }
        }
        part missionControlCenter : MissionControlCenter {
            perform action a0 { doc /* real-time spacecraft operations @S007 */ }
            perform action a1 { doc /* pass supervision @S007 */ }
            perform action a2 { doc /* anomaly response @S007 */ }
            perform action a3 { doc /* release of validated command activities @S007 */ }
            perform action a4 { doc /* maintains the operational contact schedule @S032 */ }
            perform action a5 { doc /* uses it as the controlling reference for console staffing, command readiness, and telemetry coverage @S032 */ }
            perform action a6 { doc /* hosts the primary routing policy point @S056 */ }
            perform action a7 { doc /* treats every scheduled contact as a controlled operational activity @S077 */ }
            perform action a8 { doc /* readiness check @S077 */ }
            perform action a9 { doc /* live monitoring period @S077 */ }
            perform action a10 { doc /* post-pass closure step @S077 */ }
            perform action a11 { doc /* emphasize deviations from expected state @S083 */ }
            perform action a12 { doc /* coordinates with the Payload Processing Facility @S093 */ }
            perform action a13 { doc /* records unresolved actions, open engineering questions, and expected specialist responses @S100 */ }
            perform action a14 { doc /* maintains the authority boundary for routine spacecraft operations @S203 */ }
            perform action a15 { doc /* confirms that elevated access is tied to an approved shift role and a time-limited operational need @S203 */ }
            perform action a16 { doc /* Continuity modes are declared @S217 */ }
            perform action a17 { doc /* demonstrates continuous console coverage for the agreed service hours @S230 */ }
            perform action a18 { doc /* proves that shift handover logs contain the state needed by the incoming controller @S230 */ }
        }
        part missionManagement : MissionManagement {
            perform action a0 { doc /* approves a different backlog rule @S176 */ }
            perform action a1 { doc /* approved for open dissemination @S186 */ }
        }
        part missionPlanningSystem : MissionPlanningSystem {
            perform action a0 { doc /* converts approved imaging demand and spacecraft constraints into executable activity plans @S011 */ }
            perform action a1 { doc /* receives operational constraints from mission control @S099 */ }
            perform action a2 { doc /* assembling candidate observation timelines and associated ground contact activities @S102 */ }
            perform action a3 { doc /* combines request priority, instrument availability, contact opportunities, onboard storage margin, and downlink capacity into a draft activity schedule @S107 */ }
            perform action a4 { doc /* flags conflicts @S114 */ }
            perform action a5 { doc /* exports a command preparation package @S118 */ }
            perform action a6 { doc /* uses accepted orbit files to align imaging requests, contact opportunities, recorder margins, and downlink windows @S142 */ }
            perform action a7 { doc /* treats the retroreflector window as a constrained planning input @S207 */ }
            perform action a8 { doc /* prevents its use outside the approved scheduling interval @S207 */ }
            perform action a9 { doc /* suspends automatic schedule publication @S216 */ }
            perform action a10 { doc /* applies the delta note during schedule validation @S240 */ }
        }
        part networkControlSystem : NetworkControlSystem {
            perform action a0 { doc /* monitors communications availability @S010 */ }
            perform action a1 { doc /* routes operational traffic @S010 */ }
            perform action a2 { doc /* provides status awareness for ground connectivity @S010 */ }
            perform action a3 { doc /* distributes station allocations @S033 */ }
            perform action a4 { doc /* confirms antenna readiness states @S033 */ }
            perform action a5 { doc /* records the actual start and end times of each contact @S033 */ }
            perform action a6 { doc /* maintains operational visibility of circuit state, path selection, and active maintenance windows @S056 */ }
            perform action a7 { doc /* confirms that the alarm is not caused by a known maintenance interval or a failed local reference check @S072 */ }
            perform action a8 { doc /* provides the Mission Control Center with antenna status, link configuration, timing references, and routing readiness @S079 */ }
            perform action a9 { doc /* uses antenna pointing predictions derived from the accepted ephemeris @S148 */ }
            perform action a10 { doc /* prepare scheduled contacts @S148 */ }
            perform action a11 { doc /* verify tracking readiness @S148 */ }
            perform action a12 { doc /* uses the Security Exception Ticket to restrict affected transfer paths @S170 */ }
            perform action a13 { doc /* preserve the last validated routing configuration @S171 */ }
            perform action a14 { doc /* reject unreviewed changes @S171 */ }
            perform action a15 { doc /* enforces approved routing paths between ground stations, processing services, and external interfaces @S205 */ }
            perform action a16 { doc /* records configuration changes in the operational log @S205 */ }
            perform action a17 { doc /* records rehearsal outcomes for planned maintenance, station loss, degraded routing, and restoration of nominal connectivity @S233 */ }
        }
        part northSBandAntenna : NorthSBandAntenna {
            perform action a0 { doc /* provides the nominal early-pass command uplink and low-rate telemetry return @S028 */ }
            perform action a1 { doc /* connect to the Mission Control Center through protected access routers @S054 */ }
            perform action a2 { doc /* assigned for command and low-rate telemetry contacts @S078 */ }
        }
        part operationalReadinessReview : OperationalReadinessReview {
            perform action a0 { doc /* confirms that ground procedures, staffing rosters, monitoring views, and escalation paths are under configuration control @S227 */ }
        }
        part operatorDisplay : OperatorDisplay {
            perform action a0 { doc /* shows whether recovery, retransmission, or discard is required @S154 */ }
        }
        part operators : Operators {
            perform action a0 { doc /* preserve the command state @S098 */ }
            perform action a1 { doc /* avoid discretionary commanding @S098 */ }
            perform action a2 { doc /* request specialist review @S098 */ }
            perform action a3 { doc /* changing spacecraft configuration @S098 */ }
            perform action a4 { doc /* preserve volatile logs, current configuration state, operator console history, and relevant message identifiers @S213 */ }
            perform action a5 { doc /* restarting services or changing routing @S213 */ }
        }
        part orbitDeterminationEngine : OrbitDeterminationEngine {
            perform action a0 { doc /* supports routine orbit maintenance @S014 */ }
            perform action a1 { doc /* processing tracking inputs @S014 */ }
            perform action a2 { doc /* producing controlled orbit knowledge @S014 */ }
            perform action a3 { doc /* produces the Doppler Residual Report @S041 */ }
            perform action a4 { doc /* supports routine state updates @S089 */ }
            perform action a5 { doc /* provides the basis for predicting future visibility periods, maneuver planning constraints, and antenna pointing expectations @S089 */ }
            perform action a6 { doc /* provides the current orbital solution @S123 */ }
            perform action a7 { doc /* fits dynamic orbit solutions @S128 */ }
            perform action a8 { doc /* produces the Laser Retroreflector Window from the refined orbit solution and the approved station geometry constraints @S145 */ }
        }
        part payloadCalibrationTeam : PayloadCalibrationTeam {
            perform action a0 { doc /* owns payload performance monitoring, calibration parameter stewardship, and the technical assessment of product quality trends @S022 */ }
            perform action a1 { doc /* sends the Calibration Patch Bundle @S094 */ }
            perform action a2 { doc /* reviews planned calibration activities @S117 */ }
            perform action a3 { doc /* obtains predicted viewing geometry from flight dynamics products @S147 */ }
            perform action a4 { doc /* interpret instrument trends @S147 */ }
            perform action a5 { doc /* plan calibration activities @S147 */ }
            perform action a6 { doc /* maintains the approved calibration baseline @S161 */ }
            perform action a7 { doc /* reviews trend evidence @S161 */ }
            perform action a8 { doc /* request a reprocessing campaign @S193 */ }
            perform action a9 { doc /* assesses product integrity @S211 */ }
            perform action a10 { doc /* validates that calibration operations are represented in the rehearsal schedule @S237 */ }
        }
        part payloadImaging : PayloadImaging;
        part payloadProcessingFacility : PayloadProcessingFacility {
            perform action a0 { doc /* provides the operational environment for payload data processing, calibration control, product assessment, and distribution staging @S009 */ }
            perform action a1 { doc /* coordinates with Primary Processing Cluster and Backup Processing Cluster @S049 */ }
            perform action a2 { doc /* receives planning metadata @S110 */ }
            perform action a3 { doc /* transforming downlinked payload telemetry into image products @S151 */ }
            perform action a4 { doc /* delivered the product package, associated quality metadata, and checksum evidence @S178 */ }
            perform action a5 { doc /* quarantine suspect input and derived output @S215 */ }
            perform action a6 { doc /* demonstrates that science product generation can be sustained during representative contact patterns @S232 */ }
        }
        part physicalTopology : PhysicalTopology {
            perform action a0 { doc /* uses redundant terrestrial circuits between the Mission Control Center, the Flight Dynamics Facility, the Payload Processing Facility, and the Long Term Archive @S053 */ }
        }
        part planningCycle : PlanningCycle {
            perform action a0 { doc /* determine feasible imaging windows and ground contacts @S106 */ }
        }
        part primaryMonthlyServiceReview : PrimaryMonthlyServiceReview {
            perform action a0 { doc /* compares actual performance against the accepted baseline @S246 */ }
            perform action a1 { doc /* records trend explanations for any measure that moves outside the watch band @S246 */ }
        }
        part primaryProcessingCluster : PrimaryProcessingCluster {
            perform action a0 { doc /* generates Level 0 products @S155 */ }
            perform action a1 { doc /* removing transfer framing @S155 */ }
            perform action a2 { doc /* ordering source packets @S155 */ }
            perform action a3 { doc /* preserving instrument time tags @S155 */ }
            perform action a4 { doc /* pause nonessential production queues @S220 */ }
            perform action a5 { doc /* reserve compute capacity for validated recovery runs from known-good inputs @S220 */ }
            perform action a6 { doc /* are baselined with approved software versions, processing configurations, capacity reservations, monitoring checks, and rollback instructions @S247 */ }
            exhibit state modes {
                state s0 { doc /* unavailable @S150 */ }
            }
        }
        part processingLevel : ProcessingLevel {
            perform action a0 { doc /* records software build identifiers, calibration baseline identifiers, and ancillary input versions @S158 */ }
        }
        part product : Product {
            exhibit state modes {
                state s0 { doc /* delivery hold @S167 */ }
            }
        }
        part productLatency : ProductLatency;
        part productQualityDispositionTime : ProductQualityDispositionTime;
        part productQualityService : ProductQualityService {
            perform action a0 { doc /* performs automated and analyst-supported checks on generated products @S015 */ }
            perform action a1 { doc /* add planning feedback @S124 */ }
            perform action a2 { doc /* checks each orbit solution @S130 */ }
            perform action a3 { doc /* uses the patch bundle to update calibration applicability checks @S162 */ }
            perform action a4 { doc /* assigns quality flags for missing source packets, timing discontinuity, saturation, cloud screening uncertainty, geolocation residuals, and processing fallback @S165 */ }
            perform action a5 { doc /* produces the Product Hold List @S168 */ }
            perform action a6 { doc /* treats that marker as an input to its quality decision @S173 */ }
            perform action a7 { doc /* set the public quality status @S181 */ }
            perform action a8 { doc /* records the reason for any reprocessing decision @S195 */ }
        }
        part protectedAccessRouters : ProtectedAccessRouters {
            perform action a0 { doc /* keep command and telemetry traffic separate from site administration traffic @S054 */ }
        }
        part readinessReviewBoard : ReadinessReviewBoard {
            perform action a0 { doc /* verifies that each open action from launch and commissioning has an owner, a due date, and an accepted residual risk statement @S228 */ }
        }
        part recorderManagement : RecorderManagement;
        part redundantReferenceClocks : RedundantReferenceClocks {
            perform action a0 { doc /* Time synchronization is provided @S068 */ }
        }
        part redundantTerrestrialCircuits : RedundantTerrestrialCircuits;
        part registeredUsers : RegisteredUsers {
            perform action a0 { doc /* receive authorization scopes @S185 */ }
        }
        part responsibleTeams : ResponsibleTeams {
            perform action a0 { doc /* signed the incident record @S226 */ }
        }
        part schedulingService : SchedulingService {
            perform action a0 { doc /* assigns eligible jobs to the Backup Processing Cluster @S172 */ }
        }
        part southSBandAntenna : SouthSBandAntenna {
            perform action a0 { doc /* provides the alternate S-band path @S029 */ }
            perform action a1 { doc /* is kept in a compatible configuration @S029 */ }
            perform action a2 { doc /* connect to the Mission Control Center through protected access routers @S054 */ }
            perform action a3 { doc /* assigned for command and low-rate telemetry contacts @S078 */ }
        }
        part spacecraft : Spacecraft;
        part spacecraftOperationsTeam : SpacecraftOperationsTeam {
            perform action a0 { doc /* owns spacecraft safety execution, contact conduct, command authorization support, and operational decision making @S020 */ }
            perform action a1 { doc /* monitors spacecraft mode, power state, thermal margins, attitude indicators, command counters, onboard storage, and fault protection messages @S082 */ }
            perform action a2 { doc /* identify safety trends @S083 */ }
            perform action a3 { doc /* coordinate closely before orbit-control activities @S097 */ }
            perform action a4 { doc /* reviews late operational requests @S105 */ }
            perform action a5 { doc /* uses the Antenna Deicing Notice to assess whether planned support can proceed @S113 */ }
            perform action a6 { doc /* receives a maneuver recommendation package @S137 */ }
            perform action a7 { doc /* receives maneuver recommendations @S146 */ }
            perform action a8 { doc /* rehearse commanding @S146 */ }
            perform action a9 { doc /* verify contingency actions @S146 */ }
            perform action a10 { doc /* coordinate contact coverage @S146 */ }
            perform action a11 { doc /* uses the Pass Replay Packet @S198 */ }
            perform action a12 { doc /* confirm that archived downlink context can support anomaly reconstruction @S198 */ }
            perform action a13 { doc /* leads triage for spacecraft safety indicators @S209 */ }
            perform action a14 { doc /* conducts at least one integrated day-in-the-life rehearsal @S235 */ }
            exhibit state modes {
                state s0 { doc /* contingency @S020 */ }
                state s1 { doc /* nominal @S020 */ }
            }
        }
        part spacecraftSystemsEngineer : SpacecraftSystemsEngineer {
            perform action a0 { doc /* interprets health telemetry @S086 */ }
            perform action a1 { doc /* confirms that subsystem states remain within flight rules @S086 */ }
            perform action a2 { doc /* records any anomaly context @S086 */ }
        }
        part stationOperators : StationOperators {
            perform action a0 { doc /* notify the Mission Control Center @S043 */ }
        }
        part subsystemSpecialists : SubsystemSpecialists;
        part supportTeams : SupportTeams {
            perform action a0 { doc /* confirm on-call coverage @S249 */ }
        }
        part svalbardXBandAntenna : SvalbardXBandAntenna {
            perform action a0 { doc /* extends northern contact opportunities @S031 */ }
            perform action a1 { doc /* use dual wide area paths toward the Payload Processing Facility @S055 */ }
            perform action a2 { doc /* support high-rate telemetry reception @S078 */ }
        }
        part telemetryCompleteness : TelemetryCompleteness;
        part telemetryEngineer : TelemetryEngineer {
            perform action a0 { doc /* verifies reception quality, frame loss, latency, and stream continuity @S085 */ }
            perform action a1 { doc /* advises the console lead @S085 */ }
        }
        part telemetryIngestService : TelemetryIngestService {
            perform action a0 { doc /* receives spacecraft telemetry from scheduled contacts @S013 */ }
            perform action a1 { doc /* makes it available to operations, engineering analysis, and downstream processing functions @S013 */ }
            perform action a2 { doc /* receives contact status and data-flow indicators @S048 */ }
            perform action a3 { doc /* accepts real-time frames @S080 */ }
            perform action a4 { doc /* validates basic framing and time continuity @S080 */ }
            perform action a5 { doc /* records reception metadata @S080 */ }
            perform action a6 { doc /* produces the Pass Replay Packet @S081 */ }
            perform action a7 { doc /* is consulted for the latest spacecraft state @S122 */ }
            perform action a8 { doc /* verifies file size, sequence continuity, checksum, and acquisition time @S152 */ }
            perform action a9 { doc /* writes accepted raw data to immutable staging storage @S153 */ }
            perform action a10 { doc /* records the session identifier @S153 */ }
        }
        part unresolvedAnomalyAge : UnresolvedAnomalyAge;
        part userServicesPortal : UserServicesPortal {
            perform action a0 { doc /* provides the controlled external interface for product search, ordering, status communication, and user support workflows @S018 */ }
            perform action a1 { doc /* records the request state @S104 */ }
            perform action a2 { doc /* provides search, preview, order, and download functions @S183 */ }
            perform action a3 { doc /* displays a service status message @S201 */ }
            perform action a4 { doc /* communicates confirmed service impacts in operational terms @S225 */ }
            perform action a5 { doc /* avoids publishing speculative root cause information @S225 */ }
            perform action a6 { doc /* uses the Product Hold List to prevent release of affected products @S239 */ }
        }
        part wideAreaConnectivityDesign : WideAreaConnectivityDesign {
            perform action a0 { doc /* extends the ground network management practices from the scheduling domain into continuous transport control across all operational sites @S052 */ }
        }
        flow f0 of SpacecraftTelemetryItem from spacecraft to telemetryIngestService { doc /* @S013 */ }
        flow f1 of CommandUplinkItem from northSBandAntenna to spacecraft { doc /* @S028 */ }
        flow f2 of LowRateTelemetryItem from spacecraft to northSBandAntenna { doc /* @S028 */ }
        flow f3 of HighRatePayloadDownlinkItem from spacecraft to kirunaXBandAntenna { doc /* @S030 */ }
        flow f4 of VisibilityPredictionsItem from flightDynamicsFacility to missionPlanningSystem { doc /* @S040 */ }
        flow f5 of AntennaPointingSupportProductsItem from flightDynamicsFacility to missionPlanningSystem { doc /* @S040 */ }
        flow f6 of LocalConstraintsItem from stationOperators to missionControlCenter { doc /* @S043 */ }
        flow f7 of ContactStatusItem from networkControlSystem to telemetryIngestService { doc /* @S048 */ }
        flow f8 of DataFlowIndicatorsItem from networkControlSystem to telemetryIngestService { doc /* @S048 */ }
        flow f9 of PayloadDownlinkTrafficItem from kirunaXBandAntenna to payloadProcessingFacility { doc /* @S055 */ }
        flow f10 of PayloadDownlinkTrafficItem from svalbardXBandAntenna to payloadProcessingFacility { doc /* @S055 */ }
        flow f11 of TransfersItem from primaryProcessingCluster to longTermArchive { doc /* @S065 */ }
        flow f12 of AntennaStatusLinkConfigurationTimingReferencesAndRoutingReadinessItem from networkControlSystem to missionControlCenter { doc /* @S079 */ }
        flow f13 of SpacecraftModePowerStateThermalMarginsAttitudeIndicatorsCommandCountersOnboardStorageAndFaultProtectionMessagesItem from missionControlCenter to spacecraftOperationsTeam { doc /* @S082 */ }
        flow f14 of DegradedLinkConditionsAdviceItem from telemetryEngineer to consoleLead { doc /* @S085 */ }
        flow f15 of OperationalConstraintsItem from missionControlCenter to missionPlanningSystem { doc /* @S099 */ }
        flow f16 of OrbitPredictionsItem from flightDynamicsFacility to planningCycle { doc /* @S106 */ }
        flow f17 of VisibilityAssumptionsItem from flightDynamicsFacility to planningCycle { doc /* @S106 */ }
        flow f18 of PlanningMetadataItem from missionPlanningSystem to payloadProcessingFacility { doc /* @S110 */ }
        flow f19 of AntennaDeicingNoticeItem from groundNetworkManager to spacecraftOperationsTeam { doc /* @S113 */ }
        flow f20 of CommandPreparationPackageItem from missionPlanningSystem to missionControlCenter { doc /* @S118 */ }
        flow f21 of DopplerResidualReportItem from orbitDeterminationEngine to flightDynamicsTeam { doc /* @S131 */ }
        flow f22 of RoutineEphemeridesAndEventPredictionsItem from flightDynamicsFacility to missionControlCenter { doc /* @S141 */ }
        flow f23 of RoutineEphemeridesAndEventPredictionsItem from flightDynamicsFacility to missionPlanningSystem { doc /* @S141 */ }
        flow f24 of RoutineEphemeridesAndEventPredictionsItem from flightDynamicsFacility to payloadProcessingFacility { doc /* @S141 */ }
        flow f25 of AcceptedOrbitFilesItem from flightDynamicsFacility to missionPlanningSystem { doc /* @S142 */ }
        flow f26 of ManeuverRecommendationsItem from flightDynamicsTeam to spacecraftOperationsTeam { doc /* @S146 */ }
        flow f27 of PredictedViewingGeometryItem from flightDynamicsFacility to payloadCalibrationTeam { doc /* @S147 */ }
        flow f28 of AcceptedRawDataItem from telemetryIngestService to immutableStagingStorage { doc /* @S153 */ }
        flow f29 of CalibrationPatchBundleItem from payloadCalibrationTeam to productQualityService { doc /* @S162 */ }
        flow f30 of SecurityExceptionTicketItem from groundNetworkManager to networkControlSystem { doc /* @S170 */ }
        flow f31 of EligibleJobsItem from schedulingService to backupProcessingCluster { doc /* @S172 */ }
        flow f32 of ProvenanceMarkerItem from backupProcessingCluster to productQualityService { doc /* @S173 */ }
        flow f33 of ProductPackageItem from payloadProcessingFacility to longTermArchive { doc /* @S178 */ }
        flow f34 of QualityMetadataItem from payloadProcessingFacility to longTermArchive { doc /* @S178 */ }
        flow f35 of ChecksumEvidenceItem from payloadProcessingFacility to longTermArchive { doc /* @S178 */ }
        flow f36 of OrbitQualityStateChangesItem from flightDynamicsFacility to archiveOperationsQueue { doc /* @S194 */ }
        flow f37 of StarTrackerMaskFileItem from flightDynamicsFacility to commandValidationGateway { doc /* @S206 */ }
        flow f38 of LaserRetroreflectorWindowItem from orbitDeterminationEngine to missionPlanningSystem { doc /* @S207 */ }
        flow f39 of ProductHoldListItem from productQualityService to userServicesPortal { doc /* @S239 */ }
        flow f40 of EphemerisDeltaNoteItem from flightDynamicsTeam to missionPlanningSystem { doc /* @S240 */ }
        flow f41 of StorageWatermarkSnapshotItem from longTermArchive to backupProcessingCluster { doc /* @S241 */ }
    }
    requirement def R0 { doc /* the received stream must be reconstructed for engineering review @S081 */ subject s : TelemetryIngestService; }
    requirement def R1 { doc /* operators must identify safety trends while a contact is still available @S083 */ subject s : SpacecraftOperationsTeam; }
    requirement def R2 { doc /* must be reachable during planned critical activities and whenever a console operator declares an off-nominal condition @S095 */ subject s : SubsystemSpecialists; }
    requirement def R3 { doc /* Final approval requires concurrence from the Mission Control Center and the Spacecraft Operations Team before any command stack is placed in the queue for the next authorized uplink opportunity. @S126 */ subject s : CommandStack; }
    requirement def R4 { doc /* Bluebell requires that each flight dynamics delivery include a validity interval, coordinate frame, generation time, and operational use statement. @S140 */ subject s : FlightDynamicsDelivery; }
    requirement def R5 { doc /* The Payload Processing Facility is responsible for transforming downlinked payload telemetry into image products that are traceable to the source telemetry and to the processing configuration used at execution time. @S151 */ subject s : PayloadProcessingFacility; }
    requirement def R6 { doc /* Lantern shall preserve the last validated routing configuration and reject unreviewed changes while payload product transfers are active. @S171 */ subject s : NetworkControlSystem; }
    requirement def R7 { doc /* Forgehouse must quarantine suspect input and derived output when product lineage cannot be proven during an active anomaly investigation. @S215 */ subject s : PayloadProcessingFacility; }
}
