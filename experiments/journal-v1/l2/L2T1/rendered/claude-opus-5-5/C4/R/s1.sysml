package L2Model {
    item def AccessRequestItem { doc /* @S214 */ }
    item def AcknowledgementsItem { doc /* @S044 */ }
    item def AlarmsItem { doc /* @S009 */ }
    item def ApprovedServiceMessagesItem { doc /* @S015 */ }
    item def AxleCounterResetRequestItem { doc /* @S189 */ }
    item def CommandedRouteLockedRoutePointStateAndTrackOccupancyStateItem { doc /* @S098 */ }
    item def ConsolidatedTrainPositionsItem { doc /* @S009 */ }
    item def DataItem { doc /* @S012 */ }
    item def DoorClosedAndLockedIndicationsItem { doc /* @S093 */ }
    item def EquipmentRecoveryOptionsItem { doc /* @S120 */ }
    item def IndependentDistanceMeasurementInputsItem { doc /* @S112 */ }
    item def LinkQualityRegistrationStateAndSessionContinuityInformationItem { doc /* @S039 */ }
    item def LossOfSafeDataConnectivityItem { doc /* @S181 */ }
    item def MessagesCarryingRouteStatusItem { doc /* @S096 */ }
    item def MovementAuthorityDataItem { doc /* @S029 */ }
    item def NonVitalTrendDataItem { doc /* @S119 */ }
    item def OdometryChannelsItem { doc /* @S032 */ }
    item def PlatformDoorStatusSnapshotItem { doc /* @S129 */ }
    item def ProposedRegulatingActionAffectedTrainIdentitiesAndPredictedRecoveryTimeItem { doc /* @S104 */ }
    item def RadioQualityChangesItem { doc /* @S055 */ }
    item def RouteReleaseExceptionListItem { doc /* @S157 */ }
    item def RouteRequestsItem { doc /* @S079 */ }
    item def RouteStateIndicationsItem { doc /* @S108 */ }
    item def ScheduleContextItem { doc /* @S048 */ }
    item def SecurityEventsItem { doc /* @S202 */ }
    item def SelectedFaultSummariesItem { doc /* @S165 */ }
    item def StationStatusIndicationsItem { doc /* @S133 */ }
    item def TestTrainClearanceMemoItem { doc /* @S216 */ }
    item def TrainPositionItem { doc /* @S066 */ }
    item def TrainPredictionDataStoppingPatternChangesAndPlatformAllocationUpdatesItem { doc /* @S136 */ }
    item def UnsafeDoorInterfaceStateItem { doc /* @S132 */ }
    item def ZoneStatusRadioCoverageAlarmsAndTrainSupervisionStatesItem { doc /* @S071 */ }
    part def AcceptanceForRevenueService { doc /* @S245 */ }
    part def AccessApprovals { doc /* @S217 */ }
    part def AlarmAcknowledgements { doc /* @S217 */ }
    part def Alerts { doc /* @S204 */ }
    part def ApprovedChangeReferences { doc /* @S170 */ }
    part def AtlasOnboardController { doc /* @S012,S025,S027,S028,S029,S032,S036,S037,S039,S044,S055,S057,S066,S095,S111,S112,S144,S161,S178,S181,S222,S227 */ }
    part def AuditEvidence { doc /* @S217 */ }
    part def AuditRecords { doc /* @S218 */ }
    part def Berth { doc /* @S132 */ }
    part def CBTCSystem { doc /* @S133,S134,S136,S137,S142 */ }
    part def CertificateActions { doc /* @S217 */ }
    part def CertificateIssuance { doc /* @S208 */ }
    part def CertificateRenewal { doc /* @S209 */ }
    part def CommunicationsBasedTrainControlSystem { doc /* @S002,S129,S150,S199,S200,S201 */ }
    part def ConfigurationChanges { doc /* @S217 */ }
    part def ConfigurationRecords { doc /* @S170 */ }
    part def ControlRoom { doc /* @S009 */ }
    part def ControlStaff { doc /* @S098 */ }
    part def CryptographicKeyManagementAppliance { doc /* @S023,S042,S060,S123,S124,S171,S196,S207,S213,S239 */ }
    part def CustomerInformationSystems { doc /* @S015 */ }
    part def CyberSecurityOfficer { doc /* @S023,S125,S149,S156,S195,S202,S206,S214,S242 */ }
    part def DualChannelOdometer { doc /* @S012,S031,S032,S066,S112,S162,S180,S222 */ }
    part def EastJunctionInterlocking { doc /* @S011,S030,S068,S079,S087,S107,S160,S185,S189,S210,S229 */ }
    part def GreenvaleMetro { doc /* @S001,S175,S176 */ }
    part def InterlockingDataVersions { doc /* @S170 */ }
    part def LineTrafficController { doc /* @S006,S018,S071,S099,S101,S103,S104,S109,S110,S116,S120,S121,S142,S157,S165,S168,S176,S187,S193,S205,S226,S244 */ }
    part def LocalStationStaff { doc /* @S133 */ }
    part def MaintenanceDiagnosticServer { doc /* @S050,S072,S100,S119,S148,S153,S154,S169,S194,S212,S238 */ }
    part def Management { doc /* @S247 */ }
    part def MetroOperationsControlSystem { doc /* @S009,S024,S048,S071,S098,S102,S104,S135,S140,S165,S177,S202,S216,S233 */ }
    part def MovementAuthorityEnvironment { doc /* @S128 */ }
    part def NorthDistrictZoneController { doc /* @S010,S029,S063,S079,S105,S132,S158,S183,S227 */ }
    part def OperationalRehearsal { doc /* @S243 */ }
    part def OperationsControlCentre { doc /* @S108 */ }
    part def OperatorInstructions { doc /* @S217 */ }
    part def ParameterSetIdentifiers { doc /* @S170 */ }
    part def PassengerInformationGateway { doc /* @S015,S047,S076,S122,S136,S137,S138,S198,S219,S236 */ }
    part def PlatformEquipment { doc /* @S128 */ }
    part def PlatformScreenDoorController { doc /* @S017,S046,S075,S093,S129,S130,S192,S221,S234 */ }
    part def RadioConfigurationVersions { doc /* @S170 */ }
    part def ReadinessReviewAuthority { doc /* @S246 */ }
    part def ReadinessReviews { doc /* @S240 */ }
    part def RevenueTrainOperator { doc /* @S007,S043,S044,S117,S118,S166,S179,S191,S197,S215,S216,S226,S244 */ }
    part def Revocation { doc /* @S211 */ }
    part def SafetyDataCommunicationNetwork { doc /* @S014,S040,S041,S051,S058,S097,S147,S164,S202,S232 */ }
    part def SecurityMonitoring { doc /* @S203 */ }
    part def ServiceTimetableServer { doc /* @S015,S048,S076,S139,S219,S235 */ }
    part def SignalMaintenanceEngineer { doc /* @S022,S050,S072,S089,S119,S120,S148,S155,S168,S188,S189,S214,S241 */ }
    part def SoftwareBuildIdentifiers { doc /* @S170 */ }
    part def SouthDistrictZoneController { doc /* @S010,S029,S064,S065,S080,S106,S159,S184,S228 */ }
    part def SupervisingWaysideSystems { doc /* @S093 */ }
    part def System { doc /* @S018,S019 */ }
    part def TestTrain { doc /* @S226 */ }
    part def TimeSynchronizedEventRecords { doc /* @S217 */ }
    part def TrainRadioModem { doc /* @S013,S038,S039,S053,S055,S096,S113,S146,S163,S181 */ }
    part def VoiceDispatchConsole { doc /* @S016,S045,S074,S141,S190,S220,S237 */ }
    part def WaysideRadioAccessNetwork { doc /* @S013,S053,S073,S096,S145,S164,S202,S232 */ }
    part def WestJunctionInterlocking { doc /* @S011,S030,S068,S090,S108,S157,S160,S186,S229 */ }
    part def ZoneController { doc /* @S091 */ }
    part system {
        part acceptanceForRevenueService : AcceptanceForRevenueService;
        part accessApprovals : AccessApprovals;
        part alarmAcknowledgements : AlarmAcknowledgements;
        part alerts : Alerts;
        part approvedChangeReferences : ApprovedChangeReferences;
        part atlasOnboardController : AtlasOnboardController {
            perform action a0 { doc /* supervises automatic train protection functions @S012 */ }
            perform action a1 { doc /* maintain a validated estimate of train position and speed @S012 */ }
            perform action a2 { doc /* assumes the active train control role @S025 */ }
            perform action a3 { doc /* supervises movement authority processing @S027 */ }
            perform action a4 { doc /* supervises onboard speed enforcement @S027 */ }
            perform action a5 { doc /* supervises door enable logic @S027 */ }
            perform action a6 { doc /* supervises train interface commands @S027 */ }
            perform action a7 { doc /* maintains a safety-critical state machine @S028 */ }
            perform action a8 { doc /* compares the two odometry channels @S032 */ }
            perform action a9 { doc /* degrades the operating mode @S032 */ }
            perform action a10 { doc /* recalculates the braking demand needed to keep the train within the authorized movement limits @S036 */ }
            perform action a11 { doc /* produces the Brake Curve Checksum Log @S037 */ }
            perform action a12 { doc /* validating the active enforcement data set @S037 */ }
            perform action a13 { doc /* falls back to the last validated movement authority rules @S057 */ }
            perform action a14 { doc /* confirms train position from the Dual Channel Odometer @S066 */ }
            perform action a15 { doc /* accepting the next authority source @S066 */ }
            perform action a16 { doc /* uses the token bundle to validate that onboard operating context is current @S095 */ }
            perform action a17 { doc /* accepting supervised route-related data @S095 */ }
            perform action a18 { doc /* enforces the active movement profile @S111 */ }
            perform action a19 { doc /* presents any onboard rejection or degraded mode indication @S111 */ }
            perform action a20 { doc /* report train door enable side, berth identity, and departure readiness @S144 */ }
            perform action a21 { doc /* stores onboard fault codes, movement authority acceptance records, propulsion cutback requests, and train interface exceptions @S161 */ }
            perform action a22 { doc /* report security-relevant diagnostic conditions @S222 */ }
            perform action a23 { doc /* demonstrate stable supervision @S227 */ }
            exhibit state modes {
                state s0 { doc /* automatic train operation @S028 */ }
                state s1 { doc /* cutout @S028 */ }
                state s2 { doc /* degraded mode @S111 */ }
                state s3 { doc /* fallback operation @S028 */ }
                state s4 { doc /* initialization @S028 */ }
                state s5 { doc /* protected manual operation @S028 */ }
                state s6 { doc /* restricted manual operation @S178 */ }
            }
        }
        part auditEvidence : AuditEvidence;
        part auditRecords : AuditRecords;
        part berth : Berth {
            perform action a0 { doc /* reports an unsafe door interface state @S132 */ }
        }
        part cBTCSystem : CBTCSystem {
            perform action a0 { doc /* reconciled them with the active timetable @S136 */ }
            perform action a1 { doc /* confirmed the underlying train identity and route @S137 */ }
            perform action a2 { doc /* hold is reflected in CBTC departure logic @S142 */ }
            exhibit state modes {
                state s0 { doc /* door interlock fault @S134 */ }
                state s1 { doc /* emergency stop active @S134 */ }
                state s2 { doc /* evacuation support @S134 */ }
                state s3 { doc /* held train @S134 */ }
                state s4 { doc /* normal service @S134 */ }
                state s5 { doc /* radio degraded @S134 */ }
            }
        }
        part certificateActions : CertificateActions;
        part certificateIssuance : CertificateIssuance;
        part certificateRenewal : CertificateRenewal;
        part communicationsBasedTrainControlSystem : CommunicationsBasedTrainControlSystem {
            perform action a0 { doc /* supervising train separation, movement authority, and service regulation @S002 */ }
            perform action a1 { doc /* favours restrictive platform states @S150 */ }
            perform action a2 { doc /* requires explicit controller action before restoring automatic departure support at the affected station @S150 */ }
            exhibit state modes {
                state s0 { doc /* automatic operation @S199 */ }
                state s1 { doc /* degraded operation @S150 */ }
            }
        }
        part configurationChanges : ConfigurationChanges;
        part configurationRecords : ConfigurationRecords;
        part controlRoom : ControlRoom;
        part controlStaff : ControlStaff {
            perform action a0 { doc /* identify mismatches @S098 */ }
        }
        part cryptographicKeyManagementAppliance : CryptographicKeyManagementAppliance {
            perform action a0 { doc /* supports key-management processes @S023 */ }
            perform action a1 { doc /* supports the security material used by onboard communications @S042 */ }
            perform action a2 { doc /* supports the authentication framework used on the safety data paths @S060 */ }
            perform action a3 { doc /* uses the sample report @S123 */ }
            perform action a4 { doc /* verify that certificate validity windows and controller clocks remain within the permitted tolerance @S123 */ }
            perform action a5 { doc /* produces the Encryption Certificate Renewal Pack @S124 */ }
            perform action a6 { doc /* records the change reference for later security audit @S124 */ }
            perform action a7 { doc /* maintains certificate and key status records @S171 */ }
            perform action a8 { doc /* supporting commissioning operations without manual workarounds @S239 */ }
        }
        part customerInformationSystems : CustomerInformationSystems;
        part cyberSecurityOfficer : CyberSecurityOfficer {
            perform action a0 { doc /* oversees access controls @S023 */ }
            perform action a1 { doc /* oversees key-management processes @S023 */ }
            perform action a2 { doc /* oversees the response to security events @S023 */ }
            perform action a3 { doc /* reviews certificate change records, access events, and unusual authentication failures @S125 */ }
            perform action a4 { doc /* authorising normal operational reliance on the renewed security configuration @S125 */ }
            perform action a5 { doc /* reviews access rights for passenger information and dispatch integration workstations @S149 */ }
            perform action a6 { doc /* reviews privileged diagnostic access logs @S156 */ }
            perform action a7 { doc /* confirms that remote connections use current credentials and approved encryption settings @S156 */ }
            perform action a8 { doc /* review any degraded condition @S195 */ }
            perform action a9 { doc /* maintain continuous monitoring of security events @S202 */ }
            perform action a10 { doc /* uses the audit file to investigate radio session continuity @S206 */ }
            perform action a11 { doc /* confirm that security monitoring records are complete @S206 */ }
            perform action a12 { doc /* approve security-sensitive permissions @S214 */ }
            perform action a13 { doc /* confirm that access controls, event monitoring, operator accounts, and security incident escalation paths are effective @S242 */ }
        }
        part dualChannelOdometer : DualChannelOdometer {
            perform action a0 { doc /* provides independent speed and distance measurements @S031 */ }
            perform action a1 { doc /* providing independent distance measurement inputs @S112 */ }
            perform action a2 { doc /* provides distance and speed plausibility information @S162 */ }
            perform action a3 { doc /* cause the train location to be treated as uncertain @S180 */ }
            perform action a4 { doc /* report security-relevant diagnostic conditions @S222 */ }
        }
        part eastJunctionInterlocking : EastJunctionInterlocking {
            perform action a0 { doc /* maintain vital control of points and signals @S011 */ }
            perform action a1 { doc /* report switch state, track occupancy, and route locking status to the responsible zone controller @S068 */ }
            perform action a2 { doc /* sends the Axle Counter Reset Request @S087 */ }
            perform action a3 { doc /* holds the route locked @S107 */ }
            perform action a4 { doc /* report route command histories, point detection changes, and protective lock status @S160 */ }
            perform action a5 { doc /* hold commanded points locked @S185 */ }
            perform action a6 { doc /* reject any control message with an invalid signature, an expired certificate, or a sequence value outside the accepted window @S210 */ }
            exhibit state modes {
                state s0 { doc /* degraded mode @S087 */ }
                state s1 { doc /* enhanced monitoring @S229 */ }
            }
        }
        part greenvaleMetro : GreenvaleMetro {
            perform action a0 { doc /* is operated as a high-frequency urban railway @S001 */ }
            perform action a1 { doc /* keeps trains stationary or moving at controlled speed @S175 */ }
            exhibit state modes {
                state s0 { doc /* degraded mode @S176 */ }
                state s1 { doc /* degraded operation @S175 */ }
            }
        }
        part interlockingDataVersions : InterlockingDataVersions;
        part lineTrafficController : LineTrafficController {
            perform action a0 { doc /* monitoring service performance @S006 */ }
            perform action a1 { doc /* authorizing planned operational changes @S006 */ }
            perform action a2 { doc /* coordinating incident response @S006 */ }
            perform action a3 { doc /* directing recovery actions @S006 */ }
            perform action a4 { doc /* manage service @S071 */ }
            perform action a5 { doc /* request a regulating action @S099 */ }
            perform action a6 { doc /* maintaining a live view of train positions, route status, alarms, and service performance @S101 */ }
            perform action a7 { doc /* selects holding, skip-stop, turnback, or run-through measures @S103 */ }
            perform action a8 { doc /* checking that passenger impact and downstream recovery have been assessed @S103 */ }
            perform action a9 { doc /* confirms the command @S104 */ }
            perform action a10 { doc /* produces the Temporary Speed Restriction Notice @S109 */ }
            perform action a11 { doc /* confirming the limits, speed value, start time, and expected removal condition @S109 */ }
            perform action a12 { doc /* monitors actual train performance against the expected delay allowance @S110 */ }
            perform action a13 { doc /* adjusts regulation plans @S110 */ }
            perform action a14 { doc /* records the initial event time, train identifier, location, passenger impact, and the first safe operating instruction issued @S116 */ }
            perform action a15 { doc /* verifies that the revised plan is visible @S121 */ }
            perform action a16 { doc /* relying on it for regulation @S121 */ }
            perform action a17 { doc /* apply a station hold through dispatch controls @S142 */ }
            perform action a18 { doc /* receives the Route Release Exception List @S157 */ }
            perform action a19 { doc /* check whether a release anomaly could affect service recovery decisions @S157 */ }
            perform action a20 { doc /* confirms the operating restriction @S168 */ }
            perform action a21 { doc /* declares degraded mode @S176 */ }
            perform action a22 { doc /* confirms train positions through independent indications and direct verbal reports @S187 */ }
            perform action a23 { doc /* stop the trial @S226 */ }
            perform action a24 { doc /* maintain safe service regulation @S244 */ }
        }
        part localStationStaff : LocalStationStaff;
        part maintenanceDiagnosticServer : MaintenanceDiagnosticServer {
            perform action a0 { doc /* collects non-vital health indications from trainborne equipment @S050 */ }
            perform action a1 { doc /* receives non-vital summaries of radio and network health @S072 */ }
            perform action a2 { doc /* records route command outcomes, point operation timing, and detection transitions @S100 */ }
            perform action a3 { doc /* provides non-vital trend data @S119 */ }
            perform action a4 { doc /* records station interface faults, rejected commands, and inconsistent indications @S148 */ }
            perform action a5 { doc /* receives event streams from fixed and onboard equipment @S153 */ }
            perform action a6 { doc /* uses the checksum log to compare stored braking data identifiers against the expected maintenance baseline @S154 */ }
            perform action a7 { doc /* preserves raw events, normalised event records, diagnostic session notes, and file integrity values @S169 */ }
            perform action a8 { doc /* mark each degraded-mode diagnostic session with the incident identifier @S194 */ }
            perform action a9 { doc /* collect commissioning diagnostics @S238 */ }
        }
        part management : Management {
            perform action a0 { doc /* confirms that training, documentation, staffing, spare equipment, monitoring arrangements, and emergency procedures are in place @S247 */ }
        }
        part metroOperationsControlSystem : MetroOperationsControlSystem {
            perform action a0 { doc /* provides the control room with consolidated train positions, service regulation functions, alarms, and operator command interfaces @S009 */ }
            perform action a1 { doc /* sends the Crew Login Token Bundle @S024 */ }
            perform action a2 { doc /* displays zone status, radio coverage alarms, and train supervision states @S071 */ }
            perform action a3 { doc /* displays the commanded route, locked route, point state, and track occupancy state as separate indications @S098 */ }
            perform action a4 { doc /* presents regulating options @S102 */ }
            perform action a5 { doc /* displays the proposed regulating action, affected train identities, and predicted recovery time @S104 */ }
            perform action a6 { doc /* displays station and platform states @S135 */ }
            perform action a7 { doc /* coordinates timetable deviation, platform closure, and station crowding information @S140 */ }
            perform action a8 { doc /* displays selected fault summaries @S165 */ }
            perform action a9 { doc /* present the affected limits, the selected fallback mode, and any pending operator actions @S177 */ }
            perform action a10 { doc /* uses the Test Train Clearance Memo as a controlled prerequisite @S216 */ }
            perform action a11 { doc /* accepting security exceptions for non-revenue movement in protected territory @S216 */ }
            perform action a12 { doc /* uses the status snapshot @S233 */ }
            perform action a13 { doc /* confirm that platform interface conditions are suitable @S233 */ }
            perform action a14 { doc /* authorizing the associated commissioning scenario @S233 */ }
        }
        part movementAuthorityEnvironment : MovementAuthorityEnvironment;
        part northDistrictZoneController : NorthDistrictZoneController {
            perform action a0 { doc /* calculate safe movement authority limits @S010 */ }
            perform action a1 { doc /* supervises the northern main line, the northern turnback, and the approach to East Junction Interlocking @S063 */ }
            perform action a2 { doc /* requests routes through East Junction Interlocking @S079 */ }
            perform action a3 { doc /* applies movement authority constraints @S105 */ }
            perform action a4 { doc /* reports any conflict or unavailable route condition @S105 */ }
            perform action a5 { doc /* suppresses platform departure authority @S132 */ }
            perform action a6 { doc /* records controller health, interface state, and fallback mode transitions @S158 */ }
            perform action a7 { doc /* applies the Temporary Speed Restriction Notice @S183 */ }
            perform action a8 { doc /* validating the affected track limits against its degraded-mode map @S183 */ }
            perform action a9 { doc /* demonstrate stable supervision @S227 */ }
            exhibit state modes {
                state s0 { doc /* fallback mode @S158 */ }
            }
        }
        part operationalRehearsal : OperationalRehearsal;
        part operationsControlCentre : OperationsControlCentre;
        part operatorInstructions : OperatorInstructions;
        part parameterSetIdentifiers : ParameterSetIdentifiers;
        part passengerInformationGateway : PassengerInformationGateway {
            perform action a0 { doc /* distributes approved service messages to customer information systems @S015 */ }
            perform action a1 { doc /* receives non-vital train position and service state data @S047 */ }
            perform action a2 { doc /* receive selected service information @S076 */ }
            perform action a3 { doc /* receives the operational service state @S122 */ }
            perform action a4 { doc /* align platform messages and train destination information with the current regulating plan @S122 */ }
            perform action a5 { doc /* receives train prediction data, stopping pattern changes, and platform allocation updates @S136 */ }
            perform action a6 { doc /* publish a revised destination or skip-stop message @S137 */ }
            perform action a7 { doc /* marks the affected train movements as unavailable for boarding @S138 */ }
            perform action a8 { doc /* issue disruption messages @S198 */ }
        }
        part platformEquipment : PlatformEquipment;
        part platformScreenDoorController : PlatformScreenDoorController {
            perform action a0 { doc /* exchanges platform interface indications with the train control environment @S017 */ }
            perform action a1 { doc /* exchanges door enable and closed-and-locked indications with the train interface @S046 */ }
            perform action a2 { doc /* exchanges only the permitted interface indications with the supervising wayside systems @S075 */ }
            perform action a3 { doc /* provides door closed and locked indications to the supervising wayside systems @S093 */ }
            perform action a4 { doc /* produces the Platform Door Status Snapshot at each monitored platform face @S129 */ }
            perform action a5 { doc /* reports closed, locked, bypassed, inhibited, and faulted conditions @S130 */ }
            perform action a6 { doc /* accept only authenticated interfaces @S221 */ }
            perform action a7 { doc /* be included in end-to-end tests @S234 */ }
            exhibit state modes {
                state s0 { doc /* bypassed @S130 */ }
                state s1 { doc /* closed @S130 */ }
                state s2 { doc /* faulted @S130 */ }
                state s3 { doc /* inhibited @S130 */ }
                state s4 { doc /* locked @S130 */ }
                state s5 { doc /* protected local state @S192 */ }
            }
        }
        part radioConfigurationVersions : RadioConfigurationVersions;
        part readinessReviewAuthority : ReadinessReviewAuthority {
            perform action a0 { doc /* assessed and approved operational restriction, maintenance response, and passenger impact @S246 */ }
        }
        part readinessReviews : ReadinessReviews;
        part revenueTrainOperator : RevenueTrainOperator {
            perform action a0 { doc /* compliance with instructions issued through approved operational channels @S007 */ }
            perform action a1 { doc /* entered Acknowledgements @S044 */ }
            perform action a2 { doc /* instruction is repeated back @S117 */ }
            perform action a3 { doc /* reports train condition, cab indications, passenger issues, and any local hazard @S118 */ }
            perform action a4 { doc /* reports observed cab indications, train handling effects, and passenger service impacts @S166 */ }
            perform action a5 { doc /* remains responsible for speed control, stopping accuracy, door release discipline, and compliance with verbal movement limits @S179 */ }
            perform action a6 { doc /* repeat back the movement limit, maximum permitted speed, stopping point, and any instruction to remain clear of a platform interface @S191 */ }
            perform action a7 { doc /* sends the Test Train Clearance Memo @S197 */ }
            perform action a8 { doc /* completing the prescribed proving run under restricted manual control @S197 */ }
            perform action a9 { doc /* crewed by a Revenue Train Operator @S226 */ }
            perform action a10 { doc /* follows onboard indications and rulebook instructions @S244 */ }
        }
        part revocation : Revocation;
        part safetyDataCommunicationNetwork : SafetyDataCommunicationNetwork {
            perform action a0 { doc /* carries safety-related messages between approved control components @S014 */ }
            perform action a1 { doc /* provides the protected communications transport @S040 */ }
            perform action a2 { doc /* sends the Clock Drift Sample Report @S041 */ }
            perform action a3 { doc /* carries vital movement authority traffic @S051 */ }
            perform action a4 { doc /* carries vital messages between zone controllers, interlockings, and approved interfaces @S058 */ }
            perform action a5 { doc /* configured for deterministic delivery of vital state changes and command acknowledgements @S097 */ }
            perform action a6 { doc /* carries safety-relevant station interface messages @S147 */ }
            perform action a7 { doc /* provide communication performance records @S164 */ }
        }
        part securityMonitoring : SecurityMonitoring;
        part serviceTimetableServer : ServiceTimetableServer {
            perform action a0 { doc /* supplies planned service data @S015 */ }
            perform action a1 { doc /* provides schedule context @S048 */ }
            perform action a2 { doc /* receive selected service information @S076 */ }
            perform action a3 { doc /* provides planned service context @S139 */ }
            perform action a4 { doc /* provide trial schedules @S235 */ }
        }
        part signalMaintenanceEngineer : SignalMaintenanceEngineer {
            perform action a0 { doc /* review equipment health @S022 */ }
            perform action a1 { doc /* correlate alarms @S022 */ }
            perform action a2 { doc /* support restoration @S022 */ }
            perform action a3 { doc /* uses Maintenance Diagnostic Server @S022 */ }
            perform action a4 { doc /* review faults @S050 */ }
            perform action a5 { doc /* investigate degraded coverage trends @S072 */ }
            perform action a6 { doc /* verifies local track clearance evidence @S089 */ }
            perform action a7 { doc /* records the result @S089 */ }
            perform action a8 { doc /* authorising restoration of normal route setting @S089 */ }
            perform action a9 { doc /* determine whether an incident has an equipment cause or an operational cause @S119 */ }
            perform action a10 { doc /* advises the Line Traffic Controller on equipment recovery options @S120 */ }
            perform action a11 { doc /* later investigation @S148 */ }
            perform action a12 { doc /* initiates remote diagnostic sessions @S155 */ }
            perform action a13 { doc /* confirms the engineering status @S168 */ }
            perform action a14 { doc /* verifies point condition, track vacancy, and local protection @S188 */ }
            perform action a15 { doc /* uses the Axle Counter Reset Request @S189 */ }
            perform action a16 { doc /* request access needed for fault isolation @S214 */ }
            perform action a17 { doc /* verify that field defects raised during test running have been closed, deferred with approved controls, or assigned to a post-commissioning monitoring plan @S241 */ }
        }
        part softwareBuildIdentifiers : SoftwareBuildIdentifiers;
        part southDistrictZoneController : SouthDistrictZoneController {
            perform action a0 { doc /* calculate safe movement authority limits @S010 */ }
            perform action a1 { doc /* supervises the southern main line, the southern turnback, and the approach to West Junction Interlocking @S064 */ }
            perform action a2 { doc /* applies the same route protection principles for interfaces with West Junction Interlocking @S080 */ }
            perform action a3 { doc /* applies the same operating principles for the southern section @S106 */ }
            perform action a4 { doc /* preserving separation margins and route locking conditions @S106 */ }
            perform action a5 { doc /* maintains comparable diagnostic coverage @S159 */ }
            perform action a6 { doc /* inhibit automatic route setting @S184 */ }
        }
        part supervisingWaysideSystems : SupervisingWaysideSystems;
        part systemPart : System {
            perform action a0 { doc /* is operated to a defined safe state @S019 */ }
            exhibit state modes {
                state s0 { doc /* degraded operation @S019 */ }
                state s1 { doc /* normal operation @S018 */ }
                state s2 { doc /* safe state @S019 */ }
            }
        }
        part testTrain : TestTrain;
        part timeSynchronizedEventRecords : TimeSynchronizedEventRecords;
        part trainRadioModem : TrainRadioModem {
            perform action a0 { doc /* connects each train to the Wayside Radio Access Network @S013 */ }
            perform action a1 { doc /* provides the onboard data radio function @S038 */ }
            perform action a2 { doc /* maintains CBTC sessions over Wayside Radio Access Network coverage areas @S038 */ }
            perform action a3 { doc /* reports link quality, registration state, and session continuity information @S039 */ }
            perform action a4 { doc /* maintain a stable session during normal operation @S053 */ }
            perform action a5 { doc /* maintains the active bearer used by the Atlas Onboard Controller @S055 */ }
            perform action a6 { doc /* reports radio quality changes @S055 */ }
            perform action a7 { doc /* messages carrying route status are exchanged through Wayside Radio Access Network paths @S096 */ }
            perform action a8 { doc /* supports continuous operational messaging @S113 */ }
            perform action a9 { doc /* uses the Encryption Certificate Renewal Pack @S146 */ }
            perform action a10 { doc /* accepting renewed secure sessions @S146 */ }
            perform action a11 { doc /* records bearer loss, reconnection timing, signal quality indicators, and message retry counts @S163 */ }
            perform action a12 { doc /* report loss of safe data connectivity @S181 */ }
            perform action a13 { doc /* not mask intermittent communication failures from the cab display @S181 */ }
            exhibit state modes {
                state s0 { doc /* normal operation @S053 */ }
            }
        }
        part voiceDispatchConsole : VoiceDispatchConsole {
            perform action a0 { doc /* provides the fallback voice coordination path @S016 */ }
            perform action a1 { doc /* provides a means for voice coordination during degraded service @S045 */ }
            perform action a2 { doc /* displays train calling identity, current platform association, and the latest operational hold reason @S141 */ }
            exhibit state modes {
                state s0 { doc /* available @S074 */ }
            }
        }
        part waysideRadioAccessNetwork : WaysideRadioAccessNetwork {
            perform action a0 { doc /* provides the radio bearer for train-to-wayside control communications @S013 */ }
            perform action a1 { doc /* provides overlapping cell coverage through stations, tunnels, crossovers, and depot approach tracks @S053 */ }
            perform action a2 { doc /* sends the Radio Handover Audit File @S073 */ }
            perform action a3 { doc /* maintain message delivery paths for station interface traffic @S145 */ }
            perform action a4 { doc /* provide communication performance records @S164 */ }
        }
        part westJunctionInterlocking : WestJunctionInterlocking {
            perform action a0 { doc /* maintain vital control of points and signals @S011 */ }
            perform action a1 { doc /* report switch state, track occupancy, and route locking status to the responsible zone controller @S068 */ }
            perform action a2 { doc /* sends the Route Release Exception List @S090 */ }
            perform action a3 { doc /* provides route state indications @S108 */ }
            perform action a4 { doc /* report route command histories, point detection changes, and protective lock status @S160 */ }
            perform action a5 { doc /* reject a route command @S186 */ }
            exhibit state modes {
                state s0 { doc /* enhanced monitoring @S229 */ }
            }
        }
        part zoneController : ZoneController {
            perform action a0 { doc /* treats any release exception as a retained hazard @S091 */ }
        }
        flow f0 of ConsolidatedTrainPositionsItem from metroOperationsControlSystem to controlRoom { doc /* @S009 */ }
        flow f1 of AlarmsItem from metroOperationsControlSystem to controlRoom { doc /* @S009 */ }
        flow f2 of DataItem from dualChannelOdometer to atlasOnboardController { doc /* @S012 */ }
        flow f3 of ApprovedServiceMessagesItem from passengerInformationGateway to customerInformationSystems { doc /* @S015 */ }
        flow f4 of MovementAuthorityDataItem from northDistrictZoneController to atlasOnboardController { doc /* @S029 */ }
        flow f5 of MovementAuthorityDataItem from southDistrictZoneController to atlasOnboardController { doc /* @S029 */ }
        flow f6 of OdometryChannelsItem from dualChannelOdometer to atlasOnboardController { doc /* @S032 */ }
        flow f7 of LinkQualityRegistrationStateAndSessionContinuityInformationItem from trainRadioModem to atlasOnboardController { doc /* @S039 */ }
        flow f8 of AcknowledgementsItem from revenueTrainOperator to atlasOnboardController { doc /* @S044 */ }
        flow f9 of ScheduleContextItem from serviceTimetableServer to metroOperationsControlSystem { doc /* @S048 */ }
        flow f10 of RadioQualityChangesItem from trainRadioModem to atlasOnboardController { doc /* @S055 */ }
        flow f11 of TrainPositionItem from dualChannelOdometer to atlasOnboardController { doc /* @S066 */ }
        flow f12 of ZoneStatusRadioCoverageAlarmsAndTrainSupervisionStatesItem from metroOperationsControlSystem to lineTrafficController { doc /* @S071 */ }
        flow f13 of RouteRequestsItem from northDistrictZoneController to eastJunctionInterlocking { doc /* @S079 */ }
        flow f14 of DoorClosedAndLockedIndicationsItem from platformScreenDoorController to supervisingWaysideSystems { doc /* @S093 */ }
        flow f15 of MessagesCarryingRouteStatusItem from trainRadioModem to waysideRadioAccessNetwork { doc /* @S096 */ }
        flow f16 of CommandedRouteLockedRoutePointStateAndTrackOccupancyStateItem from metroOperationsControlSystem to controlStaff { doc /* @S098 */ }
        flow f17 of ProposedRegulatingActionAffectedTrainIdentitiesAndPredictedRecoveryTimeItem from metroOperationsControlSystem to lineTrafficController { doc /* @S104 */ }
        flow f18 of RouteStateIndicationsItem from westJunctionInterlocking to operationsControlCentre { doc /* @S108 */ }
        flow f19 of IndependentDistanceMeasurementInputsItem from dualChannelOdometer to atlasOnboardController { doc /* @S112 */ }
        flow f20 of NonVitalTrendDataItem from maintenanceDiagnosticServer to signalMaintenanceEngineer { doc /* @S119 */ }
        flow f21 of EquipmentRecoveryOptionsItem from signalMaintenanceEngineer to lineTrafficController { doc /* @S120 */ }
        flow f22 of PlatformDoorStatusSnapshotItem from platformScreenDoorController to communicationsBasedTrainControlSystem { doc /* @S129 */ }
        flow f23 of UnsafeDoorInterfaceStateItem from berth to northDistrictZoneController { doc /* @S132 */ }
        flow f24 of StationStatusIndicationsItem from cBTCSystem to localStationStaff { doc /* @S133 */ }
        flow f25 of TrainPredictionDataStoppingPatternChangesAndPlatformAllocationUpdatesItem from cBTCSystem to passengerInformationGateway { doc /* @S136 */ }
        flow f26 of RouteReleaseExceptionListItem from westJunctionInterlocking to lineTrafficController { doc /* @S157 */ }
        flow f27 of SelectedFaultSummariesItem from metroOperationsControlSystem to lineTrafficController { doc /* @S165 */ }
        flow f28 of LossOfSafeDataConnectivityItem from trainRadioModem to atlasOnboardController { doc /* @S181 */ }
        flow f29 of AxleCounterResetRequestItem from eastJunctionInterlocking to signalMaintenanceEngineer { doc /* @S189 */ }
        flow f30 of SecurityEventsItem from safetyDataCommunicationNetwork to cyberSecurityOfficer { doc /* @S202 */ }
        flow f31 of SecurityEventsItem from waysideRadioAccessNetwork to cyberSecurityOfficer { doc /* @S202 */ }
        flow f32 of SecurityEventsItem from metroOperationsControlSystem to cyberSecurityOfficer { doc /* @S202 */ }
        flow f33 of AccessRequestItem from signalMaintenanceEngineer to cyberSecurityOfficer { doc /* @S214 */ }
        flow f34 of TestTrainClearanceMemoItem from revenueTrainOperator to metroOperationsControlSystem { doc /* @S216 */ }
    }
    requirement def R0 { doc /* a train authority must be reissued by the receiving zone @S065 */ subject s : SouthDistrictZoneController; }
    requirement def R1 { doc /* its state is not allowed to override movement authority logic @S075 */ subject s : PlatformScreenDoorController; }
    requirement def R2 { doc /* shall not publish a revised destination or skip-stop message until the underlying train identity and route have been confirmed by the CBTC system @S137 */ subject s : PassengerInformationGateway; }
    requirement def R3 { doc /* shall report train door enable side, berth identity, and departure readiness to support platform interface checks during dwell and dispatch @S144 */ subject s : AtlasOnboardController; }
    requirement def R4 { doc /* shall maintain message delivery paths for station interface traffic during normal radio coverage transitions and degraded coverage recovery @S145 */ subject s : WaysideRadioAccessNetwork; }
    requirement def R5 { doc /* requires explicit controller action before restoring automatic departure support at the affected station @S150 */ subject s : CommunicationsBasedTrainControlSystem; }
    requirement def R6 { doc /* The Metro Operations Control System shall present the affected limits, the selected fallback mode, and any pending operator actions without obscuring safety alarms. @S177 */ subject s : MetroOperationsControlSystem; }
    requirement def R7 { doc /* The Dual Channel Odometer shall cause the train location to be treated as uncertain when its channels disagree beyond the permitted tolerance. @S180 */ subject s : DualChannelOdometer; }
    requirement def R8 { doc /* The Train Radio Modem shall report loss of safe data connectivity to the Atlas Onboard Controller and shall not mask intermittent communication failures from the cab display. @S181 */ subject s : TrainRadioModem; }
    requirement def R9 { doc /* Orchid shall inhibit automatic route setting within any block whose occupancy state is under manual confirmation. @S184 */ subject s : SouthDistrictZoneController; }
    requirement def R10 { doc /* The East Junction Interlocking shall hold commanded points locked until field confirmation or a verified diagnostic indication supports a safe release. @S185 */ subject s : EastJunctionInterlocking; }
    requirement def R11 { doc /* The West Junction Interlocking shall reject a route command that conflicts with a manually protected train movement. @S186 */ subject s : WestJunctionInterlocking; }
    requirement def R12 { doc /* Restricted manual movements shall be authorized through the Voice Dispatch Console unless the contingency communications procedure has been formally invoked. @S190 */ subject s : VoiceDispatchConsole; }
    requirement def R13 { doc /* The Revenue Train Operator shall repeat back the movement limit, maximum permitted speed, stopping point, and any instruction to remain clear of a platform interface. @S191 */ subject s : RevenueTrainOperator; }
    requirement def R14 { doc /* Reset authorizations require concurrence between the Line Traffic Controller and the Signal Maintenance Engineer when the reset can change route availability or occupancy status. @S193 */ subject s : LineTrafficController; }
    requirement def R15 { doc /* Quarry shall mark each degraded-mode diagnostic session with the incident identifier before any component restart is attempted. @S194 */ subject s : MaintenanceDiagnosticServer; }
    requirement def R16 { doc /* The Cyber Security Officer shall review any degraded condition that involves authentication failure, unexpected lockout, or abnormal network access behavior. @S195 */ subject s : CyberSecurityOfficer; }
    requirement def R17 { doc /* The Cryptographic Key Management Appliance shall not be bypassed to accelerate service recovery unless the approved emergency security procedure is active. @S196 */ subject s : CryptographicKeyManagementAppliance; }
    requirement def R18 { doc /* The Passenger Information Gateway shall issue disruption messages that are consistent with the operating limits accepted by the Line Traffic Controller. @S198 */ subject s : PassengerInformationGateway; }
    requirement def R19 { doc /* Return to automatic operation requires stable communications, verified route state, confirmed train position, and a recorded handback from maintenance control to operations control. @S199 */ subject s : CommunicationsBasedTrainControlSystem; }
    requirement def R20 { doc /* Cybersecurity controls for the Greenvale Metro Communications-Based Train Control System shall be treated as operating prerequisites for safe automatic train movement after any maintenance handback. @S200 */ subject s : CommunicationsBasedTrainControlSystem; }
    requirement def R21 { doc /* the operating response shall reflect that assumption. @S201 */ subject s : CommunicationsBasedTrainControlSystem; }
    requirement def R22 { doc /* The Cyber Security Officer shall maintain continuous monitoring of security events from the Safety Data Communication Network, the Wayside Radio Access Network, and the Metro Operations Control System. @S202 */ subject s : CyberSecurityOfficer; }
    requirement def R23 { doc /* Security monitoring shall correlate authentication failures, session resets, rejected messages, configuration changes, and abnormal timing patterns without altering any safety command path. @S203 */ subject s : SecurityMonitoring; }
    requirement def R24 { doc /* Alerts affecting train control availability shall be classified using operational impact, affected territory, and whether the event could change train movement authority. @S204 */ subject s : Alerts; }
    requirement def R25 { doc /* The Line Traffic Controller shall be notified when a cybersecurity event requires a restriction on automatic operation or a change in communications mode. @S205 */ subject s : LineTrafficController; }
    requirement def R26 { doc /* The Cryptographic Key Management Appliance shall be the controlled source for operational certificates used by trainborne, wayside, control center, and maintenance components. @S207 */ subject s : CryptographicKeyManagementAppliance; }
    requirement def R27 { doc /* Certificate issuance shall require approved asset identity, recorded software baseline, assigned operating domain, and confirmation that the requesting component is authorized for service. @S208 */ subject s : CertificateIssuance; }
    requirement def R28 { doc /* Certificate renewal shall be planned before expiry so that the Atlas Onboard Controller, Train Radio Modem, North District Zone Controller, South District Zone Controller, and West Junction Interlocking do not enter service with degraded trust. @S209 */ subject s : CertificateRenewal; }
    requirement def R29 { doc /* Falcon shall reject any control message with an invalid signature, an expired certificate, or a sequence value outside the accepted window. @S210 */ subject s : EastJunctionInterlocking; }
    requirement def R30 { doc /* Revocation shall be available for a compromised device, a retired device, or a device whose maintenance history can no longer be reconciled with approved configuration records. @S211 */ subject s : Revocation; }
    requirement def R31 { doc /* The Maintenance Diagnostic Server shall not be used to bypass certificate checks or to create alternate trust paths into safety-related communications. @S212 */ subject s : MaintenanceDiagnosticServer; }
    requirement def R32 { doc /* Administrative access to the Cryptographic Key Management Appliance shall require named accounts, multifactor authentication, separation of duties, and recorded approval for privileged changes. @S213 */ subject s : CryptographicKeyManagementAppliance; }
    requirement def R33 { doc /* the Cyber Security Officer shall approve security-sensitive permissions before they are enabled. @S214 */ subject s : CyberSecurityOfficer; }
    requirement def R34 { doc /* The Revenue Train Operator shall not be assigned cybersecurity administration duties during passenger service, although security warnings presented in the cab shall remain part of normal operating awareness. @S215 */ subject s : RevenueTrainOperator; }
    requirement def R35 { doc /* Audit evidence shall include time-synchronized event records, access approvals, certificate actions, configuration changes, alarm acknowledgements, and operator instructions related to communications security. @S217 */ subject s : AuditEvidence; }
    requirement def R36 { doc /* Audit records shall be protected from local alteration by the component that generates them and shall be retained for the period defined by Greenvale Metro governance. @S218 */ subject s : AuditRecords; }
    requirement def R37 { doc /* The Service Timetable Server and Passenger Information Gateway shall be monitored for compromise because incorrect operational context can influence control room decisions even when safety commands remain valid. @S219 */ subject s : ServiceTimetableServer; }
    requirement def R38 { doc /* The Service Timetable Server and Passenger Information Gateway shall be monitored for compromise because incorrect operational context can influence control room decisions even when safety commands remain valid. @S219 */ subject s : PassengerInformationGateway; }
    requirement def R39 { doc /* The Voice Dispatch Console shall be included in security incident procedures when a cyber event changes the normal method for issuing operational instructions. @S220 */ subject s : VoiceDispatchConsole; }
    requirement def R40 { doc /* The Platform Screen Door Controller shall accept only authenticated interfaces approved for passenger service coordination and maintenance testing. @S221 */ subject s : PlatformScreenDoorController; }
    requirement def R41 { doc /* The Dual Channel Odometer and Atlas Onboard Controller shall report security-relevant diagnostic conditions in a manner that supports investigation without exposing cryptographic material. @S222 */ subject s : DualChannelOdometer; }
    requirement def R42 { doc /* The Dual Channel Odometer and Atlas Onboard Controller shall report security-relevant diagnostic conditions in a manner that supports investigation without exposing cryptographic material. @S222 */ subject s : AtlasOnboardController; }
    requirement def R43 { doc /* Each test train shall be crewed by a Revenue Train Operator qualified for commissioning duties and supported by a Line Traffic Controller with authority to stop the trial when observed conditions depart from the approved script. @S226 */ subject s : TestTrain; }
    requirement def R44 { doc /* The South District Zone Controller shall be commissioned under the same test regime so that boundary behavior is verified before whole-line operation is attempted. @S228 */ subject s : SouthDistrictZoneController; }
    requirement def R45 { doc /* East Junction Interlocking and West Junction Interlocking shall remain under enhanced monitoring during migration because route setting, point detection, and authority release behavior are critical to mixed-mode operation. @S229 */ subject s : EastJunctionInterlocking; }
    requirement def R46 { doc /* East Junction Interlocking and West Junction Interlocking shall remain under enhanced monitoring during migration because route setting, point detection, and authority release behavior are critical to mixed-mode operation. @S229 */ subject s : WestJunctionInterlocking; }
    requirement def R47 { doc /* Before any cutover stage, the Safety Data Communication Network and Wayside Radio Access Network shall be verified for coverage, latency, redundancy, and alarm presentation at the control center. @S232 */ subject s : SafetyDataCommunicationNetwork; }
    requirement def R48 { doc /* Before any cutover stage, the Safety Data Communication Network and Wayside Radio Access Network shall be verified for coverage, latency, redundancy, and alarm presentation at the control center. @S232 */ subject s : WaysideRadioAccessNetwork; }
    requirement def R49 { doc /* The Platform Screen Door Controller shall be included in end-to-end tests that confirm safe coordination between platform equipment, train stopping position, and supervised door enablement. @S234 */ subject s : PlatformScreenDoorController; }
    requirement def R50 { doc /* The Service Timetable Server shall provide trial schedules that exercise normal headways, recovery margins, terminal reversals, and junction conflicts without carrying passengers. @S235 */ subject s : ServiceTimetableServer; }
    requirement def R51 { doc /* The Passenger Information Gateway shall be observed during operational rehearsal to confirm that public-facing messages remain consistent with the planned commissioning condition. @S236 */ subject s : PassengerInformationGateway; }
    requirement def R52 { doc /* Voice Dispatch Console procedures shall be rehearsed for test-train dispatch, abnormal stop instructions, evacuation coordination, and return to depot instructions. @S237 */ subject s : VoiceDispatchConsole; }
    requirement def R53 { doc /* The Maintenance Diagnostic Server shall collect commissioning diagnostics so that intermittent radio, odometry, controller, and interlocking events can be reviewed before acceptance. @S238 */ subject s : MaintenanceDiagnosticServer; }
    requirement def R54 { doc /* The Cryptographic Key Management Appliance shall be confirmed as available, synchronized with the approved security baseline, and capable of supporting commissioning operations without manual workarounds. @S239 */ subject s : CryptographicKeyManagementAppliance; }
    requirement def R55 { doc /* Readiness reviews shall be held at the completion of each stage and shall include representatives from operations, signalling maintenance, rolling stock, communications, safety assurance, and cyber security. @S240 */ subject s : ReadinessReviews; }
    requirement def R56 { doc /* A Signal Maintenance Engineer shall verify that field defects raised during test running have been closed, deferred with approved controls, or assigned to a post-commissioning monitoring plan. @S241 */ subject s : SignalMaintenanceEngineer; }
    requirement def R57 { doc /* A Cyber Security Officer shall confirm that access controls, event monitoring, operator accounts, and security incident escalation paths are effective before revenue operation is recommended. @S242 */ subject s : CyberSecurityOfficer; }
    requirement def R58 { doc /* Operational rehearsal shall use realistic degraded scenarios including radio coverage loss, failed train initialization, controller switchover, interlocking unavailability, and control center workstation failure. @S243 */ subject s : OperationalRehearsal; }
    requirement def R59 { doc /* The rehearsal shall demonstrate that the Line Traffic Controller can maintain safe service regulation while the Revenue Train Operator follows onboard indications and rulebook instructions. @S244 */ subject s : LineTrafficController; }
    requirement def R60 { doc /* Acceptance for revenue service shall require completion of planned test cases, closure of safety-critical defects, successful rollback demonstration, and approval of the operations readiness record. @S245 */ subject s : AcceptanceForRevenueService; }
    requirement def R61 { doc /* No open defect shall be accepted for revenue service unless its operational restriction, maintenance response, and passenger impact have been assessed and approved by the readiness review authority. @S246 */ subject s : ReadinessReviewAuthority; }
    requirement def R62 { doc /* Final entry into revenue service shall occur only after management confirms that training, documentation, staffing, spare equipment, monitoring arrangements, and emergency procedures are in place for sustained operation. @S247 */ subject s : Management; }
}
