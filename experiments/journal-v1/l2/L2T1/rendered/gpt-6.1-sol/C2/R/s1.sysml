package L2Model {
    item def AcknowledgementsItem { doc /* @S044 */ }
    item def ActiveBearerItem { doc /* @S055 */ }
    item def AlarmsItem { doc /* @S009 */ }
    item def ApprovedServiceMessagesItem { doc /* @S015 */ }
    item def AxleCounterResetRequestItem { doc /* @S189 */ }
    item def BrakeCurveChecksumLogItem { doc /* @S154 */ }
    item def CommandedRouteItem { doc /* @S098 */ }
    item def ConflictItem { doc /* @S105 */ }
    item def ConsolidatedTrainPositionsItem { doc /* @S009 */ }
    item def CrewLoginTokenBundleItem { doc /* @S095 */ }
    item def DataItem { doc /* @S012 */ }
    item def DoorClosedAndLockedIndicationsItem { doc /* @S093 */ }
    item def DoorEnableAndClosedAndLockedIndicationsItem { doc /* @S046 */ }
    item def EncryptionCertificateRenewalPackItem { doc /* @S146 */ }
    item def EquipmentRecoveryOptionsItem { doc /* @S120 */ }
    item def EventStreamsItem { doc /* @S153 */ }
    item def ExceptionsItem { doc /* @S018 */ }
    item def FallbackVoiceCoordinationPathItem { doc /* @S016 */ }
    item def IndependentSpeedAndDistanceMeasurementsItem { doc /* @S031 */ }
    item def LinkQualityItem { doc /* @S039 */ }
    item def LockedRouteItem { doc /* @S098 */ }
    item def LossOfSafeDataConnectivityItem { doc /* @S181 */ }
    item def MovementAuthorityDataItem { doc /* @S029 */ }
    item def MovementAuthorityLimitsItem { doc /* @S043 */ }
    item def NonVitalHealthIndicationsItem { doc /* @S050 */ }
    item def NonVitalTrainPositionItem { doc /* @S047 */ }
    item def NonVitalTrendDataItem { doc /* @S119 */ }
    item def OperationalCertificatesItem { doc /* @S207 */ }
    item def OperatorCommandInterfacesItem { doc /* @S009 */ }
    item def PermittedInterfaceIndicationsItem { doc /* @S075 */ }
    item def PermittedSpeedItem { doc /* @S043 */ }
    item def PlannedServiceDataItem { doc /* @S015 */ }
    item def PlatformDoorStatusSnapshotItem { doc /* @S129,S233 */ }
    item def PlatformInterfaceIndicationsItem { doc /* @S017 */ }
    item def PointStateItem { doc /* @S098 */ }
    item def RadioConditionItem { doc /* @S043 */ }
    item def RadioCoverageAlarmsItem { doc /* @S071 */ }
    item def RadioHandoverAuditFileItem { doc /* @S206 */ }
    item def RadioQualityChangesItem { doc /* @S055 */ }
    item def RecordedHandbackItem { doc /* @S199 */ }
    item def RegistrationStateItem { doc /* @S039 */ }
    item def RequiredOperatorActionsItem { doc /* @S043 */ }
    item def RouteLockingStatusItem { doc /* @S068 */ }
    item def RouteReleaseExceptionListItem { doc /* @S157 */ }
    item def RouteStateIndicationsItem { doc /* @S108 */ }
    item def RouteStatusItem { doc /* @S101 */ }
    item def RoutesItem { doc /* @S079 */ }
    item def ScheduleContextItem { doc /* @S048 */ }
    item def SecurityEventsItem { doc /* @S202 */ }
    item def SecurityMaterialItem { doc /* @S042 */ }
    item def SelectedFaultSummariesItem { doc /* @S165 */ }
    item def ServiceRegulationFunctionsItem { doc /* @S009 */ }
    item def SessionContinuityInformationItem { doc /* @S039 */ }
    item def SwitchStateItem { doc /* @S068 */ }
    item def TestTrainClearanceMemoItem { doc /* @S216 */ }
    item def TrackOccupancyItem { doc /* @S068 */ }
    item def TrackOccupancyStateItem { doc /* @S098 */ }
    item def TrainLocationConfidenceItem { doc /* @S043 */ }
    item def TrainPositionItem { doc /* @S066 */ }
    item def TrainPositionsItem { doc /* @S101 */ }
    item def TrainSupervisionStatesItem { doc /* @S071 */ }
    item def UnavailableRouteConditionItem { doc /* @S105 */ }
    item def UnsafeDoorInterfaceStateItem { doc /* @S132 */ }
    item def VitalMovementAuthorityTrafficItem { doc /* @S051 */ }
    item def ZoneStatusItem { doc /* @S071 */ }
    part def AcceptanceForRevenueService { doc /* @S245 */ }
    part def AccessApprovals { doc /* @S217 */ }
    part def AdministrativeAccessToTheCryptographicKeyManagementAppliance { doc /* @S213 */ }
    part def AffectedTrainMovements { doc /* @S138 */ }
    part def AlarmAcknowledgements { doc /* @S217 */ }
    part def AlertsAffectingTrainControlAvailability { doc /* @S204 */ }
    part def ApprovedChangeReferences { doc /* @S170 */ }
    part def ApprovedEmergencySecurityProcedure { doc /* @S196 */ }
    part def ApprovedMaintenanceWindow { doc /* @S155 */ }
    part def AssociatedBerth { doc /* @S132 */ }
    part def AtlasOnboardController { doc /* @S012,S025,S027,S028,S029,S031,S032,S033,S036,S037,S039,S044,S051,S055,S057,S066,S095,S111,S144,S154,S161,S178,S181,S209,S222,S227 */ }
    part def AuditEvidence { doc /* @S217 */ }
    part def AuditRecords { doc /* @S218 */ }
    part def AuthorizedTechnicalStaff { doc /* @S060 */ }
    part def AutomaticSupervision { doc /* @S018 */ }
    part def AxleCounterOccupation { doc /* @S086 */ }
    part def Block { doc /* @S184 */ }
    part def BrakeAssuranceFunctions { doc /* @S035 */ }
    part def CapacityConditions { doc /* @S114 */ }
    part def CentralControlRoom { doc /* @S009 */ }
    part def CentralRegulationFunctions { doc /* @S015 */ }
    part def CertificateActions { doc /* @S217 */ }
    part def CertificateIssuance { doc /* @S208 */ }
    part def CertificateRenewal { doc /* @S209 */ }
    part def CommandedPoints { doc /* @S185 */ }
    part def Commands { doc /* @S011 */ }
    part def Commissioning { doc /* @S224 */ }
    part def CommunicationsBasedTrainControlSystem { doc /* @S002,S018,S019,S020,S082,S086,S129 */ }
    part def ConfigurationChanges { doc /* @S217 */ }
    part def ConfigurationRecords { doc /* @S170 */ }
    part def ControlCenterComponents { doc /* @S207 */ }
    part def ControlStaff { doc /* @S098 */ }
    part def ControlledAreas { doc /* @S230 */ }
    part def CryptographicKeyManagementAppliance { doc /* @S042,S060,S123,S124,S146,S171,S196,S207,S239 */ }
    part def CustomerInformationSystems { doc /* @S015 */ }
    part def CutoverPlanning { doc /* @S231 */ }
    part def CyberEvent { doc /* @S220 */ }
    part def CyberSecurityOfficer { doc /* @S023,S125,S149,S156,S195,S202,S206,S214,S242 */ }
    part def CybersecurityControls { doc /* @S200 */ }
    part def CybersecurityEvent { doc /* @S205 */ }
    part def DirectVerbalInstruction { doc /* @S117 */ }
    part def DispatchRelatedControls { doc /* @S143 */ }
    part def DoorClosedAndLockedIndications { doc /* @S093 */ }
    part def DoorInterface { doc /* @S130,S132 */ }
    part def DualChannelOdometer { doc /* @S012,S031,S066,S112,S162,S180,S222 */ }
    part def EastJunctionInterlocking { doc /* @S011,S030,S068,S079,S087,S107,S160,S185,S189,S210,S229 */ }
    part def EndToEndTests { doc /* @S234 */ }
    part def FailureTriage { doc /* @S167 */ }
    part def FieldConfirmation { doc /* @S185 */ }
    part def FieldStaff { doc /* @S016 */ }
    part def FinalEntryIntoRevenueService { doc /* @S247 */ }
    part def FixedEquipment { doc /* @S153 */ }
    part def GreenvaleMetroCommunicationsBasedTrainControlSystem { doc /* @S134,S136,S150,S175,S176,S199 */ }
    part def Handover { doc /* @S056 */ }
    part def InconsistentConditions { doc /* @S069 */ }
    part def InitialMovements { doc /* @S227 */ }
    part def Interface { doc /* @S047 */ }
    part def InterlockingDataVersions { doc /* @S170 */ }
    part def LineTrafficController { doc /* @S006,S016,S018,S071,S099,S101,S103,S104,S105,S109,S110,S116,S120,S121,S142,S157,S165,S168,S176,S187,S205,S226,S244 */ }
    part def LocalStationStaff { doc /* @S133 */ }
    part def MaintenanceComponents { doc /* @S207 */ }
    part def MaintenanceControl { doc /* @S199 */ }
    part def MaintenanceDiagnosticServer { doc /* @S050,S072,S100,S119,S148,S153,S154,S169,S194,S212,S238 */ }
    part def MaintenanceTraffic { doc /* @S153 */ }
    part def Management { doc /* @S247 */ }
    part def ManualRouteRecovery { doc /* @S187 */ }
    part def MeasuredDivergence { doc /* @S032 */ }
    part def MetroOperationsControlSystem { doc /* @S009,S024,S047,S048,S071,S095,S098,S101,S102,S104,S135,S140,S165,S177,S202,S216,S233 */ }
    part def MonitoredInputPath { doc /* @S044 */ }
    part def MonitoredInterfaces { doc /* @S153 */ }
    part def MovementAuthorityEnvironment { doc /* @S128 */ }
    part def NewPath { doc /* @S056 */ }
    part def NonVitalTrendData { doc /* @S119 */ }
    part def NorthDistrictZoneController { doc /* @S010,S029,S063,S068,S079,S105,S132,S158,S183,S209,S227 */ }
    part def ObservedConditions { doc /* @S226 */ }
    part def OdometryConfidence { doc /* @S033 */ }
    part def OldRadioPath { doc /* @S056 */ }
    part def OnboardCommunications { doc /* @S042 */ }
    part def OnboardEquipment { doc /* @S153 */ }
    part def OpenDefect { doc /* @S246 */ }
    part def OperatingActions { doc /* @S033 */ }
    part def OperatingResponse { doc /* @S201 */ }
    part def OperationalContext { doc /* @S219 */ }
    part def OperationalRehearsal { doc /* @S243,S244 */ }
    part def OperationsControl { doc /* @S199 */ }
    part def OperationsControlCentre { doc /* @S108 */ }
    part def OperationsControlCentreWorkflow { doc /* @S101 */ }
    part def OperatorInstructionsRelatedToCommunicationsSecurity { doc /* @S217 */ }
    part def OperatorInterface { doc /* @S043 */ }
    part def ParameterSetIdentifiers { doc /* @S170 */ }
    part def PassengerFacingSystems { doc /* @S140 */ }
    part def PassengerInformationGateway { doc /* @S015,S047,S076,S122,S136,S137,S198,S219,S236 */ }
    part def PassengerInformationInterface { doc /* @S138 */ }
    part def PassengerSystems { doc /* @S047 */ }
    part def Platform { doc /* @S138 */ }
    part def PlatformDoorReadiness { doc /* @S094 */ }
    part def PlatformEquipment { doc /* @S128 */ }
    part def PlatformScreenDoorController { doc /* @S017,S046,S075,S093,S129,S192,S221,S233,S234 */ }
    part def Points { doc /* @S082 */ }
    part def ProceduralConfirmation { doc /* @S016 */ }
    part def ProtectedRepository { doc /* @S174 */ }
    part def RadioConfigurationVersions { doc /* @S170 */ }
    part def RadioSites { doc /* @S054 */ }
    part def RadioSubsystem { doc /* @S039 */ }
    part def Railway { doc /* @S230 */ }
    part def ReadinessReviews { doc /* @S240 */ }
    part def RelatedNonVitalFunctions { doc /* @S048 */ }
    part def ReleaseAnomaly { doc /* @S157 */ }
    part def RemoteConnections { doc /* @S156 */ }
    part def Reset { doc /* @S193 */ }
    part def ResetAuthorizations { doc /* @S193 */ }
    part def RestrictedManualMovements { doc /* @S190 */ }
    part def RevenueTrainOperator { doc /* @S016,S043,S044,S117,S118,S166,S191,S197,S215,S216,S244 */ }
    part def Revocation { doc /* @S211 */ }
    part def Route { doc /* @S082,S107 */ }
    part def RouteStateIndications { doc /* @S108 */ }
    part def SafetyCase { doc /* @S201 */ }
    part def SafetyCriticalStateMachine { doc /* @S028 */ }
    part def SafetyDataCommunicationNetwork { doc /* @S014,S040,S041,S051,S058,S147,S164,S202,S232 */ }
    part def SafetyRelatedPart { doc /* @S152 */ }
    part def SecurityEvents { doc /* @S023,S204 */ }
    part def SecurityMonitoring { doc /* @S203 */ }
    part def SecurityResponsibilities { doc /* @S223 */ }
    part def SecurityWarnings { doc /* @S215 */ }
    part def ServiceRisk { doc /* @S113 */ }
    part def ServiceTimetableServer { doc /* @S015,S048,S076,S139,S219,S235 */ }
    part def Session { doc /* @S055 */ }
    part def SignalMaintenanceEngineer { doc /* @S022,S050,S072,S089,S119,S120,S148,S168,S188,S189,S214,S241 */ }
    part def SoftwareBuildIdentifiers { doc /* @S170 */ }
    part def SouthDistrictZoneController { doc /* @S010,S029,S064,S068,S080,S106,S159,S184,S209,S228 */ }
    part def SpokenInstructions { doc /* @S141 */ }
    part def StagedMigrationFromLegacySignalling { doc /* @S230 */ }
    part def StationEquipment { doc /* @S127 */ }
    part def StationStatusIndications { doc /* @S134 */ }
    part def SupervisingWaysideSystems { doc /* @S075,S093 */ }
    part def TemporaryOperatingConstraint { doc /* @S110 */ }
    part def TestTrain { doc /* @S226 */ }
    part def TestTrainPhase { doc /* @S225 */ }
    part def TimeSynchronizedEventRecords { doc /* @S217 */ }
    part def Train { doc /* @S025,S046,S088,S094,S128 */ }
    part def TrainAuthority { doc /* @S065 */ }
    part def TrainControlEnvironment { doc /* @S017 */ }
    part def TrainControlMessages { doc /* @S040 */ }
    part def TrainIntegrityIndications { doc /* @S025 */ }
    part def TrainInterface { doc /* @S046 */ }
    part def TrainLocation { doc /* @S180 */ }
    part def TrainRadioModem { doc /* @S013,S038,S053,S055,S113,S146,S163,S181,S206,S209 */ }
    part def TrainRadioModemMessages { doc /* @S096 */ }
    part def TrainborneComponents { doc /* @S207 */ }
    part def TrainborneEquipment { doc /* @S050 */ }
    part def TrainborneInterfaceToPropulsionAndBrakingEquipment { doc /* @S034 */ }
    part def TrialSchedules { doc /* @S235 */ }
    part def VerifiedDiagnosticIndication { doc /* @S185 */ }
    part def VoiceDispatchConsole { doc /* @S016,S045,S074,S141,S220 */ }
    part def VoiceDispatchConsoleProcedures { doc /* @S237 */ }
    part def WaysideComponents { doc /* @S207 */ }
    part def WaysideRadioAccessNetwork { doc /* @S013,S053,S073,S145,S164,S202,S232 */ }
    part def WaysideSupervision { doc /* @S069,S070 */ }
    part def WestJunctionInterlocking { doc /* @S011,S030,S068,S081,S090,S108,S157,S160,S186,S209,S229 */ }
    part system {
        part acceptanceForRevenueService : AcceptanceForRevenueService {
            perform action a0 { doc /* require completion of planned test cases, closure of safety-critical defects, successful rollback demonstration, and approval of the operations readiness record @S245 */ }
        }
        part accessApprovals : AccessApprovals;
        part administrativeAccessToTheCryptographicKeyManagementAppliance : AdministrativeAccessToTheCryptographicKeyManagementAppliance {
            perform action a0 { doc /* require named accounts, multifactor authentication, separation of duties, and recorded approval for privileged changes @S213 */ }
        }
        part affectedTrainMovements : AffectedTrainMovements {
            exhibit state modes {
                state s0 { doc /* unavailable for boarding @S138 */ }
            }
        }
        part alarmAcknowledgements : AlarmAcknowledgements;
        part alertsAffectingTrainControlAvailability : AlertsAffectingTrainControlAvailability;
        part approvedChangeReferences : ApprovedChangeReferences;
        part approvedEmergencySecurityProcedure : ApprovedEmergencySecurityProcedure {
            exhibit state modes {
                state s0 { doc /* active @S196 */ }
            }
        }
        part approvedMaintenanceWindow : ApprovedMaintenanceWindow {
            perform action a0 { doc /* authorises a specific intervention @S155 */ }
        }
        part associatedBerth : AssociatedBerth {
            perform action a0 { doc /* reports an unsafe door interface state @S132 */ }
        }
        part atlasOnboardController : AtlasOnboardController {
            perform action a0 { doc /* supervises automatic train protection functions on each equipped train @S012 */ }
            perform action a1 { doc /* uses data from Dual Channel Odometer @S012 */ }
            perform action a2 { doc /* maintain a validated estimate of train position and speed @S012 */ }
            perform action a3 { doc /* assumes the active train control role @S025 */ }
            perform action a4 { doc /* supervises movement authority processing, onboard speed enforcement, door enable logic, and train interface commands required for CBTC operation @S027 */ }
            perform action a5 { doc /* maintains a safety-critical state machine @S028 */ }
            perform action a6 { doc /* compares the two odometry channels continuously @S032 */ }
            perform action a7 { doc /* degrades the operating mode @S032 */ }
            perform action a8 { doc /* increase position uncertainty @S033 */ }
            perform action a9 { doc /* request operating actions that preserve separation from other trains @S033 */ }
            perform action a10 { doc /* recalculates the braking demand needed to keep the train within the authorized movement limits @S036 */ }
            perform action a11 { doc /* keep the train within the authorized movement limits @S036 */ }
            perform action a12 { doc /* produces the Brake Curve Checksum Log @S037 */ }
            perform action a13 { doc /* validating the active enforcement data set @S037 */ }
            perform action a14 { doc /* used by the Atlas Onboard Controller @S055 */ }
            perform action a15 { doc /* falls back to the last validated movement authority rules @S057 */ }
            perform action a16 { doc /* accepting unverified wayside data @S057 */ }
            perform action a17 { doc /* confirms train position from the Dual Channel Odometer @S066 */ }
            perform action a18 { doc /* accepting the next authority source @S066 */ }
            perform action a19 { doc /* uses the token bundle @S095 */ }
            perform action a20 { doc /* validate that onboard operating context is current @S095 */ }
            perform action a21 { doc /* accepting supervised route-related data @S095 */ }
            perform action a22 { doc /* enforces the active movement profile on each equipped train @S111 */ }
            perform action a23 { doc /* presents any onboard rejection or degraded mode indication for operational assessment @S111 */ }
            perform action a24 { doc /* shall report train door enable side, berth identity, and departure readiness @S144 */ }
            perform action a25 { doc /* support platform interface checks during dwell and dispatch @S144 */ }
            perform action a26 { doc /* stores onboard fault codes, movement authority acceptance records, propulsion cutback requests, and train interface exceptions for later retrieval @S161 */ }
            perform action a27 { doc /* transitions to restricted manual operation when valid movement authority is unavailable or when onboard location confidence falls below the configured threshold @S178 */ }
            perform action a28 { doc /* do not enter service with degraded trust @S209 */ }
            perform action a29 { doc /* report security-relevant diagnostic conditions in a manner that supports investigation without exposing cryptographic material @S222 */ }
            perform action a30 { doc /* exposing cryptographic material @S222 */ }
            perform action a31 { doc /* demonstrate stable supervision @S227 */ }
            exhibit state modes {
                state s0 { doc /* automatic train operation @S028 */ }
                state s1 { doc /* cutout conditions @S028 */ }
                state s2 { doc /* degraded mode @S111 */ }
                state s3 { doc /* fallback operation @S028 */ }
                state s4 { doc /* initialization @S028 */ }
                state s5 { doc /* protected manual operation @S028 */ }
                state s6 { doc /* restricted manual operation @S178 */ }
            }
        }
        part auditEvidence : AuditEvidence;
        part auditRecords : AuditRecords;
        part authorizedTechnicalStaff : AuthorizedTechnicalStaff {
            perform action a0 { doc /* is managed under controlled access by authorized technical staff @S060 */ }
        }
        part automaticSupervision : AutomaticSupervision {
            perform action a0 { doc /* regulate headways @S018 */ }
            perform action a1 { doc /* enforce safe separation @S018 */ }
            perform action a2 { doc /* present the Line Traffic Controller with exceptions rather than routine control steps @S018 */ }
        }
        part axleCounterOccupation : AxleCounterOccupation {
            perform action a0 { doc /* conflicts with the train location estimated by the CBTC system @S086 */ }
        }
        part block : Block {
            exhibit state modes {
                state s0 { doc /* manual confirmation @S184 */ }
            }
        }
        part brakeAssuranceFunctions : BrakeAssuranceFunctions {
            perform action a0 { doc /* verify service and emergency brake availability @S035 */ }
            perform action a1 { doc /* monitoring brake feedback, pneumatic pressure indications, and commanded deceleration response @S035 */ }
        }
        part capacityConditions : CapacityConditions {
            perform action a0 { doc /* could affect the stability of train control communications @S114 */ }
        }
        part centralControlRoom : CentralControlRoom;
        part centralRegulationFunctions : CentralRegulationFunctions;
        part certificateActions : CertificateActions;
        part certificateIssuance : CertificateIssuance {
            perform action a0 { doc /* require approved asset identity, recorded software baseline, assigned operating domain, and confirmation that the requesting component is authorized for service @S208 */ }
        }
        part certificateRenewal : CertificateRenewal;
        part commandedPoints : CommandedPoints {
            exhibit state modes {
                state s0 { doc /* locked @S185 */ }
            }
        }
        part commands : Commands {
            perform action a0 { doc /* satisfy their configured safety rules @S011 */ }
        }
        part commissioning : Commissioning {
            perform action a0 { doc /* begin @S224 */ }
        }
        part communicationsBasedTrainControlSystem : CommunicationsBasedTrainControlSystem {
            perform action a0 { doc /* supervising train separation, movement authority, and service regulation on the controlled portions of the railway @S002 */ }
            perform action a1 { doc /* treats a route as available @S082 */ }
            perform action a2 { doc /* estimated by the CBTC system @S086 */ }
            exhibit state modes {
                state s0 { doc /* defined safe state @S019 */ }
                state s1 { doc /* degraded operation @S019 */ }
                state s2 { doc /* normal operation @S018 */ }
                state s3 { doc /* protective restriction of movement @S020 */ }
            }
        }
        part configurationChanges : ConfigurationChanges;
        part configurationRecords : ConfigurationRecords;
        part controlCenterComponents : ControlCenterComponents;
        part controlStaff : ControlStaff {
            perform action a0 { doc /* can identify mismatches @S098 */ }
        }
        part controlledAreas : ControlledAreas;
        part cryptographicKeyManagementAppliance : CryptographicKeyManagementAppliance {
            perform action a0 { doc /* supports the security material used by onboard communications @S042 */ }
            perform action a1 { doc /* without changing the safety logic executed on the train @S042 */ }
            perform action a2 { doc /* supports the authentication framework used on the safety data paths @S060 */ }
            perform action a3 { doc /* uses the sample report @S123 */ }
            perform action a4 { doc /* verify that certificate validity windows and controller clocks remain within the permitted tolerance @S123 */ }
            perform action a5 { doc /* produces the Encryption Certificate Renewal Pack under an approved maintenance window @S124 */ }
            perform action a6 { doc /* records the change reference for later security audit @S124 */ }
            perform action a7 { doc /* maintains certificate and key status records used to verify whether communications faults could be related to authentication or expiry conditions @S171 */ }
            perform action a8 { doc /* supporting commissioning operations without manual workarounds @S239 */ }
        }
        part customerInformationSystems : CustomerInformationSystems;
        part cutoverPlanning : CutoverPlanning {
            perform action a0 { doc /* define the exact control boundaries, permissible train movements, staffing levels, and rollback conditions for each migration stage @S231 */ }
        }
        part cyberEvent : CyberEvent {
            perform action a0 { doc /* changes the normal method for issuing operational instructions @S220 */ }
        }
        part cyberSecurityOfficer : CyberSecurityOfficer {
            perform action a0 { doc /* oversees access controls, key-management processes supported by Cryptographic Key Management Appliance, and the response to security events that could affect train control availability or integrity @S023 */ }
            perform action a1 { doc /* reviews certificate change records, access events, and unusual authentication failures @S125 */ }
            perform action a2 { doc /* authorising normal operational reliance on the renewed security configuration @S125 */ }
            perform action a3 { doc /* reviews access rights for passenger information and dispatch integration workstations @S149 */ }
            perform action a4 { doc /* reviews privileged diagnostic access logs @S156 */ }
            perform action a5 { doc /* confirms that remote connections use current credentials and approved encryption settings @S156 */ }
            perform action a6 { doc /* review any degraded condition that involves authentication failure, unexpected lockout, or abnormal network access behavior @S195 */ }
            perform action a7 { doc /* maintain continuous monitoring of security events from the Safety Data Communication Network, the Wayside Radio Access Network, and the Metro Operations Control System @S202 */ }
            perform action a8 { doc /* uses the audit file @S206 */ }
            perform action a9 { doc /* investigate radio session continuity @S206 */ }
            perform action a10 { doc /* confirm that security monitoring records are complete @S206 */ }
            perform action a11 { doc /* approve security-sensitive permissions @S214 */ }
            perform action a12 { doc /* confirm that access controls, event monitoring, operator accounts, and security incident escalation paths are effective @S242 */ }
        }
        part cybersecurityControls : CybersecurityControls;
        part cybersecurityEvent : CybersecurityEvent {
            perform action a0 { doc /* requires a restriction on automatic operation or a change in communications mode @S205 */ }
        }
        part directVerbalInstruction : DirectVerbalInstruction;
        part dispatchRelatedControls : DispatchRelatedControls {
            perform action a0 { doc /* use positive confirmation and cancellation states @S143 */ }
            exhibit state modes {
                state s0 { doc /* cancellation @S143 */ }
                state s1 { doc /* positive confirmation @S143 */ }
            }
        }
        part doorClosedAndLockedIndications : DoorClosedAndLockedIndications {
            perform action a0 { doc /* do not replace interlocking route proof @S093 */ }
        }
        part doorInterface : DoorInterface {
            perform action a0 { doc /* reports closed, locked, bypassed, inhibited, and faulted conditions using coded states that are interpreted consistently across the line @S130 */ }
            perform action a1 { doc /* using coded states @S130 */ }
            exhibit state modes {
                state s0 { doc /* bypassed @S130 */ }
                state s1 { doc /* closed @S130 */ }
                state s2 { doc /* faulted @S130 */ }
                state s3 { doc /* inhibited @S130 */ }
                state s4 { doc /* locked @S130 */ }
                state s5 { doc /* unsafe door interface state @S132 */ }
            }
        }
        part dualChannelOdometer : DualChannelOdometer {
            perform action a0 { doc /* provides independent speed and distance measurements derived from axle rotation, inertial sensing, and configured calibration parameters @S031 */ }
            perform action a1 { doc /* supports train position confidence @S112 */ }
            perform action a2 { doc /* providing independent distance measurement inputs @S112 */ }
            perform action a3 { doc /* provides distance and speed plausibility information that is retained with trainborne diagnostic records after any odometry disagreement @S162 */ }
            perform action a4 { doc /* cause the train location to be treated as uncertain when its channels disagree beyond the permitted tolerance @S180 */ }
            perform action a5 { doc /* report security-relevant diagnostic conditions in a manner that supports investigation without exposing cryptographic material @S222 */ }
            perform action a6 { doc /* exposing cryptographic material @S222 */ }
        }
        part eastJunctionInterlocking : EastJunctionInterlocking {
            perform action a0 { doc /* maintain vital control of points and signals at the principal junction areas @S011 */ }
            perform action a1 { doc /* only accept commands that satisfy their configured safety rules @S011 */ }
            perform action a2 { doc /* report switch state, track occupancy, and route locking status to the responsible zone controller through vital interfaces @S068 */ }
            perform action a3 { doc /* sends the Axle Counter Reset Request under the configured degraded-mode reset procedure @S087 */ }
            perform action a4 { doc /* holds the route locked until track section detection, point correspondence, and opposing route conditions meet the configured release criteria @S107 */ }
            perform action a5 { doc /* report route command histories, point detection changes, and protective lock status @S160 */ }
            perform action a6 { doc /* support failure localisation @S160 */ }
            perform action a7 { doc /* hold commanded points locked until field confirmation or a verified diagnostic indication supports a safe release @S185 */ }
            perform action a8 { doc /* reject any control message with an invalid signature, an expired certificate, or a sequence value outside the accepted window @S210 */ }
            perform action a9 { doc /* remain under enhanced monitoring during migration @S229 */ }
        }
        part endToEndTests : EndToEndTests {
            perform action a0 { doc /* confirm safe coordination between platform equipment, train stopping position, and supervised door enablement @S234 */ }
        }
        part failureTriage : FailureTriage {
            perform action a0 { doc /* establishes whether the condition is safety critical, service affecting, cyber security related, or a maintenance-only defect @S167 */ }
        }
        part fieldConfirmation : FieldConfirmation {
            perform action a0 { doc /* supports a safe release @S185 */ }
        }
        part fieldStaff : FieldStaff;
        part finalEntryIntoRevenueService : FinalEntryIntoRevenueService {
            perform action a0 { doc /* occur only after management confirms that training, documentation, staffing, spare equipment, monitoring arrangements, and emergency procedures are in place for sustained operation @S247 */ }
        }
        part fixedEquipment : FixedEquipment;
        part greenvaleMetroCommunicationsBasedTrainControlSystem : GreenvaleMetroCommunicationsBasedTrainControlSystem {
            perform action a0 { doc /* has reconciled them with the active timetable @S136 */ }
            perform action a1 { doc /* favours restrictive platform states @S150 */ }
            perform action a2 { doc /* requires explicit controller action before restoring automatic departure support at the affected station @S150 */ }
            perform action a3 { doc /* keeps trains stationary or moving at controlled speed until separation assurance is restored @S175 */ }
            exhibit state modes {
                state s0 { doc /* automatic operation @S199 */ }
                state s1 { doc /* degraded mode @S176 */ }
                state s2 { doc /* degraded operation @S150,S175 */ }
                state s3 { doc /* door interlock fault @S134 */ }
                state s4 { doc /* emergency stop active @S134 */ }
                state s5 { doc /* evacuation support @S134 */ }
                state s6 { doc /* held train @S134 */ }
                state s7 { doc /* normal service @S134 */ }
                state s8 { doc /* radio degraded @S134 */ }
            }
        }
        part handover : Handover {
            perform action a0 { doc /* is planned as a make-before-break event where practical @S056 */ }
        }
        part inconsistentConditions : InconsistentConditions {
            perform action a0 { doc /* can affect service @S069 */ }
        }
        part initialMovements : InitialMovements {
            perform action a0 { doc /* progress to representative service speeds @S227 */ }
        }
        part interfacePart : Interface {
            perform action a0 { doc /* prevents passenger systems from influencing safety decisions @S047 */ }
        }
        part interlockingDataVersions : InterlockingDataVersions;
        part lineTrafficController : LineTrafficController {
            perform action a0 { doc /* monitoring service performance @S006 */ }
            perform action a1 { doc /* authorizing planned operational changes @S006 */ }
            perform action a2 { doc /* coordinating incident response @S006 */ }
            perform action a3 { doc /* directing recovery actions when automatic regulation is insufficient @S006 */ }
            perform action a4 { doc /* can manage service without direct intervention in vital logic @S071 */ }
            perform action a5 { doc /* may request a regulating action @S099 */ }
            perform action a6 { doc /* maintaining a live view of train positions, route status, alarms, and service performance across the Greenvale Metro line @S101 */ }
            perform action a7 { doc /* selects holding, skip-stop, turnback, or run-through measures @S103 */ }
            perform action a8 { doc /* checking that passenger impact and downstream recovery have been assessed @S103 */ }
            perform action a9 { doc /* confirms the command @S104 */ }
            perform action a10 { doc /* produces the Temporary Speed Restriction Notice @S109 */ }
            perform action a11 { doc /* confirming the limits, speed value, start time, and expected removal condition @S109 */ }
            perform action a12 { doc /* monitors actual train performance against the expected delay allowance @S110 */ }
            perform action a13 { doc /* adjusts regulation plans when recovery margins are exceeded @S110 */ }
            perform action a14 { doc /* records the initial event time, train identifier, location, passenger impact, and the first safe operating instruction issued @S116 */ }
            perform action a15 { doc /* verifies that the revised plan is visible @S121 */ }
            perform action a16 { doc /* relying on it for regulation @S121 */ }
            perform action a17 { doc /* may apply a station hold through dispatch controls @S142 */ }
            perform action a18 { doc /* receives the Route Release Exception List during incident triage @S157 */ }
            perform action a19 { doc /* uses it @S157 */ }
            perform action a20 { doc /* check whether a release anomaly could affect service recovery decisions @S157 */ }
            perform action a21 { doc /* confirms the operating restriction @S168 */ }
            perform action a22 { doc /* is declared by the Line Traffic Controller when automatic movement authority, train localization, point detection, platform interface, or radio continuity cannot be trusted @S176 */ }
            perform action a23 { doc /* confirms train positions through independent indications and direct verbal reports @S187 */ }
            perform action a24 { doc /* stop the trial @S226 */ }
            perform action a25 { doc /* maintain safe service regulation @S244 */ }
        }
        part localStationStaff : LocalStationStaff;
        part maintenanceComponents : MaintenanceComponents;
        part maintenanceControl : MaintenanceControl;
        part maintenanceDiagnosticServer : MaintenanceDiagnosticServer {
            perform action a0 { doc /* collects non-vital health indications from trainborne equipment @S050 */ }
            perform action a1 { doc /* receives non-vital summaries of radio and network health @S072 */ }
            perform action a2 { doc /* records route command outcomes, point operation timing, and detection transitions for later engineering review @S100 */ }
            perform action a3 { doc /* without participating in vital decisions @S100 */ }
            perform action a4 { doc /* provides non-vital trend data @S119 */ }
            perform action a5 { doc /* records station interface faults, rejected commands, and inconsistent indications @S148 */ }
            perform action a6 { doc /* receives event streams from fixed and onboard equipment through monitored interfaces that do not allow maintenance traffic to alter train movement authority @S153 */ }
            perform action a7 { doc /* uses the checksum log @S154 */ }
            perform action a8 { doc /* compare stored braking data identifiers against the expected maintenance baseline for the affected train @S154 */ }
            perform action a9 { doc /* preserves raw events, normalised event records, diagnostic session notes, and file integrity values for post-incident analysis @S169 */ }
            perform action a10 { doc /* mark each degraded-mode diagnostic session with the incident identifier @S194 */ }
            perform action a11 { doc /* bypass certificate checks @S212 */ }
            perform action a12 { doc /* create alternate trust paths into safety-related communications @S212 */ }
            perform action a13 { doc /* collect commissioning diagnostics @S238 */ }
        }
        part maintenanceTraffic : MaintenanceTraffic {
            perform action a0 { doc /* alter train movement authority @S153 */ }
        }
        part management : Management {
            perform action a0 { doc /* confirms that training, documentation, staffing, spare equipment, monitoring arrangements, and emergency procedures are in place for sustained operation @S247 */ }
        }
        part manualRouteRecovery : ManualRouteRecovery {
            perform action a0 { doc /* begins @S187 */ }
        }
        part measuredDivergence : MeasuredDivergence {
            perform action a0 { doc /* exceeds the permitted threshold @S032 */ }
        }
        part metroOperationsControlSystem : MetroOperationsControlSystem {
            perform action a0 { doc /* provides the control room with consolidated train positions, service regulation functions, alarms, and operator command interfaces @S009 */ }
            perform action a1 { doc /* sends the Crew Login Token Bundle as part of the controlled start-of-duty process @S024 */ }
            perform action a2 { doc /* displays zone status, radio coverage alarms, and train supervision states @S071 */ }
            perform action a3 { doc /* displays the commanded route, locked route, point state, and track occupancy state as separate indications @S098 */ }
            perform action a4 { doc /* presents regulating options based on timetable variance, platform dwell time, headway spacing, and the current availability of routes @S102 */ }
            perform action a5 { doc /* displays the proposed regulating action, affected train identities, and predicted recovery time @S104 */ }
            perform action a6 { doc /* displays station and platform states with the same identifiers used in controller workstations @S135 */ }
            perform action a7 { doc /* reduce interpretation errors during incidents @S135 */ }
            perform action a8 { doc /* coordinates timetable deviation, platform closure, and station crowding information @S140 */ }
            perform action a9 { doc /* displays selected fault summaries to the Line Traffic Controller @S165 */ }
            perform action a10 { doc /* does not expose detailed maintenance commands at the traffic control workstation @S165 */ }
            perform action a11 { doc /* present the affected limits, the selected fallback mode, and any pending operator actions without obscuring safety alarms @S177 */ }
            perform action a12 { doc /* uses the Test Train Clearance Memo as a controlled prerequisite @S216 */ }
            perform action a13 { doc /* accepting security exceptions for non-revenue movement in protected territory @S216 */ }
            perform action a14 { doc /* uses the status snapshot @S233 */ }
            perform action a15 { doc /* confirm that platform interface conditions are suitable @S233 */ }
            perform action a16 { doc /* authorizing the associated commissioning scenario @S233 */ }
        }
        part monitoredInputPath : MonitoredInputPath {
            perform action a0 { doc /* rejects stale or inconsistent commands @S044 */ }
        }
        part monitoredInterfaces : MonitoredInterfaces {
            perform action a0 { doc /* do not allow maintenance traffic to alter train movement authority @S153 */ }
        }
        part movementAuthorityEnvironment : MovementAuthorityEnvironment;
        part newPath : NewPath {
            perform action a0 { doc /* has accepted the session @S056 */ }
            perform action a1 { doc /* passed basic message checks @S056 */ }
        }
        part nonVitalTrendData : NonVitalTrendData {
            perform action a0 { doc /* helps the Signal Maintenance Engineer determine whether an incident has an equipment cause or an operational cause @S119 */ }
        }
        part northDistrictZoneController : NorthDistrictZoneController {
            perform action a0 { doc /* calculate safe movement authority limits @S010 */ }
            perform action a1 { doc /* using train location reports, track occupancy data, and the state of controlled field equipment @S010 */ }
            perform action a2 { doc /* supervises the northern main line, the northern turnback, and the approach to East Junction Interlocking within its configured limits @S063 */ }
            perform action a3 { doc /* requests routes through East Junction Interlocking @S079 */ }
            perform action a4 { doc /* applies movement authority constraints according to the confirmed operating state @S105 */ }
            perform action a5 { doc /* reports any conflict or unavailable route condition for controller review @S105 */ }
            perform action a6 { doc /* suppresses platform departure authority @S132 */ }
            perform action a7 { doc /* records controller health, interface state, and fallback mode transitions in a form that can be correlated with adjacent wayside and operations records @S158 */ }
            perform action a8 { doc /* applies the Temporary Speed Restriction Notice @S183 */ }
            perform action a9 { doc /* validating the affected track limits against its degraded-mode map @S183 */ }
            perform action a10 { doc /* do not enter service with degraded trust @S209 */ }
            perform action a11 { doc /* demonstrate stable supervision @S227 */ }
            exhibit state modes {
                state s0 { doc /* fallback mode @S158 */ }
            }
        }
        part observedConditions : ObservedConditions {
            perform action a0 { doc /* depart from the approved script @S226 */ }
        }
        part odometryConfidence : OdometryConfidence {
            exhibit state modes {
                state s0 { doc /* reduced @S033 */ }
            }
        }
        part oldRadioPath : OldRadioPath {
            perform action a0 { doc /* retained until the new path has accepted the session and passed basic message checks @S056 */ }
        }
        part onboardCommunications : OnboardCommunications;
        part onboardEquipment : OnboardEquipment;
        part openDefect : OpenDefect;
        part operatingActions : OperatingActions {
            perform action a0 { doc /* preserve separation from other trains @S033 */ }
        }
        part operatingResponse : OperatingResponse {
            perform action a0 { doc /* reflect that assumption @S201 */ }
        }
        part operationalContext : OperationalContext {
            perform action a0 { doc /* influence control room decisions @S219 */ }
        }
        part operationalRehearsal : OperationalRehearsal {
            perform action a0 { doc /* use realistic degraded scenarios including radio coverage loss, failed train initialization, controller switchover, interlocking unavailability, and control center workstation failure @S243 */ }
            perform action a1 { doc /* demonstrate that the Line Traffic Controller can maintain safe service regulation while the Revenue Train Operator follows onboard indications and rulebook instructions @S244 */ }
        }
        part operationsControl : OperationsControl;
        part operationsControlCentre : OperationsControlCentre {
            perform action a0 { doc /* distinguish an operational delay from a signalling equipment fault @S108 */ }
        }
        part operationsControlCentreWorkflow : OperationsControlCentreWorkflow {
            perform action a0 { doc /* begins with the Line Traffic Controller maintaining a live view of train positions, route status, alarms, and service performance across the Greenvale Metro line @S101 */ }
        }
        part operatorInstructionsRelatedToCommunicationsSecurity : OperatorInstructionsRelatedToCommunicationsSecurity;
        part operatorInterface : OperatorInterface {
            perform action a0 { doc /* presents movement authority limits, permitted speed, train location confidence, radio condition, and required operator actions to Revenue Train Operator @S043 */ }
        }
        part parameterSetIdentifiers : ParameterSetIdentifiers;
        part passengerFacingSystems : PassengerFacingSystems;
        part passengerInformationGateway : PassengerInformationGateway {
            perform action a0 { doc /* distributes approved service messages to customer information systems @S015 */ }
            perform action a1 { doc /* receives non-vital train position and service state data through an interface that prevents passenger systems from influencing safety decisions @S047 */ }
            perform action a2 { doc /* may receive selected service information @S076 */ }
            perform action a3 { doc /* receives the operational service state needed to align platform messages and train destination information with the current regulating plan @S122 */ }
            perform action a4 { doc /* align platform messages and train destination information with the current regulating plan @S122 */ }
            perform action a5 { doc /* receives train prediction data, stopping pattern changes, and platform allocation updates @S136 */ }
            perform action a6 { doc /* shall not publish a revised destination or skip-stop message until the underlying train identity and route have been confirmed by the CBTC system @S137 */ }
            perform action a7 { doc /* issue disruption messages that are consistent with the operating limits accepted by the Line Traffic Controller @S198 */ }
        }
        part passengerInformationInterface : PassengerInformationInterface {
            perform action a0 { doc /* marks the affected train movements as unavailable for boarding @S138 */ }
            perform action a1 { doc /* retaining their operational tracking in the control center @S138 */ }
        }
        part passengerSystems : PassengerSystems {
            perform action a0 { doc /* influencing safety decisions @S047 */ }
        }
        part platform : Platform {
            exhibit state modes {
                state s0 { doc /* out of service @S138 */ }
            }
        }
        part platformDoorReadiness : PlatformDoorReadiness {
            exhibit state modes {
                state s0 { doc /* absent @S094 */ }
            }
        }
        part platformEquipment : PlatformEquipment {
            perform action a0 { doc /* can prevent a train from arriving, dwelling, or departing safely @S128 */ }
        }
        part platformScreenDoorController : PlatformScreenDoorController {
            perform action a0 { doc /* exchanges platform interface indications with the train control environment @S017 */ }
            perform action a1 { doc /* exchanges door enable and closed-and-locked indications with the train interface @S046 */ }
            perform action a2 { doc /* exchanges only the permitted interface indications with the supervising wayside systems @S075 */ }
            perform action a3 { doc /* provides door closed and locked indications to the supervising wayside systems @S093 */ }
            perform action a4 { doc /* produces the Platform Door Status Snapshot at each monitored platform face for operational use by the CBTC system @S129 */ }
            perform action a5 { doc /* remains in a protected local state @S192 */ }
            perform action a6 { doc /* accept only authenticated interfaces approved for passenger service coordination and maintenance testing @S221 */ }
            exhibit state modes {
                state s0 { doc /* protected local state @S192 */ }
            }
        }
        part points : Points {
            exhibit state modes {
                state s0 { doc /* detected @S082 */ }
                state s1 { doc /* locked @S082 */ }
                state s2 { doc /* proved in the required position @S082 */ }
            }
        }
        part proceduralConfirmation : ProceduralConfirmation;
        part protectedRepository : ProtectedRepository;
        part radioConfigurationVersions : RadioConfigurationVersions;
        part radioSites : RadioSites {
            perform action a0 { doc /* are engineered with sector overlap at station throats and interlocking approaches @S054 */ }
        }
        part radioSubsystem : RadioSubsystem {
            perform action a0 { doc /* reports link quality, registration state, and session continuity information to Atlas Onboard Controller @S039 */ }
        }
        part railway : Railway;
        part readinessReviews : ReadinessReviews {
            perform action a0 { doc /* include representatives from operations, signalling maintenance, rolling stock, communications, safety assurance, and cyber security @S240 */ }
        }
        part relatedNonVitalFunctions : RelatedNonVitalFunctions;
        part releaseAnomaly : ReleaseAnomaly {
            perform action a0 { doc /* could affect service recovery decisions @S157 */ }
        }
        part remoteConnections : RemoteConnections {
            perform action a0 { doc /* use current credentials and approved encryption settings @S156 */ }
        }
        part reset : Reset {
            perform action a0 { doc /* can change route availability or occupancy status @S193 */ }
        }
        part resetAuthorizations : ResetAuthorizations;
        part restrictedManualMovements : RestrictedManualMovements;
        part revenueTrainOperator : RevenueTrainOperator {
            perform action a0 { doc /* is repeated back by the Revenue Train Operator @S117 */ }
            perform action a1 { doc /* reports train condition, cab indications, passenger issues, and any local hazard that cannot be confirmed from the control room display alone @S118 */ }
            perform action a2 { doc /* reports observed cab indications, train handling effects, and passenger service impacts using the operational reporting channel defined for degraded service @S166 */ }
            perform action a3 { doc /* using the operational reporting channel defined for degraded service @S166 */ }
            perform action a4 { doc /* repeat back the movement limit, maximum permitted speed, stopping point, and any instruction to remain clear of a platform interface @S191 */ }
            perform action a5 { doc /* remain clear of a platform interface @S191 */ }
            perform action a6 { doc /* sends the Test Train Clearance Memo @S197 */ }
            perform action a7 { doc /* completing the prescribed proving run under restricted manual control @S197 */ }
            perform action a8 { doc /* follows onboard indications and rulebook instructions @S244 */ }
        }
        part revocation : Revocation;
        part route : Route {
            exhibit state modes {
                state s0 { doc /* available @S082 */ }
                state s1 { doc /* locked @S107 */ }
            }
        }
        part routeStateIndications : RouteStateIndications {
            perform action a0 { doc /* allow the Operations Control Centre to distinguish an operational delay from a signalling equipment fault @S108 */ }
        }
        part safetyCase : SafetyCase {
            perform action a0 { doc /* assumes that loss of trust in communications can be as significant as loss of communications @S201 */ }
        }
        part safetyCriticalStateMachine : SafetyCriticalStateMachine {
            perform action a0 { doc /* separates initialization, protected manual operation, automatic train operation, fallback operation, and cutout conditions @S028 */ }
        }
        part safetyDataCommunicationNetwork : SafetyDataCommunicationNetwork {
            perform action a0 { doc /* carries safety-related messages between approved control components @S014 */ }
            perform action a1 { doc /* provides the protected communications transport used by train control messages that require integrity, authentication, and bounded latency @S040 */ }
            perform action a2 { doc /* sends the Clock Drift Sample Report at defined synchronization intervals @S041 */ }
            perform action a3 { doc /* carries vital movement authority traffic @S051 */ }
            perform action a4 { doc /* carries vital movement authority traffic @S051 */ }
            perform action a5 { doc /* carries vital messages between zone controllers, interlockings, and approved interfaces using deterministic routing and monitored latency limits @S058 */ }
            perform action a6 { doc /* carries safety-relevant station interface messages separately from nonvital passenger information messages @S147 */ }
            perform action a7 { doc /* provide communication performance records that are compared with controller logs during network-related investigations @S164 */ }
        }
        part safetyRelatedPart : SafetyRelatedPart {
            perform action a0 { doc /* records time-stamped events for state changes, command acceptance, rejected commands, communication loss, and local protective actions @S152 */ }
        }
        part securityEvents : SecurityEvents {
            perform action a0 { doc /* could affect train control availability or integrity @S023 */ }
            perform action a1 { doc /* change train movement authority @S204 */ }
        }
        part securityMonitoring : SecurityMonitoring {
            perform action a0 { doc /* correlate authentication failures, session resets, rejected messages, configuration changes, and abnormal timing patterns @S203 */ }
            perform action a1 { doc /* altering any safety command path @S203 */ }
        }
        part securityResponsibilities : SecurityResponsibilities;
        part securityWarnings : SecurityWarnings;
        part serviceRisk : ServiceRisk {
            perform action a0 { doc /* may require holding trains before constrained areas @S113 */ }
        }
        part serviceTimetableServer : ServiceTimetableServer {
            perform action a0 { doc /* supplies planned service data used by central regulation functions @S015 */ }
            perform action a1 { doc /* provides schedule context to Metro Operations Control System and related non-vital functions @S048 */ }
            perform action a2 { doc /* may receive selected service information @S076 */ }
            perform action a3 { doc /* provides planned service context used to compare predicted arrivals against scheduled platform usage @S139 */ }
            perform action a4 { doc /* provide trial schedules that exercise normal headways, recovery margins, terminal reversals, and junction conflicts without carrying passengers @S235 */ }
        }
        part session : Session {
            perform action a0 { doc /* reaches the minimum design margin @S055 */ }
        }
        part signalMaintenanceEngineer : SignalMaintenanceEngineer {
            perform action a0 { doc /* uses Maintenance Diagnostic Server @S022 */ }
            perform action a1 { doc /* review equipment health @S022 */ }
            perform action a2 { doc /* correlate alarms @S022 */ }
            perform action a3 { doc /* support restoration without bypassing required operational authority @S022 */ }
            perform action a4 { doc /* without bypassing required operational authority @S022 */ }
            perform action a5 { doc /* can review faults @S050 */ }
            perform action a6 { doc /* without connecting directly to vital processing functions @S050 */ }
            perform action a7 { doc /* investigate degraded coverage trends @S072 */ }
            perform action a8 { doc /* connecting to the vital channels @S072 */ }
            perform action a9 { doc /* verifies local track clearance evidence @S089 */ }
            perform action a10 { doc /* records the result @S089 */ }
            perform action a11 { doc /* authorising restoration of normal route setting after a detection anomaly @S089 */ }
            perform action a12 { doc /* determine whether an incident has an equipment cause or an operational cause @S119 */ }
            perform action a13 { doc /* advises the Line Traffic Controller on equipment recovery options @S120 */ }
            perform action a14 { doc /* later investigation @S148 */ }
            perform action a15 { doc /* confirms the engineering status @S168 */ }
            perform action a16 { doc /* verifies point condition, track vacancy, and local protection using approved field procedures @S188 */ }
            perform action a17 { doc /* using approved field procedures @S188 */ }
            perform action a18 { doc /* uses the Axle Counter Reset Request as the controlling authority for restoring a failed section after local occupancy checks are complete @S189 */ }
            perform action a19 { doc /* restoring a failed section @S189 */ }
            perform action a20 { doc /* request access needed for fault isolation @S214 */ }
            perform action a21 { doc /* verify that field defects raised during test running have been closed, deferred with approved controls, or assigned to a post-commissioning monitoring plan @S241 */ }
        }
        part softwareBuildIdentifiers : SoftwareBuildIdentifiers;
        part southDistrictZoneController : SouthDistrictZoneController {
            perform action a0 { doc /* calculate safe movement authority limits @S010 */ }
            perform action a1 { doc /* using train location reports, track occupancy data, and the state of controlled field equipment @S010 */ }
            perform action a2 { doc /* supervises the southern main line, the southern turnback, and the approach to West Junction Interlocking within its configured limits @S064 */ }
            perform action a3 { doc /* applies the same route protection principles for interfaces with West Junction Interlocking, including checks on flank protection and conflicting movement locking @S080 */ }
            perform action a4 { doc /* applies the same operating principles for the southern section @S106 */ }
            perform action a5 { doc /* preserving separation margins and route locking conditions @S106 */ }
            perform action a6 { doc /* maintains comparable diagnostic coverage @S159 */ }
            perform action a7 { doc /* inhibit automatic route setting within any block whose occupancy state is under manual confirmation @S184 */ }
            perform action a8 { doc /* do not enter service with degraded trust @S209 */ }
        }
        part spokenInstructions : SpokenInstructions {
            perform action a0 { doc /* match automated indications @S141 */ }
        }
        part stagedMigrationFromLegacySignalling : StagedMigrationFromLegacySignalling {
            perform action a0 { doc /* divide the railway into controlled areas @S230 */ }
        }
        part stationEquipment : StationEquipment {
            perform action a0 { doc /* affects departures, passenger information, and dispatcher awareness @S127 */ }
        }
        part stationStatusIndications : StationStatusIndications {
            perform action a0 { doc /* distinguish normal service, held train, door interlock fault, radio degraded, emergency stop active, and evacuation support conditions @S134 */ }
        }
        part supervisingWaysideSystems : SupervisingWaysideSystems;
        part temporaryOperatingConstraint : TemporaryOperatingConstraint {
            exhibit state modes {
                state s0 { doc /* active @S110 */ }
            }
        }
        part testTrain : TestTrain;
        part testTrainPhase : TestTrainPhase {
            perform action a0 { doc /* use non-passenger movements @S225 */ }
            perform action a1 { doc /* prove train localization, movement authority processing, braking response, radio continuity, and operator displays under controlled operating conditions @S225 */ }
        }
        part timeSynchronizedEventRecords : TimeSynchronizedEventRecords;
        part train : Train {
            perform action a0 { doc /* is approaching the affected detection section @S088 */ }
            perform action a1 { doc /* approaching @S094 */ }
            perform action a2 { doc /* arriving @S128 */ }
            perform action a3 { doc /* dwelling @S128 */ }
            perform action a4 { doc /* departing safely @S128 */ }
            exhibit state modes {
                state s0 { doc /* correctly berthed at a platform @S046 */ }
                state s1 { doc /* energized @S025 */ }
            }
        }
        part trainAuthority : TrainAuthority;
        part trainControlEnvironment : TrainControlEnvironment;
        part trainControlMessages : TrainControlMessages {
            perform action a0 { doc /* require integrity, authentication, and bounded latency @S040 */ }
        }
        part trainIntegrityIndications : TrainIntegrityIndications {
            exhibit state modes {
                state s0 { doc /* valid @S025 */ }
            }
        }
        part trainInterface : TrainInterface;
        part trainLocation : TrainLocation {
            exhibit state modes {
                state s0 { doc /* uncertain @S180 */ }
            }
        }
        part trainRadioModem : TrainRadioModem {
            perform action a0 { doc /* connects each train to the Wayside Radio Access Network @S013 */ }
            perform action a1 { doc /* provides the onboard data radio function @S038 */ }
            perform action a2 { doc /* maintains CBTC sessions over Wayside Radio Access Network coverage areas @S038 */ }
            perform action a3 { doc /* can maintain a stable session during normal operation @S053 */ }
            perform action a4 { doc /* maintains the active bearer used by the Atlas Onboard Controller @S055 */ }
            perform action a5 { doc /* reports radio quality changes @S055 */ }
            perform action a6 { doc /* supports continuous operational messaging @S113 */ }
            perform action a7 { doc /* uses the Encryption Certificate Renewal Pack @S146 */ }
            perform action a8 { doc /* accepting renewed secure sessions for passenger-facing and station-interface data paths @S146 */ }
            perform action a9 { doc /* records bearer loss, reconnection timing, signal quality indicators, and message retry counts needed to distinguish radio coverage issues from equipment faults @S163 */ }
            perform action a10 { doc /* report loss of safe data connectivity to the Atlas Onboard Controller @S181 */ }
            perform action a11 { doc /* not mask intermittent communication failures from the cab display @S181 */ }
            perform action a12 { doc /* do not enter service with degraded trust @S209 */ }
            exhibit state modes {
                state s0 { doc /* normal operation @S053 */ }
            }
        }
        part trainRadioModemMessages : TrainRadioModemMessages {
            perform action a0 { doc /* carrying route status @S096 */ }
        }
        part trainborneComponents : TrainborneComponents;
        part trainborneEquipment : TrainborneEquipment;
        part trainborneInterfaceToPropulsionAndBrakingEquipment : TrainborneInterfaceToPropulsionAndBrakingEquipment {
            perform action a0 { doc /* converts safety commands into vehicle-compatible requests @S034 */ }
            perform action a1 { doc /* preserving electrical isolation from non-vital circuits @S034 */ }
        }
        part trialSchedules : TrialSchedules {
            perform action a0 { doc /* exercise normal headways, recovery margins, terminal reversals, and junction conflicts without carrying passengers @S235 */ }
        }
        part verifiedDiagnosticIndication : VerifiedDiagnosticIndication {
            perform action a0 { doc /* supports a safe release @S185 */ }
        }
        part voiceDispatchConsole : VoiceDispatchConsole {
            perform action a0 { doc /* provides the fallback voice coordination path used by the Line Traffic Controller, Revenue Train Operator, and field staff when procedural confirmation is required @S016 */ }
            perform action a1 { doc /* provides a means for voice coordination during degraded service @S045 */ }
            perform action a2 { doc /* displays train calling identity, current platform association, and the latest operational hold reason @S141 */ }
            exhibit state modes {
                state s0 { doc /* available @S074 */ }
                state s1 { doc /* operationally separate from the vital CBTC data path @S045 */ }
            }
        }
        part voiceDispatchConsoleProcedures : VoiceDispatchConsoleProcedures;
        part waysideComponents : WaysideComponents;
        part waysideRadioAccessNetwork : WaysideRadioAccessNetwork {
            perform action a0 { doc /* provides the radio bearer for train-to-wayside control communications along the alignment @S013 */ }
            perform action a1 { doc /* provides overlapping cell coverage through stations, tunnels, crossovers, and depot approach tracks @S053 */ }
            perform action a2 { doc /* sends the Radio Handover Audit File @S073 */ }
            perform action a3 { doc /* shall maintain message delivery paths for station interface traffic during normal radio coverage transitions and degraded coverage recovery @S145 */ }
            perform action a4 { doc /* provide communication performance records that are compared with controller logs during network-related investigations @S164 */ }
        }
        part waysideSupervision : WaysideSupervision {
            perform action a0 { doc /* compares interlocking indications, train position reports, and radio session state @S069 */ }
            perform action a1 { doc /* detect inconsistent conditions @S069 */ }
            perform action a2 { doc /* detects a mismatch @S070 */ }
        }
        part westJunctionInterlocking : WestJunctionInterlocking {
            perform action a0 { doc /* maintain vital control of points and signals at the principal junction areas @S011 */ }
            perform action a1 { doc /* only accept commands that satisfy their configured safety rules @S011 */ }
            perform action a2 { doc /* report switch state, track occupancy, and route locking status to the responsible zone controller through vital interfaces @S068 */ }
            perform action a3 { doc /* retains final vital authority for point movement, point locking, route locking, and release of protected sections @S081 */ }
            perform action a4 { doc /* sends the Route Release Exception List @S090 */ }
            perform action a5 { doc /* provides route state indications @S108 */ }
            perform action a6 { doc /* report route command histories, point detection changes, and protective lock status @S160 */ }
            perform action a7 { doc /* support failure localisation @S160 */ }
            perform action a8 { doc /* reject a route command that conflicts with a manually protected train movement @S186 */ }
            perform action a9 { doc /* do not enter service with degraded trust @S209 */ }
            perform action a10 { doc /* remain under enhanced monitoring during migration @S229 */ }
        }
        flow f0 of ConsolidatedTrainPositionsItem from metroOperationsControlSystem to centralControlRoom { doc /* @S009 */ }
        flow f1 of ServiceRegulationFunctionsItem from metroOperationsControlSystem to centralControlRoom { doc /* @S009 */ }
        flow f2 of AlarmsItem from metroOperationsControlSystem to centralControlRoom { doc /* @S009 */ }
        flow f3 of OperatorCommandInterfacesItem from metroOperationsControlSystem to centralControlRoom { doc /* @S009 */ }
        flow f4 of DataItem from dualChannelOdometer to atlasOnboardController { doc /* @S012 */ }
        flow f5 of PlannedServiceDataItem from serviceTimetableServer to centralRegulationFunctions { doc /* @S015 */ }
        flow f6 of ApprovedServiceMessagesItem from passengerInformationGateway to customerInformationSystems { doc /* @S015 */ }
        flow f7 of FallbackVoiceCoordinationPathItem from voiceDispatchConsole to lineTrafficController { doc /* @S016 */ }
        flow f8 of FallbackVoiceCoordinationPathItem from voiceDispatchConsole to revenueTrainOperator { doc /* @S016 */ }
        flow f9 of FallbackVoiceCoordinationPathItem from voiceDispatchConsole to fieldStaff { doc /* @S016 */ }
        flow f10 of PlatformInterfaceIndicationsItem from platformScreenDoorController to trainControlEnvironment { doc /* @S017 */ }
        flow f11 of PlatformInterfaceIndicationsItem from trainControlEnvironment to platformScreenDoorController { doc /* @S017 */ }
        flow f12 of ExceptionsItem from automaticSupervision to lineTrafficController { doc /* @S018 */ }
        flow f13 of MovementAuthorityDataItem from northDistrictZoneController to atlasOnboardController { doc /* @S029 */ }
        flow f14 of MovementAuthorityDataItem from southDistrictZoneController to atlasOnboardController { doc /* @S029 */ }
        flow f15 of IndependentSpeedAndDistanceMeasurementsItem from dualChannelOdometer to atlasOnboardController { doc /* @S031 */ }
        flow f16 of LinkQualityItem from radioSubsystem to atlasOnboardController { doc /* @S039 */ }
        flow f17 of RegistrationStateItem from radioSubsystem to atlasOnboardController { doc /* @S039 */ }
        flow f18 of SessionContinuityInformationItem from radioSubsystem to atlasOnboardController { doc /* @S039 */ }
        flow f19 of SecurityMaterialItem from cryptographicKeyManagementAppliance to onboardCommunications { doc /* @S042 */ }
        flow f20 of MovementAuthorityLimitsItem from operatorInterface to revenueTrainOperator { doc /* @S043 */ }
        flow f21 of PermittedSpeedItem from operatorInterface to revenueTrainOperator { doc /* @S043 */ }
        flow f22 of TrainLocationConfidenceItem from operatorInterface to revenueTrainOperator { doc /* @S043 */ }
        flow f23 of RadioConditionItem from operatorInterface to revenueTrainOperator { doc /* @S043 */ }
        flow f24 of RequiredOperatorActionsItem from operatorInterface to revenueTrainOperator { doc /* @S043 */ }
        flow f25 of AcknowledgementsItem from revenueTrainOperator to atlasOnboardController { doc /* @S044 */ }
        flow f26 of DoorEnableAndClosedAndLockedIndicationsItem from platformScreenDoorController to trainInterface { doc /* @S046 */ }
        flow f27 of DoorEnableAndClosedAndLockedIndicationsItem from trainInterface to platformScreenDoorController { doc /* @S046 */ }
        flow f28 of NonVitalTrainPositionItem from metroOperationsControlSystem to passengerInformationGateway { doc /* @S047 */ }
        flow f29 of ScheduleContextItem from serviceTimetableServer to metroOperationsControlSystem { doc /* @S048 */ }
        flow f30 of ScheduleContextItem from serviceTimetableServer to relatedNonVitalFunctions { doc /* @S048 */ }
        flow f31 of NonVitalHealthIndicationsItem from trainborneEquipment to maintenanceDiagnosticServer { doc /* @S050 */ }
        flow f32 of VitalMovementAuthorityTrafficItem from safetyDataCommunicationNetwork to atlasOnboardController { doc /* @S051 */ }
        flow f33 of ActiveBearerItem from trainRadioModem to atlasOnboardController { doc /* @S055 */ }
        flow f34 of RadioQualityChangesItem from trainRadioModem to atlasOnboardController { doc /* @S055 */ }
        flow f35 of TrainPositionItem from dualChannelOdometer to atlasOnboardController { doc /* @S066 */ }
        flow f36 of SwitchStateItem from eastJunctionInterlocking to northDistrictZoneController { doc /* @S068 */ }
        flow f37 of TrackOccupancyItem from eastJunctionInterlocking to northDistrictZoneController { doc /* @S068 */ }
        flow f38 of RouteLockingStatusItem from eastJunctionInterlocking to northDistrictZoneController { doc /* @S068 */ }
        flow f39 of SwitchStateItem from westJunctionInterlocking to southDistrictZoneController { doc /* @S068 */ }
        flow f40 of TrackOccupancyItem from westJunctionInterlocking to southDistrictZoneController { doc /* @S068 */ }
        flow f41 of RouteLockingStatusItem from westJunctionInterlocking to southDistrictZoneController { doc /* @S068 */ }
        flow f42 of ZoneStatusItem from metroOperationsControlSystem to lineTrafficController { doc /* @S071 */ }
        flow f43 of RadioCoverageAlarmsItem from metroOperationsControlSystem to lineTrafficController { doc /* @S071 */ }
        flow f44 of TrainSupervisionStatesItem from metroOperationsControlSystem to lineTrafficController { doc /* @S071 */ }
        flow f45 of PermittedInterfaceIndicationsItem from platformScreenDoorController to supervisingWaysideSystems { doc /* @S075 */ }
        flow f46 of PermittedInterfaceIndicationsItem from supervisingWaysideSystems to platformScreenDoorController { doc /* @S075 */ }
        flow f47 of RoutesItem from northDistrictZoneController to eastJunctionInterlocking { doc /* @S079 */ }
        flow f48 of DoorClosedAndLockedIndicationsItem from platformScreenDoorController to supervisingWaysideSystems { doc /* @S093 */ }
        flow f49 of CrewLoginTokenBundleItem from metroOperationsControlSystem to atlasOnboardController { doc /* @S095 */ }
        flow f50 of CommandedRouteItem from metroOperationsControlSystem to controlStaff { doc /* @S098 */ }
        flow f51 of LockedRouteItem from metroOperationsControlSystem to controlStaff { doc /* @S098 */ }
        flow f52 of PointStateItem from metroOperationsControlSystem to controlStaff { doc /* @S098 */ }
        flow f53 of TrackOccupancyStateItem from metroOperationsControlSystem to controlStaff { doc /* @S098 */ }
        flow f54 of TrainPositionsItem from metroOperationsControlSystem to lineTrafficController { doc /* @S101 */ }
        flow f55 of RouteStatusItem from metroOperationsControlSystem to lineTrafficController { doc /* @S101 */ }
        flow f56 of ConflictItem from northDistrictZoneController to lineTrafficController { doc /* @S105 */ }
        flow f57 of UnavailableRouteConditionItem from northDistrictZoneController to lineTrafficController { doc /* @S105 */ }
        flow f58 of RouteStateIndicationsItem from westJunctionInterlocking to operationsControlCentre { doc /* @S108 */ }
        flow f59 of NonVitalTrendDataItem from maintenanceDiagnosticServer to signalMaintenanceEngineer { doc /* @S119 */ }
        flow f60 of EquipmentRecoveryOptionsItem from signalMaintenanceEngineer to lineTrafficController { doc /* @S120 */ }
        flow f61 of PlatformDoorStatusSnapshotItem from platformScreenDoorController to communicationsBasedTrainControlSystem { doc /* @S129 */ }
        flow f62 of UnsafeDoorInterfaceStateItem from associatedBerth to northDistrictZoneController { doc /* @S132 */ }
        flow f63 of EncryptionCertificateRenewalPackItem from cryptographicKeyManagementAppliance to trainRadioModem { doc /* @S146 */ }
        flow f64 of EventStreamsItem from fixedEquipment to maintenanceDiagnosticServer { doc /* @S153 */ }
        flow f65 of EventStreamsItem from onboardEquipment to maintenanceDiagnosticServer { doc /* @S153 */ }
        flow f66 of BrakeCurveChecksumLogItem from atlasOnboardController to maintenanceDiagnosticServer { doc /* @S154 */ }
        flow f67 of RouteReleaseExceptionListItem from westJunctionInterlocking to lineTrafficController { doc /* @S157 */ }
        flow f68 of SelectedFaultSummariesItem from metroOperationsControlSystem to lineTrafficController { doc /* @S165 */ }
        flow f69 of LossOfSafeDataConnectivityItem from trainRadioModem to atlasOnboardController { doc /* @S181 */ }
        flow f70 of AxleCounterResetRequestItem from eastJunctionInterlocking to signalMaintenanceEngineer { doc /* @S189 */ }
        flow f71 of RecordedHandbackItem from maintenanceControl to operationsControl { doc /* @S199 */ }
        flow f72 of SecurityEventsItem from safetyDataCommunicationNetwork to cyberSecurityOfficer { doc /* @S202 */ }
        flow f73 of SecurityEventsItem from waysideRadioAccessNetwork to cyberSecurityOfficer { doc /* @S202 */ }
        flow f74 of SecurityEventsItem from metroOperationsControlSystem to cyberSecurityOfficer { doc /* @S202 */ }
        flow f75 of RadioHandoverAuditFileItem from trainRadioModem to cyberSecurityOfficer { doc /* @S206 */ }
        flow f76 of OperationalCertificatesItem from cryptographicKeyManagementAppliance to trainborneComponents { doc /* @S207 */ }
        flow f77 of OperationalCertificatesItem from cryptographicKeyManagementAppliance to waysideComponents { doc /* @S207 */ }
        flow f78 of OperationalCertificatesItem from cryptographicKeyManagementAppliance to controlCenterComponents { doc /* @S207 */ }
        flow f79 of OperationalCertificatesItem from cryptographicKeyManagementAppliance to maintenanceComponents { doc /* @S207 */ }
        flow f80 of TestTrainClearanceMemoItem from revenueTrainOperator to metroOperationsControlSystem { doc /* @S216 */ }
        flow f81 of PlatformDoorStatusSnapshotItem from platformScreenDoorController to metroOperationsControlSystem { doc /* @S233 */ }
    }
    requirement def R0 { doc /* procedural confirmation is required @S016 */ subject s : ProceduralConfirmation; }
    requirement def R1 { doc /* a train authority must be reissued by the receiving zone @S065 */ subject s : TrainAuthority; }
    requirement def R2 { doc /* its state is not allowed to override movement authority logic @S075 */ subject s : PlatformScreenDoorController; }
    requirement def R3 { doc /* direct verbal instruction is required @S117 */ subject s : DirectVerbalInstruction; }
    requirement def R4 { doc /* The Passenger Information Gateway shall not publish a revised destination or skip-stop message until the underlying train identity and route have been confirmed by the CBTC system. @S137 */ subject s : PassengerInformationGateway; }
    requirement def R5 { doc /* Kestrel shall report train door enable side, berth identity, and departure readiness to support platform interface checks during dwell and dispatch. @S144 */ subject s : AtlasOnboardController; }
    requirement def R6 { doc /* Saffron shall maintain message delivery paths for station interface traffic during normal radio coverage transitions and degraded coverage recovery. @S145 */ subject s : WaysideRadioAccessNetwork; }
    requirement def R7 { doc /* During degraded operation, the CBTC system favours restrictive platform states and requires explicit controller action before restoring automatic departure support at the affected station. @S150 */ subject s : GreenvaleMetroCommunicationsBasedTrainControlSystem; }
    requirement def R8 { doc /* The Metro Operations Control System shall present the affected limits, the selected fallback mode, and any pending operator actions without obscuring safety alarms. @S177 */ subject s : MetroOperationsControlSystem; }
    requirement def R9 { doc /* The Dual Channel Odometer shall cause the train location to be treated as uncertain when its channels disagree beyond the permitted tolerance. @S180 */ subject s : DualChannelOdometer; }
    requirement def R10 { doc /* The Train Radio Modem shall report loss of safe data connectivity to the Atlas Onboard Controller and shall not mask intermittent communication failures from the cab display. @S181 */ subject s : TrainRadioModem; }
    requirement def R11 { doc /* Orchid shall inhibit automatic route setting within any block whose occupancy state is under manual confirmation. @S184 */ subject s : SouthDistrictZoneController; }
    requirement def R12 { doc /* The East Junction Interlocking shall hold commanded points locked until field confirmation or a verified diagnostic indication supports a safe release. @S185 */ subject s : EastJunctionInterlocking; }
    requirement def R13 { doc /* The West Junction Interlocking shall reject a route command that conflicts with a manually protected train movement. @S186 */ subject s : WestJunctionInterlocking; }
    requirement def R14 { doc /* Restricted manual movements shall be authorized through the Voice Dispatch Console unless the contingency communications procedure has been formally invoked. @S190 */ subject s : RestrictedManualMovements; }
    requirement def R15 { doc /* The Revenue Train Operator shall repeat back the movement limit, maximum permitted speed, stopping point, and any instruction to remain clear of a platform interface. @S191 */ subject s : RevenueTrainOperator; }
    requirement def R16 { doc /* Reset authorizations require concurrence between the Line Traffic Controller and the Signal Maintenance Engineer when the reset can change route availability or occupancy status. @S193 */ subject s : ResetAuthorizations; }
    requirement def R17 { doc /* Quarry shall mark each degraded-mode diagnostic session with the incident identifier before any component restart is attempted. @S194 */ subject s : MaintenanceDiagnosticServer; }
    requirement def R18 { doc /* The Cyber Security Officer shall review any degraded condition that involves authentication failure, unexpected lockout, or abnormal network access behavior. @S195 */ subject s : CyberSecurityOfficer; }
    requirement def R19 { doc /* The Cryptographic Key Management Appliance shall not be bypassed to accelerate service recovery unless the approved emergency security procedure is active. @S196 */ subject s : CryptographicKeyManagementAppliance; }
    requirement def R20 { doc /* The Passenger Information Gateway shall issue disruption messages that are consistent with the operating limits accepted by the Line Traffic Controller. @S198 */ subject s : PassengerInformationGateway; }
    requirement def R21 { doc /* Cybersecurity controls for the Greenvale Metro Communications-Based Train Control System shall be treated as operating prerequisites for safe automatic train movement after any maintenance handback. @S200 */ subject s : CybersecurityControls; }
    requirement def R22 { doc /* The operating response shall reflect that assumption. @S201 */ subject s : OperatingResponse; }
    requirement def R23 { doc /* The Cyber Security Officer shall maintain continuous monitoring of security events from the Safety Data Communication Network, the Wayside Radio Access Network, and the Metro Operations Control System. @S202 */ subject s : CyberSecurityOfficer; }
    requirement def R24 { doc /* Security monitoring shall correlate authentication failures, session resets, rejected messages, configuration changes, and abnormal timing patterns without altering any safety command path. @S203 */ subject s : SecurityMonitoring; }
    requirement def R25 { doc /* Alerts affecting train control availability shall be classified using operational impact, affected territory, and whether the event could change train movement authority. @S204 */ subject s : AlertsAffectingTrainControlAvailability; }
    requirement def R26 { doc /* The Line Traffic Controller shall be notified when a cybersecurity event requires a restriction on automatic operation or a change in communications mode. @S205 */ subject s : LineTrafficController; }
    requirement def R27 { doc /* The Cryptographic Key Management Appliance shall be the controlled source for operational certificates used by trainborne, wayside, control center, and maintenance components. @S207 */ subject s : CryptographicKeyManagementAppliance; }
    requirement def R28 { doc /* Certificate issuance shall require approved asset identity, recorded software baseline, assigned operating domain, and confirmation that the requesting component is authorized for service. @S208 */ subject s : CertificateIssuance; }
    requirement def R29 { doc /* Certificate renewal shall be planned before expiry so that the Atlas Onboard Controller, Train Radio Modem, North District Zone Controller, South District Zone Controller, and West Junction Interlocking do not enter service with degraded trust. @S209 */ subject s : CertificateRenewal; }
    requirement def R30 { doc /* Falcon shall reject any control message with an invalid signature, an expired certificate, or a sequence value outside the accepted window. @S210 */ subject s : EastJunctionInterlocking; }
    requirement def R31 { doc /* Revocation shall be available for a compromised device, a retired device, or a device whose maintenance history can no longer be reconciled with approved configuration records. @S211 */ subject s : Revocation; }
    requirement def R32 { doc /* The Maintenance Diagnostic Server shall not be used to bypass certificate checks or to create alternate trust paths into safety-related communications. @S212 */ subject s : MaintenanceDiagnosticServer; }
    requirement def R33 { doc /* Administrative access to the Cryptographic Key Management Appliance shall require named accounts, multifactor authentication, separation of duties, and recorded approval for privileged changes. @S213 */ subject s : AdministrativeAccessToTheCryptographicKeyManagementAppliance; }
    requirement def R34 { doc /* the Cyber Security Officer shall approve security-sensitive permissions before they are enabled @S214 */ subject s : CyberSecurityOfficer; }
    requirement def R35 { doc /* The Revenue Train Operator shall not be assigned cybersecurity administration duties during passenger service @S215 */ subject s : RevenueTrainOperator; }
    requirement def R36 { doc /* security warnings presented in the cab shall remain part of normal operating awareness @S215 */ subject s : SecurityWarnings; }
    requirement def R37 { doc /* Audit evidence shall include time-synchronized event records, access approvals, certificate actions, configuration changes, alarm acknowledgements, and operator instructions related to communications security. @S217 */ subject s : AuditEvidence; }
    requirement def R38 { doc /* Audit records shall be protected from local alteration by the component that generates them and shall be retained for the period defined by Greenvale Metro governance. @S218 */ subject s : AuditRecords; }
    requirement def R39 { doc /* The Service Timetable Server and Passenger Information Gateway shall be monitored for compromise because incorrect operational context can influence control room decisions even when safety commands remain valid. @S219 */ subject s : ServiceTimetableServer; }
    requirement def R40 { doc /* The Service Timetable Server and Passenger Information Gateway shall be monitored for compromise because incorrect operational context can influence control room decisions even when safety commands remain valid. @S219 */ subject s : PassengerInformationGateway; }
    requirement def R41 { doc /* The Voice Dispatch Console shall be included in security incident procedures when a cyber event changes the normal method for issuing operational instructions. @S220 */ subject s : VoiceDispatchConsole; }
    requirement def R42 { doc /* The Platform Screen Door Controller shall accept only authenticated interfaces approved for passenger service coordination and maintenance testing. @S221 */ subject s : PlatformScreenDoorController; }
    requirement def R43 { doc /* The Dual Channel Odometer and Atlas Onboard Controller shall report security-relevant diagnostic conditions in a manner that supports investigation without exposing cryptographic material. @S222 */ subject s : DualChannelOdometer; }
    requirement def R44 { doc /* The Dual Channel Odometer and Atlas Onboard Controller shall report security-relevant diagnostic conditions in a manner that supports investigation without exposing cryptographic material. @S222 */ subject s : AtlasOnboardController; }
    requirement def R45 { doc /* Security responsibilities shall be reviewed after major timetable changes, radio coverage modifications, control center upgrades, or any incident that questions the integrity of safety-related communications. @S223 */ subject s : SecurityResponsibilities; }
    requirement def R46 { doc /* Commissioning shall begin only after the installed equipment baseline for the Atlas Onboard Controller, Dual Channel Odometer, Train Radio Modem, and wayside control equipment has been configuration checked against the approved release record. @S224 */ subject s : Commissioning; }
    requirement def R47 { doc /* The test-train phase shall use non-passenger movements to prove train localization, movement authority processing, braking response, radio continuity, and operator displays under controlled operating conditions. @S225 */ subject s : TestTrainPhase; }
    requirement def R48 { doc /* Each test train shall be crewed by a Revenue Train Operator qualified for commissioning duties and supported by a Line Traffic Controller with authority to stop the trial when observed conditions depart from the approved script. @S226 */ subject s : TestTrain; }
    requirement def R49 { doc /* Initial movements shall be conducted at restricted commissioning speeds and shall progress to representative service speeds only after the Atlas Onboard Controller and North District Zone Controller demonstrate stable supervision. @S227 */ subject s : InitialMovements; }
    requirement def R50 { doc /* The South District Zone Controller shall be commissioned under the same test regime so that boundary behavior is verified before whole-line operation is attempted. @S228 */ subject s : SouthDistrictZoneController; }
    requirement def R51 { doc /* East Junction Interlocking and West Junction Interlocking shall remain under enhanced monitoring during migration because route setting, point detection, and authority release behavior are critical to mixed-mode operation. @S229 */ subject s : EastJunctionInterlocking; }
    requirement def R52 { doc /* East Junction Interlocking and West Junction Interlocking shall remain under enhanced monitoring during migration because route setting, point detection, and authority release behavior are critical to mixed-mode operation. @S229 */ subject s : WestJunctionInterlocking; }
    requirement def R53 { doc /* The staged migration from legacy signalling shall divide the railway into controlled areas that can be commissioned, operated, and, if necessary, returned to legacy control without affecting uncommissioned areas. @S230 */ subject s : StagedMigrationFromLegacySignalling; }
    requirement def R54 { doc /* Cutover planning shall define the exact control boundaries, permissible train movements, staffing levels, and rollback conditions for each migration stage. @S231 */ subject s : CutoverPlanning; }
    requirement def R55 { doc /* Before any cutover stage, the Safety Data Communication Network and Wayside Radio Access Network shall be verified for coverage, latency, redundancy, and alarm presentation at the control center. @S232 */ subject s : SafetyDataCommunicationNetwork; }
    requirement def R56 { doc /* Before any cutover stage, the Safety Data Communication Network and Wayside Radio Access Network shall be verified for coverage, latency, redundancy, and alarm presentation at the control center. @S232 */ subject s : WaysideRadioAccessNetwork; }
    requirement def R57 { doc /* The Platform Screen Door Controller shall be included in end-to-end tests that confirm safe coordination between platform equipment, train stopping position, and supervised door enablement. @S234 */ subject s : PlatformScreenDoorController; }
    requirement def R58 { doc /* The Service Timetable Server shall provide trial schedules that exercise normal headways, recovery margins, terminal reversals, and junction conflicts without carrying passengers. @S235 */ subject s : ServiceTimetableServer; }
    requirement def R59 { doc /* The Passenger Information Gateway shall be observed during operational rehearsal to confirm that public-facing messages remain consistent with the planned commissioning condition. @S236 */ subject s : PassengerInformationGateway; }
    requirement def R60 { doc /* Voice Dispatch Console procedures shall be rehearsed for test-train dispatch, abnormal stop instructions, evacuation coordination, and return to depot instructions. @S237 */ subject s : VoiceDispatchConsoleProcedures; }
    requirement def R61 { doc /* The Maintenance Diagnostic Server shall collect commissioning diagnostics so that intermittent radio, odometry, controller, and interlocking events can be reviewed before acceptance. @S238 */ subject s : MaintenanceDiagnosticServer; }
    requirement def R62 { doc /* The Cryptographic Key Management Appliance shall be confirmed as available, synchronized with the approved security baseline, and capable of supporting commissioning operations without manual workarounds. @S239 */ subject s : CryptographicKeyManagementAppliance; }
    requirement def R63 { doc /* Readiness reviews shall be held at the completion of each stage and shall include representatives from operations, signalling maintenance, rolling stock, communications, safety assurance, and cyber security. @S240 */ subject s : ReadinessReviews; }
    requirement def R64 { doc /* A Signal Maintenance Engineer shall verify that field defects raised during test running have been closed, deferred with approved controls, or assigned to a post-commissioning monitoring plan. @S241 */ subject s : SignalMaintenanceEngineer; }
    requirement def R65 { doc /* A Cyber Security Officer shall confirm that access controls, event monitoring, operator accounts, and security incident escalation paths are effective before revenue operation is recommended. @S242 */ subject s : CyberSecurityOfficer; }
    requirement def R66 { doc /* Operational rehearsal shall use realistic degraded scenarios including radio coverage loss, failed train initialization, controller switchover, interlocking unavailability, and control center workstation failure. @S243 */ subject s : OperationalRehearsal; }
    requirement def R67 { doc /* The rehearsal shall demonstrate that the Line Traffic Controller can maintain safe service regulation while the Revenue Train Operator follows onboard indications and rulebook instructions. @S244 */ subject s : OperationalRehearsal; }
    requirement def R68 { doc /* Acceptance for revenue service shall require completion of planned test cases, closure of safety-critical defects, successful rollback demonstration, and approval of the operations readiness record. @S245 */ subject s : AcceptanceForRevenueService; }
    requirement def R69 { doc /* No open defect shall be accepted for revenue service unless its operational restriction, maintenance response, and passenger impact have been assessed and approved by the readiness review authority. @S246 */ subject s : OpenDefect; }
    requirement def R70 { doc /* Final entry into revenue service shall occur only after management confirms that training, documentation, staffing, spare equipment, monitoring arrangements, and emergency procedures are in place for sustained operation. @S247 */ subject s : FinalEntryIntoRevenueService; }
}
