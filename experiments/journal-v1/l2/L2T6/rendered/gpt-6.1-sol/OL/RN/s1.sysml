package L2Model {
    item def ACalibrationWitnessTagItem { doc /* @S176 */ }
    item def AManualRescanReceiptItem { doc /* @S159 */ }
    item def AlarmConditionsItem { doc /* @S229 */ }
    item def BagItem { doc /* @S049,S054,S076,S093,S145,S196,S206,S207,S216 */ }
    item def BagImageItem { doc /* @S156 */ }
    item def BagMatchQueryItem { doc /* @S219 */ }
    item def CarouselReleaseSlipItem { doc /* @S148 */ }
    item def CheckedBaggageItem { doc /* @S006,S014,S020 */ }
    item def ChuteOccupancyNoteItem { doc /* @S184 */ }
    item def ConditionItem { doc /* @S243 */ }
    item def ContinuousViewOfBaggageThroughputEquipmentAvailabilityQueueGrowthScreeningStatusAndReconciliationExceptionsItem { doc /* @S227 */ }
    item def CountDifferencesItem { doc /* @S235 */ }
    item def EquipmentStateChangesItem { doc /* @S229 */ }
    item def ExceptionDetailsItem { doc /* @S156 */ }
    item def FlightCutoffAdvisoryItem { doc /* @S113 */ }
    item def LateTransferBagCardItem { doc /* @S143 */ }
    item def LoadingRecordItem { doc /* @S223 */ }
    item def MissingDuplicateOrDelayedEventSequencesItem { doc /* @S228 */ }
    item def OversizeExceptionTicketItem { doc /* @S141 */ }
    item def ProcessingTimeItem { doc /* @S234 */ }
    item def ReviewBacklogItem { doc /* @S234 */ }
    item def RouteItem { doc /* @S191 */ }
    item def TheBaggageOperationsSupervisorItem { doc /* @S091 */ }
    item def TheCustodySealLogItem { doc /* @S213 */ }
    item def TheRecoveryRouteCardItem { doc /* @S185 */ }
    item def TransferBagsItem { doc /* @S222 */ }
    item def UnmatchedRecordsItem { doc /* @S235 */ }
    item def UnresolvedImagesItem { doc /* @S234 */ }
    part def AccessPanels { doc /* @S183 */ }
    part def AffectedRecords { doc /* @S250 */ }
    part def AirlineRampCoordinator { doc /* @S023,S052,S128,S148,S149,S174,S219,S224 */ }
    part def AirlineSpecificDispatchTargets { doc /* @S106 */ }
    part def AirportEquipment { doc /* @S002 */ }
    part def Alarm { doc /* @S063 */ }
    part def Alarms { doc /* @S250 */ }
    part def AssignedMakeUpDestination { doc /* @S207 */ }
    part def AuthorizedPersonnel { doc /* @S151,S191 */ }
    part def AutomatedControls { doc /* @S026 */ }
    part def AutomatedImageReview { doc /* @S051,S058 */ }
    part def AutomatedProcessing { doc /* @S016 */ }
    part def AutomaticProcessing { doc /* @S155 */ }
    part def Availability { doc /* @S245 */ }
    part def Bag { doc /* @S033,S036,S038,S046,S056,S060,S063,S071,S079,S088,S094,S095,S096,S110,S115,S116,S130,S139,S142,S152,S165,S172,S178,S201,S203,S209,S225,S226 */ }
    part def BagIdentity { doc /* @S062,S088 */ }
    part def BagImage { doc /* @S060,S158,S160 */ }
    part def BagReconciliationStation { doc /* @S019,S070,S100,S101,S143,S164,S194,S218,S219,S235 */ }
    part def BagRecord { doc /* @S032,S042 */ }
    part def BagTagPrinter { doc /* @S030,S074,S151,S176 */ }
    part def BaggageControlSystem { doc /* @S007,S012,S032,S040,S053,S064,S079,S081,S092,S107,S109,S113,S114,S121,S135,S162,S172,S191,S204,S228 */ }
    part def BaggageOperationsSupervisor { doc /* @S024,S072,S090,S091,S104,S111,S129,S132,S154,S171,S180,S184,S198,S215,S241,S249 */ }
    part def BagsProcessedPerOperatingInterval { doc /* @S245 */ }
    part def Carousel7MakeUpUnit { doc /* @S021,S076,S098,S126,S147,S148,S196,S216,S239 */ }
    part def ChangesToLoadingReadiness { doc /* @S128 */ }
    part def CheckedBaggage { doc /* @S015 */ }
    part def Chute { doc /* @S184 */ }
    part def ClearDisposition { doc /* @S062 */ }
    part def ConcourseZoneController { doc /* @S009,S013,S043,S082,S123,S134,S175,S185,S229 */ }
    part def Condition { doc /* @S197,S243 */ }
    part def CongestionAwareness { doc /* @S089 */ }
    part def ConnectionWindows { doc /* @S106 */ }
    part def ControlFunctions { doc /* @S002 */ }
    part def CountDifferences { doc /* @S235 */ }
    part def CountOrIdentityDifference { doc /* @S225 */ }
    part def CutoffValues { doc /* @S112 */ }
    part def DegradedMode { doc /* @S247 */ }
    part def Destination { doc /* @S093 */ }
    part def DestinationLane { doc /* @S085 */ }
    part def DischargeArea { doc /* @S196 */ }
    part def Disposition { doc /* @S224 */ }
    part def EastMakeUpConveyor { doc /* @S020,S125,S145,S195,S220,S240 */ }
    part def Equipment { doc /* @S176,S181,S247 */ }
    part def EquipmentFaults { doc /* @S214 */ }
    part def EquipmentRestrictions { doc /* @S153 */ }
    part def ExplosivesResponseTeam { doc /* @S018,S067,S095,S120,S170,S186,S211,S213,S244 */ }
    part def Fault { doc /* @S250 */ }
    part def Feed { doc /* @S188 */ }
    part def Flight { doc /* @S032,S132 */ }
    part def FlightAssignment { doc /* @S177,S200 */ }
    part def FlightDataGateway { doc /* @S011,S041,S105,S113,S133,S163,S190,S217 */ }
    part def FlightSchedules { doc /* @S106 */ }
    part def FlightSideConstraint { doc /* @S174 */ }
    part def FlightTiming { doc /* @S092 */ }
    part def Guards { doc /* @S183,S195 */ }
    part def IdentityAndFlightChecks { doc /* @S172 */ }
    part def IdentityCheck { doc /* @S161 */ }
    part def ImageData { doc /* @S168 */ }
    part def ImageOrIdentityException { doc /* @S155 */ }
    part def ImageResolutionDesk { doc /* @S016,S094,S118,S141,S156,S159,S209,S234 */ }
    part def Images { doc /* @S209 */ }
    part def InductionTrayConveyor { doc /* @S006,S044,S049,S054,S076,S083,S093,S124,S137,S192,S196,S206 */ }
    part def InspectionPosition { doc /* @S065 */ }
    part def InspectionStaff { doc /* @S069 */ }
    part def InterfaceErrors { doc /* @S236 */ }
    part def Interlocks { doc /* @S045 */ }
    part def Label { doc /* @S219,S222,S225,S226,S230,S231,S232,S233,S236,S237 */ }
    part def LoadingAreas { doc /* @S020 */ }
    part def LocalFault { doc /* @S240 */ }
    part def LocalStaff { doc /* @S026 */ }
    part def MaintenanceTechnician { doc /* @S103,S153,S176,S182,S185,S189,S193,S197,S214,S242,S243 */ }
    part def MakeUpAllocation { doc /* @S131 */ }
    part def MakeUpAreas { doc /* @S014 */ }
    part def MakeUpPosition { doc /* @S145 */ }
    part def ManualDisposition { doc /* @S166 */ }
    part def ManualRescan { doc /* @S061 */ }
    part def ManualResolution { doc /* @S155 */ }
    part def MaterialServiceDegradation { doc /* @S241 */ }
    part def Mismatch { doc /* @S165 */ }
    part def Movement { doc /* @S182 */ }
    part def NextHandlingStage { doc /* @S216 */ }
    part def NormalRouting { doc /* @S251 */ }
    part def NorthGateScanner { doc /* @S015,S046,S056,S087,S117,S139,S167,S168,S208 */ }
    part def OperationalChange { doc /* @S110 */ }
    part def OperationalConcept { doc /* @S001 */ }
    part def OperationalMonitoring { doc /* @S227 */ }
    part def Operations { doc /* @S248 */ }
    part def OperationsMonitoringFunction { doc /* @S229 */ }
    part def Operator { doc /* @S156,S157,S158,S160,S165,S177,S200 */ }
    part def OutboundLoadControlDesk { doc /* @S022,S127,S150,S173,S223 */ }
    part def OutstandingExceptions { doc /* @S252 */ }
    part def Payload { doc /* @S227,S228,S234,S235 */ }
    part def PhysicalHandling { doc /* @S019 */ }
    part def Pier4BagDropUnit { doc /* @S004,S029,S035,S136,S141 */ }
    part def PlannedLane { doc /* @S092 */ }
    part def PositiveThreatIndication { doc /* @S119 */ }
    part def PrimaryCrossbeltSorter { doc /* @S014,S049,S055,S084,S085,S122,S138,S166,S184,S207 */ }
    part def Procedures { doc /* @S247 */ }
    part def QueueAge { doc /* @S245 */ }
    part def ReceivingEquipment { doc /* @S042 */ }
    part def Recovery { doc /* @S199,S252 */ }
    part def ReleaseHolds { doc /* @S152 */ }
    part def ReportingIntervals { doc /* @S246 */ }
    part def RequiredControls { doc /* @S248 */ }
    part def RequiredFunctionalChecks { doc /* @S250 */ }
    part def ResponsibleOperationalAndTechnicalPersonnel { doc /* @S251 */ }
    part def Restart { doc /* @S202 */ }
    part def Review { doc /* @S178,S201 */ }
    part def Reviewer { doc /* @S059 */ }
    part def Route { doc /* @S103,S177,S200 */ }
    part def ScanMismatch { doc /* @S088 */ }
    part def Schedule { doc /* @S110 */ }
    part def ScheduleRevisions { doc /* @S111 */ }
    part def ScreeningAndSortingEquipment { doc /* @S006 */ }
    part def ScreeningCompletion { doc /* @S245 */ }
    part def ScreeningDisposition { doc /* @S121 */ }
    part def ScreeningEquipment { doc /* @S054,S057 */ }
    part def ScreeningProcess { doc /* @S206 */ }
    part def ScreeningRecord { doc /* @S062,S063 */ }
    part def ScreeningResult { doc /* @S210 */ }
    part def ScreeningStatus { doc /* @S092 */ }
    part def SecondaryInspectionChute { doc /* @S017,S093,S142,S169 */ }
    part def SecurityDutyManager { doc /* @S018,S152,S187,S213,S243 */ }
    part def SecurityResponse { doc /* @S187 */ }
    part def SelectedRoute { doc /* @S042 */ }
    part def Service { doc /* @S103,S250 */ }
    part def ServiceMeasures { doc /* @S245 */ }
    part def SouthGateScanner { doc /* @S015,S048,S056,S061,S087,S117,S140,S159,S208 */ }
    part def Staff { doc /* @S027,S028,S034,S036,S039,S051,S058,S071,S078,S091,S192,S198,S205 */ }
    part def StopCommand { doc /* @S181 */ }
    part def System { doc /* @S002,S060 */ }
    part def SystemBoundary { doc /* @S002,S003 */ }
    part def SystemRecords { doc /* @S019 */ }
    part def TagRead { doc /* @S168 */ }
    part def Target { doc /* @S222,S223 */ }
    part def Thresholds { doc /* @S246 */ }
    part def TransferBagFeeder { doc /* @S005,S037,S038,S077,S099,S143,S144,S222,S238 */ }
    part def UnmatchedRecords { doc /* @S235 */ }
    part def UnresolvedImage { doc /* @S063 */ }
    part def UnresolvedReconciliationDifferences { doc /* @S245 */ }
    part def UnverifiedEquipmentState { doc /* @S248 */ }
    part def UsableCapacity { doc /* @S098 */ }
    part def WestMakeUpConveyor { doc /* @S020,S125,S146,S221,S240 */ }
    part system {
        part accessPanels : AccessPanels {
            perform action a0 { doc /* remain in place during operation @S183 */ }
        }
        part affectedRecords : AffectedRecords {
            perform action a0 { doc /* be reconciled @S250 */ }
        }
        part airlineRampCoordinator : AirlineRampCoordinator {
            perform action a0 { doc /* coordinates acceptance of staged baggage for ramp operations @S023 */ }
            perform action a1 { doc /* sends a Carousel Release Slip @S052 */ }
            perform action a2 { doc /* reports changes to loading readiness that could alter the usable cutoff @S128 */ }
            perform action a3 { doc /* confirms staffing, equipment availability, and the planned loading sequence @S149 */ }
            perform action a4 { doc /* accepting a build for loading @S149 */ }
            perform action a5 { doc /* confirms any flight-side constraint that could prevent the reconciled bag from being accepted @S174 */ }
            perform action a6 { doc /* uses the Bag Match Query @S219 */ }
            perform action a7 { doc /* review unresolved bag-to-flight mismatches @S219 */ }
            perform action a8 { doc /* verifies that the bag identity is readable, the flight assignment is current, and the security disposition permits loading @S224 */ }
        }
        part airlineSpecificDispatchTargets : AirlineSpecificDispatchTargets;
        part airportEquipment : AirportEquipment {
            perform action a0 { doc /* convey checked baggage @S002 */ }
            perform action a1 { doc /* screen checked baggage @S002 */ }
            perform action a2 { doc /* route checked baggage @S002 */ }
            perform action a3 { doc /* reconcile checked baggage @S002 */ }
            perform action a4 { doc /* stage checked baggage @S002 */ }
        }
        part alarm : Alarm {
            perform action a0 { doc /* places the bag into an exception status for additional examination @S063 */ }
        }
        part alarms : Alarms {
            perform action a0 { doc /* clear @S250 */ }
        }
        part assignedMakeUpDestination : AssignedMakeUpDestination;
        part authorizedPersonnel : AuthorizedPersonnel {
            perform action a0 { doc /* have confirmed the required bag details @S151 */ }
        }
        part automatedControls : AutomatedControls {
            perform action a0 { doc /* cannot clear @S026 */ }
        }
        part automatedImageReview : AutomatedImageReview {
            perform action a0 { doc /* cannot resolve a bag image @S051 */ }
            perform action a1 { doc /* cannot resolve a bag image @S058 */ }
        }
        part automatedProcessing : AutomatedProcessing {
            perform action a0 { doc /* requires operator assessment @S016 */ }
        }
        part automaticProcessing : AutomaticProcessing {
            perform action a0 { doc /* establishing a reliable disposition @S155 */ }
        }
        part availability : Availability;
        part bag : Bag {
            perform action a0 { doc /* remain in a designated holding area @S036 */ }
            perform action a1 { doc /* enters from an inbound transfer stream @S038 */ }
            perform action a2 { doc /* enters the screening and sorting network @S046 */ }
            perform action a3 { doc /* passes through them @S056 */ }
            perform action a4 { doc /* remains under controlled routing @S060 */ }
            perform action a5 { doc /* entering an outbound make-up path prematurely @S060 */ }
            perform action a6 { doc /* enter sortation @S079 */ }
            perform action a7 { doc /* continuing on a route that depends on the unresolved identity @S088 */ }
            perform action a8 { doc /* returns to normal handling only after its identity, examination outcome, and routing authorization agree @S096 */ }
            perform action a9 { doc /* retains its assigned flight unless a subsequent schedule or operational change requires reassessment @S110 */ }
            perform action a10 { doc /* may proceed to flight-specific sort destinations when capacity is available @S115 */ }
            perform action a11 { doc /* awaiting screening @S116 */ }
            perform action a12 { doc /* missing the active flight cutoff @S130 */ }
            perform action a13 { doc /* proceed toward their assigned build @S139 */ }
            perform action a14 { doc /* requiring further examination @S142 */ }
            perform action a15 { doc /* can enter a departure build @S152 */ }
            perform action a16 { doc /* rejoin its previously assigned screening and sort path @S172 */ }
            perform action a17 { doc /* returned to the planned process @S178 */ }
            perform action a18 { doc /* returned to the planned process @S201 */ }
            perform action a19 { doc /* remains under controlled custody from screening release until an authorized loading handoff is confirmed @S203 */ }
            perform action a20 { doc /* can continue @S209 */ }
            perform action a21 { doc /* must agree with the reconciled records @S225 */ }
            exhibit state modes {
                state s0 { doc /* controlled custody @S203 */ }
                state s1 { doc /* exception status @S063 */ }
                state s2 { doc /* held for staff resolution @S033 */ }
                state s3 { doc /* image-related holds @S094 */ }
                state s4 { doc /* isolated @S071 */ }
                state s5 { doc /* normal handling @S096 */ }
                state s6 { doc /* normal sortation @S094 */ }
                state s7 { doc /* on hold @S165 */ }
                state s8 { doc /* ready for departure @S226 */ }
                state s9 { doc /* security holds @S095 */ }
                state s10 { doc /* under controlled routing @S060 */ }
            }
        }
        part bagIdentity : BagIdentity {
            perform action a0 { doc /* agree @S062 */ }
            exhibit state modes {
                state s0 { doc /* unresolved @S088 */ }
            }
        }
        part bagImage : BagImage {
            perform action a0 { doc /* is awaiting review @S060 */ }
            perform action a1 { doc /* support a decision @S158 */ }
            exhibit state modes {
                state s0 { doc /* awaiting review @S060 */ }
                state s1 { doc /* inconclusive @S160 */ }
            }
        }
        part bagReconciliationStation : BagReconciliationStation {
            perform action a0 { doc /* supports verification of bag identity and processing status when system records or physical handling require reconciliation @S019 */ }
            perform action a1 { doc /* verifies that the bag presented for examination matches the screening record before further handling @S070 */ }
            perform action a2 { doc /* compares bag identity with the active handling record @S100 */ }
            perform action a3 { doc /* flags unresolved discrepancies @S100 */ }
            perform action a4 { doc /* sends a Bag Match Query when bag identity cannot be reconciled with the active handling record @S101 */ }
            perform action a5 { doc /* uses the Late Transfer Bag Card to reconcile a transfer bag against its intended flight @S143 */ }
            perform action a6 { doc /* reconcile a transfer bag against its intended flight @S143 */ }
            perform action a7 { doc /* records whether the inspected bag matches the expected flight assignment @S164 */ }
            perform action a8 { doc /* supports verification @S194 */ }
            perform action a9 { doc /* compares scanned bag identities against the expected flight population @S218 */ }
            perform action a10 { doc /* flags missing or duplicate records for resolution @S218 */ }
            perform action a11 { doc /* reports unmatched records and count differences @S235 */ }
        }
        part bagRecord : BagRecord {
            exhibit state modes {
                state s0 { doc /* complete @S032 */ }
                state s1 { doc /* valid @S042 */ }
            }
        }
        part bagTagPrinter : BagTagPrinter {
            perform action a0 { doc /* produces a durable tag with a unique identifier for each accepted bag @S030 */ }
            perform action a1 { doc /* produces a Calibration Witness Tag @S074 */ }
            perform action a2 { doc /* produces replacement identification only when authorized personnel have confirmed the required bag details @S151 */ }
        }
        part baggageControlSystem : BaggageControlSystem {
            perform action a0 { doc /* coordinates bag status, routing decisions, and operational visibility across connected equipment @S007 */ }
            perform action a1 { doc /* uses current flight and operating data @S012 */ }
            perform action a2 { doc /* support routing decisions @S012 */ }
            perform action a3 { doc /* maintain alignment with scheduled departures @S012 */ }
            perform action a4 { doc /* checks that the flight is open for bag acceptance and that the bag record is complete @S032 */ }
            perform action a5 { doc /* compares transfer-bag data with the current routing information @S040 */ }
            perform action a6 { doc /* applies the approved screening profile to each bag @S053 */ }
            perform action a7 { doc /* using its tag data and the current operating configuration @S053 */ }
            perform action a8 { doc /* routes exception-status bags to the Secondary Inspection Chute through a path that avoids normal outbound flows @S064 */ }
            perform action a9 { doc /* loads the approved sort plan @S079 */ }
            perform action a10 { doc /* applies its effective time window @S079 */ }
            perform action a11 { doc /* checks the plan against current flight and handling records @S081 */ }
            perform action a12 { doc /* assigning a route @S081 */ }
            perform action a13 { doc /* selects an approved alternate route only if screening status and flight timing remain valid @S092 */ }
            perform action a14 { doc /* evaluates flight assignments against current schedule data @S107 */ }
            perform action a15 { doc /* accepting bag routing instructions @S107 */ }
            perform action a16 { doc /* applies cutoff profiles configured for each carrier, flight, and operating condition @S109 */ }
            perform action a17 { doc /* receives the Flight Cutoff Advisory @S113 */ }
            perform action a18 { doc /* compares remaining processing time with route-specific handling estimates @S114 */ }
            perform action a19 { doc /* preserves a recoverable bag-to-flight association rather than releasing the bag to make-up @S121 */ }
            perform action a20 { doc /* records each bag's screening disposition and release state against its flight assignment @S135 */ }
            perform action a21 { doc /* checks the recorded bag identity against the current routing data @S162 */ }
            perform action a22 { doc /* authorizes the bag to rejoin its previously assigned screening and sort path @S172 */ }
            perform action a23 { doc /* records equipment alarms @S191 */ }
            perform action a24 { doc /* presents the affected route for review by authorized personnel @S191 */ }
            perform action a25 { doc /* maintains the bag identity, assigned flight, screening disposition, and current handling status as the authoritative record @S204 */ }
            perform action a26 { doc /* records bag events @S228 */ }
            perform action a27 { doc /* reports missing, duplicate, or delayed event sequences for operational review @S228 */ }
        }
        part baggageOperationsSupervisor : BaggageOperationsSupervisor {
            perform action a0 { doc /* oversees routine flow @S024 */ }
            perform action a1 { doc /* responds to service interruptions @S024 */ }
            perform action a2 { doc /* coordinates operational recovery with the Security Duty Manager and Maintenance Technician @S024 */ }
            perform action a3 { doc /* coordinates decisions that affect flight readiness, staffing, or continued operation of a screening lane @S072 */ }
            perform action a4 { doc /* sets local congestion thresholds @S090 */ }
            perform action a5 { doc /* confirms the authorized response to sustained overload @S090 */ }
            perform action a6 { doc /* used for the Baggage Operations Supervisor in sortation coordination @S091 */ }
            perform action a7 { doc /* authorizes recovery to the approved sort plan after the cause of the abnormal path has been addressed @S104 */ }
            perform action a8 { doc /* reviews affected flights @S111 */ }
            perform action a9 { doc /* directs priority adjustments @S111 */ }
            perform action a10 { doc /* may defer lower-priority bags when a flight's remaining processing window is insufficient @S129 */ }
            perform action a11 { doc /* authorizes release to a make-up position only when the flight remains within its processing window @S132 */ }
            perform action a12 { doc /* coordinates changes to build priority with airline ground operations @S154 */ }
            perform action a13 { doc /* communicates any resulting delivery constraints @S154 */ }
            perform action a14 { doc /* approves the operational disposition @S171 */ }
            perform action a15 { doc /* may stop induction @S180 */ }
            perform action a16 { doc /* uses the occupancy note @S184 */ }
            perform action a17 { doc /* confirm that a chute can safely accept bags @S184 */ }
            perform action a18 { doc /* controls the operational hold @S198 */ }
            perform action a19 { doc /* communicates its scope @S198 */ }
            perform action a20 { doc /* confirms that affected staff understand the restriction @S198 */ }
            perform action a21 { doc /* confirms that outstanding holds and route exceptions have an assigned owner @S215 */ }
            perform action a22 { doc /* authorizing continuation of processing @S215 */ }
            perform action a23 { doc /* reviews the operating dashboard @S241 */ }
            perform action a24 { doc /* confirms that material service degradation has been assigned an owner and response priority @S241 */ }
            perform action a25 { doc /* coordinates escalation to maintenance, security, and airline operations according to the severity and operational impact of the condition @S249 */ }
        }
        part bagsProcessedPerOperatingInterval : BagsProcessedPerOperatingInterval;
        part carousel7MakeUpUnit : Carousel7MakeUpUnit {
            perform action a0 { doc /* supports staging of baggage for its assigned departure operation @S021 */ }
            perform action a1 { doc /* accepts only bags with a valid screening disposition and an authorized routing instruction @S076 */ }
            perform action a2 { doc /* operates within its assigned flight window @S098 */ }
            perform action a3 { doc /* reports when its usable capacity is constrained @S098 */ }
            perform action a4 { doc /* presents bags for outbound loading only after flight grouping and screening status are confirmed @S126 */ }
            perform action a5 { doc /* maintains bag order and position information for its active flight build @S147 */ }
            perform action a6 { doc /* receives the Carousel Release Slip @S148 */ }
            perform action a7 { doc /* receiving bags @S196 */ }
            perform action a8 { doc /* release a bag to the next handling stage @S216 */ }
            perform action a9 { doc /* is monitored for operating state, accumulation, and the time required to clear assigned work @S239 */ }
            perform action a10 { doc /* clear assigned work @S239 */ }
            exhibit state modes {
                state s0 { doc /* operating status is uncertain @S196 */ }
            }
        }
        part changesToLoadingReadiness : ChangesToLoadingReadiness {
            perform action a0 { doc /* could alter the usable cutoff @S128 */ }
        }
        part checkedBaggage : CheckedBaggage {
            perform action a0 { doc /* moving through the system @S015 */ }
        }
        part chute : Chute {
            perform action a0 { doc /* can safely accept bags @S184 */ }
        }
        part clearDisposition : ClearDisposition {
            perform action a0 { doc /* permits normal routing only when the bag identity and screening record agree @S062 */ }
        }
        part concourseZoneController : ConcourseZoneController {
            perform action a0 { doc /* coordinates local equipment and conveyance within its assigned operating area @S009 */ }
            perform action a1 { doc /* produces the Recovery Route Card @S013 */ }
            perform action a2 { doc /* grants an induction permissive only when local equipment status and operating restrictions allow movement @S043 */ }
            perform action a3 { doc /* coordinates local conveyor availability with the active sort plan @S082 */ }
            perform action a4 { doc /* coordinates induction demand with available conveyor capacity across the operating area @S123 */ }
            perform action a5 { doc /* assigns bags to active make-up lanes using current zone status @S134 */ }
            perform action a6 { doc /* using current zone status @S134 */ }
            perform action a7 { doc /* applies the authorized routing state without bypassing required screening controls @S175 */ }
            perform action a8 { doc /* without bypassing required screening controls @S175 */ }
            perform action a9 { doc /* reports equipment state changes and alarm conditions to the operations monitoring function @S229 */ }
        }
        part condition : Condition {
            perform action a0 { doc /* prevents safe restart @S197 */ }
            perform action a1 { doc /* could compromise screening coverage, security controls, or custody continuity @S243 */ }
        }
        part congestionAwareness : CongestionAwareness {
            perform action a0 { doc /* uses current lane availability, conveyor stops, and the observed rate of incoming bags @S089 */ }
        }
        part connectionWindows : ConnectionWindows;
        part controlFunctions : ControlFunctions {
            perform action a0 { doc /* convey checked baggage @S002 */ }
            perform action a1 { doc /* screen checked baggage @S002 */ }
            perform action a2 { doc /* route checked baggage @S002 */ }
            perform action a3 { doc /* reconcile checked baggage @S002 */ }
            perform action a4 { doc /* stage checked baggage @S002 */ }
        }
        part countDifferences : CountDifferences {
            perform action a0 { doc /* remain subject to resolution before acceptance @S235 */ }
        }
        part countOrIdentityDifference : CountOrIdentityDifference {
            perform action a0 { doc /* blocks acceptance @S225 */ }
        }
        part cutoffValues : CutoffValues {
            perform action a0 { doc /* account for screening, sortation, make-up, and transfer handling allowances rather than only aircraft departure @S112 */ }
        }
        part degradedMode : DegradedMode {
            perform action a0 { doc /* may be used only when the remaining equipment and procedures preserve required screening, traceability, custody, and reconciliation controls @S247 */ }
        }
        part destination : Destination {
            exhibit state modes {
                state s0 { doc /* unresolved @S093 */ }
            }
        }
        part destinationLane : DestinationLane {
            perform action a0 { doc /* approaches its configured limit @S085 */ }
        }
        part dischargeArea : DischargeArea {
            exhibit state modes {
                state s0 { doc /* obstructed @S196 */ }
            }
        }
        part disposition : Disposition {
            perform action a0 { doc /* permits loading @S224 */ }
        }
        part eastMakeUpConveyor : EastMakeUpConveyor {
            perform action a0 { doc /* convey routed baggage toward the relevant loading areas @S020 */ }
            perform action a1 { doc /* receive flight groups according to active allocation rules @S125 */ }
            perform action a2 { doc /* delivers assigned bags to the designated make-up position at a controlled rate @S145 */ }
            perform action a3 { doc /* runs @S195 */ }
            perform action a4 { doc /* moves reconciled bags toward the correct flight position without bypassing required identity checks @S220 */ }
            perform action a5 { doc /* bypassing required identity checks @S220 */ }
            perform action a6 { doc /* are assessed separately @S240 */ }
        }
        part equipment : Equipment {
            perform action a0 { doc /* returns to service @S176 */ }
            perform action a1 { doc /* preserve required screening, traceability, custody, and reconciliation controls @S247 */ }
            exhibit state modes {
                state s0 { doc /* defined safe state @S181 */ }
            }
        }
        part equipmentFaults : EquipmentFaults {
            perform action a0 { doc /* could affect bag identity, screening integrity, or controlled access @S214 */ }
        }
        part equipmentRestrictions : EquipmentRestrictions {
            perform action a0 { doc /* affect lane availability or safe bag delivery @S153 */ }
        }
        part explosivesResponseTeam : ExplosivesResponseTeam {
            perform action a0 { doc /* coordinate security response and disposition for escalated screening events @S018 */ }
            perform action a1 { doc /* responds to escalated alarms @S067 */ }
            perform action a2 { doc /* coordinates any required safety controls with airport security personnel @S067 */ }
            perform action a3 { doc /* manages security holds under the applicable response procedures @S095 */ }
            perform action a4 { doc /* produces the Custody Seal Log @S120 */ }
            perform action a5 { doc /* conducts any security examination assigned under applicable procedures @S170 */ }
            perform action a6 { doc /* secures the response area @S186 */ }
            perform action a7 { doc /* directs handling of any bag referred for explosives assessment @S186 */ }
            perform action a8 { doc /* assesses security events referred for specialist action @S211 */ }
            perform action a9 { doc /* communicates the resulting disposition through approved operational channels @S211 */ }
            perform action a10 { doc /* is escalated to when an unresolved security condition requires its response under airport procedures @S244 */ }
        }
        part fault : Fault {
            perform action a0 { doc /* be corrected @S250 */ }
        }
        part feed : Feed;
        part flight : Flight {
            perform action a0 { doc /* remains within its processing window @S132 */ }
            exhibit state modes {
                state s0 { doc /* open for bag acceptance @S032 */ }
            }
        }
        part flightAssignment : FlightAssignment {
            perform action a0 { doc /* has changed @S177 */ }
            perform action a1 { doc /* has changed @S200 */ }
        }
        part flightDataGateway : FlightDataGateway {
            perform action a0 { doc /* sends the Flight Cutoff Advisory @S011 */ }
            perform action a1 { doc /* supplies flight and routing records @S041 */ }
            perform action a2 { doc /* maintains scheduled flight identifiers, destinations, planned departure times, and revisions needed for baggage planning @S105 */ }
            perform action a3 { doc /* maintains the flight identity and departure timing used for make-up planning @S133 */ }
            perform action a4 { doc /* provides the flight data used to validate the bag's assigned destination and service date @S163 */ }
            perform action a5 { doc /* supplies current flight data @S190 */ }
            perform action a6 { doc /* provides the flight and destination data used to check that the bag remains assigned to an operating departure @S217 */ }
        }
        part flightSchedules : FlightSchedules;
        part flightSideConstraint : FlightSideConstraint {
            perform action a0 { doc /* could prevent the reconciled bag from being accepted @S174 */ }
        }
        part flightTiming : FlightTiming {
            exhibit state modes {
                state s0 { doc /* valid @S092 */ }
            }
        }
        part guards : Guards {
            perform action a0 { doc /* remain in place during operation @S183 */ }
            exhibit state modes {
                state s0 { doc /* closed @S195 */ }
            }
        }
        part identityAndFlightChecks : IdentityAndFlightChecks {
            perform action a0 { doc /* pass @S172 */ }
        }
        part identityCheck : IdentityCheck {
            perform action a0 { doc /* verifies that the physical tag is attached to the inspected bag and that its number agrees with the recorded bag identity @S161 */ }
        }
        part imageData : ImageData {
            perform action a0 { doc /* support an operator's identity check @S168 */ }
        }
        part imageOrIdentityException : ImageOrIdentityException {
            perform action a0 { doc /* prevents automatic processing from establishing a reliable disposition @S155 */ }
        }
        part imageResolutionDesk : ImageResolutionDesk {
            perform action a0 { doc /* supports review of screening images when automated processing requires operator assessment @S016 */ }
            perform action a1 { doc /* resolves image-related holds @S094 */ }
            perform action a2 { doc /* reviews unresolved images @S118 */ }
            perform action a3 { doc /* uses the exception ticket to confirm an authorized make-up position for an oversize bag @S141 */ }
            perform action a4 { doc /* confirm an authorized make-up position for an oversize bag @S141 */ }
            perform action a5 { doc /* presents the available bag image and exception details to the operator for review @S156 */ }
            perform action a6 { doc /* uses the rescan receipt to confirm that a second image was captured under the approved procedure @S159 */ }
            perform action a7 { doc /* confirm that a second image was captured under the approved procedure @S159 */ }
            perform action a8 { doc /* reviews images that require operator assessment @S209 */ }
            perform action a9 { doc /* records a disposition @S209 */ }
            perform action a10 { doc /* reports unresolved images, review backlog, and processing time against the locally approved service target @S234 */ }
        }
        part images : Images;
        part inductionTrayConveyor : InductionTrayConveyor {
            perform action a0 { doc /* presents bags in a controlled manner to the screening and sorting equipment @S006 */ }
            perform action a1 { doc /* accepts bags through controlled feed points @S044 */ }
            perform action a2 { doc /* maintains separation between successive bags @S044 */ }
            perform action a3 { doc /* presents bags to the screening equipment at a controlled spacing that supports reliable image capture @S054 */ }
            perform action a4 { doc /* presents bags at controlled spacing @S083 */ }
            perform action a5 { doc /* admits bags in priority order, subject to scan confirmation and safe spacing @S124 */ }
            perform action a6 { doc /* meters bags into the handling stream at a rate that avoids accumulation at the make-up interface @S137 */ }
            perform action a7 { doc /* stops unexpectedly @S192 */ }
            perform action a8 { doc /* carries only bags with readable identity data and a valid route assignment into the screening process @S206 */ }
        }
        part inspectionPosition : InspectionPosition {
            exhibit state modes {
                state s0 { doc /* blocked @S065 */ }
                state s1 { doc /* unavailable @S065 */ }
            }
        }
        part inspectionStaff : InspectionStaff {
            perform action a0 { doc /* maintain physical control of an alarmed bag @S069 */ }
            perform action a1 { doc /* do not return it to the sorter until an authorized disposition is recorded @S069 */ }
        }
        part interfaceErrors : InterfaceErrors {
            perform action a0 { doc /* affecting flight assignment data @S236 */ }
        }
        part interlocks : Interlocks {
            perform action a0 { doc /* stop feed movement @S045 */ }
        }
        part label : Label;
        part loadingAreas : LoadingAreas;
        part localFault : LocalFault {
            perform action a0 { doc /* does not obscure the condition of the other conveyor @S240 */ }
        }
        part localStaff : LocalStaff {
            perform action a0 { doc /* resolving conditions that automated controls cannot clear @S026 */ }
        }
        part maintenanceTechnician : MaintenanceTechnician {
            perform action a0 { doc /* isolates a failed conveyor section @S103 */ }
            perform action a1 { doc /* confirms that the route is safe @S103 */ }
            perform action a2 { doc /* reports equipment restrictions that affect lane availability or safe bag delivery @S153 */ }
            perform action a3 { doc /* uses the witness tag to verify that the applicable calibration status was witnessed before equipment returns to service @S176 */ }
            perform action a4 { doc /* verify that the applicable calibration status was witnessed before equipment returns to service @S176 */ }
            perform action a5 { doc /* entering a conveyor or sorter hazard zone @S182 */ }
            perform action a6 { doc /* isolates the relevant energy sources @S182 */ }
            perform action a7 { doc /* verifies that movement has stopped @S182 */ }
            perform action a8 { doc /* consults the Recovery Route Card @S185 */ }
            perform action a9 { doc /* returning equipment to service after a route change @S185 */ }
            perform action a10 { doc /* checks for jammed bags, damaged belts, sensor obstruction, and signs of mechanical wear @S189 */ }
            perform action a11 { doc /* clearing a fault @S189 */ }
            perform action a12 { doc /* removes a jam @S193 */ }
            perform action a13 { doc /* confirming isolation @S193 */ }
            perform action a14 { doc /* arranging safe access to the blockage @S193 */ }
            perform action a15 { doc /* performs corrective work @S197 */ }
            perform action a16 { doc /* reports any condition that prevents safe restart @S197 */ }
            perform action a17 { doc /* reports equipment faults that could affect bag identity, screening integrity, or controlled access @S214 */ }
            perform action a18 { doc /* investigates equipment faults that exceed the approved recovery interval @S242 */ }
            perform action a19 { doc /* records the corrective action taken @S242 */ }
        }
        part makeUpAllocation : MakeUpAllocation {
            perform action a0 { doc /* begins when the active flight assignment and available build positions are confirmed @S131 */ }
        }
        part makeUpAreas : MakeUpAreas;
        part makeUpPosition : MakeUpPosition;
        part manualDisposition : ManualDisposition {
            exhibit state modes {
                state s0 { doc /* unresolved @S166 */ }
            }
        }
        part manualRescan : ManualRescan;
        part manualResolution : ManualResolution {
            perform action a0 { doc /* begins when an image or identity exception prevents automatic processing from establishing a reliable disposition @S155 */ }
        }
        part materialServiceDegradation : MaterialServiceDegradation {
            perform action a0 { doc /* has been assigned an owner and response priority @S241 */ }
        }
        part mismatch : Mismatch {
            perform action a0 { doc /* places the bag on hold @S165 */ }
        }
        part movement : Movement {
            perform action a0 { doc /* has stopped @S182 */ }
        }
        part nextHandlingStage : NextHandlingStage;
        part normalRouting : NormalRouting {
            perform action a0 { doc /* resumes @S251 */ }
        }
        part northGateScanner : NorthGateScanner {
            perform action a0 { doc /* provide screening interfaces for baggage moving through the system @S015 */ }
            perform action a1 { doc /* reads the bag identifier @S046 */ }
            perform action a2 { doc /* acquire screening images @S056 */ }
            perform action a3 { doc /* return a disposition for each bag that passes through them @S056 */ }
            perform action a4 { doc /* verify bag identity at their respective route decision points @S087 */ }
            perform action a5 { doc /* record screening outcomes for inducted bags @S117 */ }
            perform action a6 { doc /* verifies readable bag identification @S139 */ }
            perform action a7 { doc /* captures a readable tag image @S167 */ }
            perform action a8 { doc /* records the tag read and image data needed to support an operator's identity check @S168 */ }
            perform action a9 { doc /* report healthy status @S208 */ }
        }
        part operationalChange : OperationalChange {
            perform action a0 { doc /* requires reassessment @S110 */ }
        }
        part operationalConcept : OperationalConcept {
            perform action a0 { doc /* covers checked baggage from acceptance at airport bag-drop or transfer induction through screening, sorting, make-up, and handoff for aircraft loading @S001 */ }
        }
        part operationalMonitoring : OperationalMonitoring {
            perform action a0 { doc /* provides a continuous view of baggage throughput, equipment availability, queue growth, screening status, and reconciliation exceptions @S227 */ }
        }
        part operations : Operations {
            perform action a0 { doc /* must suspend the affected activity when required controls cannot be maintained or when an unverified equipment state could misroute baggage @S248 */ }
        }
        part operationsMonitoringFunction : OperationsMonitoringFunction;
        part operator : Operator {
            perform action a0 { doc /* compares visible bag features with the recorded tag number and the handling data associated with the bag @S157 */ }
            perform action a1 { doc /* confirms that the image is legible enough to support a decision @S158 */ }
            perform action a2 { doc /* does not rely on an uncertain visual match @S158 */ }
            perform action a3 { doc /* requests a physical inspection through the established inspection process @S160 */ }
            perform action a4 { doc /* resolves the discrepancy @S165 */ }
            perform action a5 { doc /* escalates it @S165 */ }
            perform action a6 { doc /* obtains approval @S177 */ }
            perform action a7 { doc /* obtains approval @S200 */ }
        }
        part outboundLoadControlDesk : OutboundLoadControlDesk {
            perform action a0 { doc /* provides the operational interface for confirming baggage readiness at the aircraft-loading handoff @S022 */ }
            perform action a1 { doc /* uses planned dispatch time and load-close targets @S127 */ }
            perform action a2 { doc /* monitor whether assigned bags can be accepted @S127 */ }
            perform action a3 { doc /* reconciles the completed build against the permitted flight load before departure closeout @S150 */ }
            perform action a4 { doc /* confirms that the bag remains eligible for inclusion in the planned flight load @S173 */ }
            perform action a5 { doc /* confirms that the flight assignment, reconciled bag count, and operational status are consistent @S223 */ }
            perform action a6 { doc /* accepting the loading record @S223 */ }
        }
        part outstandingExceptions : OutstandingExceptions {
            perform action a0 { doc /* have been resolved @S252 */ }
            perform action a1 { doc /* formally assigned @S252 */ }
        }
        part payload : Payload;
        part physicalHandling : PhysicalHandling {
            perform action a0 { doc /* require reconciliation @S019 */ }
        }
        part pier4BagDropUnit : Pier4BagDropUnit {
            perform action a0 { doc /* captures bag identification @S004 */ }
            perform action a1 { doc /* accepts baggage for processing @S004 */ }
            perform action a2 { doc /* records the accepted bag @S029 */ }
            perform action a3 { doc /* initiates its processing @S029 */ }
            perform action a4 { doc /* sends an Oversize Exception Ticket @S035 */ }
            perform action a5 { doc /* stages accepted bags for onward processing without changing their flight association @S136 */ }
            perform action a6 { doc /* without changing their flight association @S136 */ }
        }
        part plannedLane : PlannedLane {
            exhibit state modes {
                state s0 { doc /* unavailable @S092 */ }
            }
        }
        part positiveThreatIndication : PositiveThreatIndication {
            perform action a0 { doc /* suspends ordinary routing until the authorized security disposition is entered @S119 */ }
        }
        part primaryCrossbeltSorter : PrimaryCrossbeltSorter {
            perform action a0 { doc /* routes cleared bags toward the applicable make-up areas @S014 */ }
            perform action a1 { doc /* receives inducted bags @S049 */ }
            perform action a2 { doc /* directs them according to the active routing data @S049 */ }
            perform action a3 { doc /* maintains bag identity @S055 */ }
            perform action a4 { doc /* routes each bag according to the screening disposition available at the time of sorting @S055 */ }
            perform action a5 { doc /* applies the assigned destination and screening status to each identified bag @S084 */ }
            perform action a6 { doc /* sends a Chute Occupancy Note @S085 */ }
            perform action a7 { doc /* routes eligible bags according to flight assignment and current cutoff priority @S122 */ }
            perform action a8 { doc /* separates bags according to their authorized destination and current operating status @S138 */ }
            perform action a9 { doc /* holds the affected bag from automatic sorting @S166 */ }
            perform action a10 { doc /* directs cleared bags to their assigned make-up destination @S207 */ }
            perform action a11 { doc /* diverts unresolved items from normal handling @S207 */ }
        }
        part procedures : Procedures {
            perform action a0 { doc /* preserve required screening, traceability, custody, and reconciliation controls @S247 */ }
        }
        part queueAge : QueueAge;
        part receivingEquipment : ReceivingEquipment {
            exhibit state modes {
                state s0 { doc /* ready @S042 */ }
            }
        }
        part recovery : Recovery {
            perform action a0 { doc /* begins with a controlled inspection of the affected equipment and confirmation that bags in the area have been accounted for @S199 */ }
            perform action a1 { doc /* is monitored at increased frequency until performance is stable and outstanding exceptions have been resolved or formally assigned @S252 */ }
        }
        part releaseHolds : ReleaseHolds {
            perform action a0 { doc /* require a security decision @S152 */ }
        }
        part reportingIntervals : ReportingIntervals {
            perform action a0 { doc /* are established in the approved operating plan @S246 */ }
            perform action a1 { doc /* reviewed against demand, flight schedules, and safety constraints @S246 */ }
        }
        part requiredControls : RequiredControls {
            perform action a0 { doc /* cannot be maintained @S248 */ }
        }
        part requiredFunctionalChecks : RequiredFunctionalChecks {
            perform action a0 { doc /* pass @S250 */ }
        }
        part responsibleOperationalAndTechnicalPersonnel : ResponsibleOperationalAndTechnicalPersonnel {
            perform action a0 { doc /* confirm that screening and custody controls are effective @S251 */ }
        }
        part restart : Restart;
        part review : Review {
            perform action a0 { doc /* can trace why the bag returned to the planned process @S178 */ }
            perform action a1 { doc /* can trace why the bag returned to the planned process @S201 */ }
        }
        part reviewer : Reviewer {
            perform action a0 { doc /* considers the full image, bag identification, and any system prompts @S059 */ }
            perform action a1 { doc /* assigning a disposition @S059 */ }
        }
        part route : Route {
            perform action a0 { doc /* has changed @S177 */ }
            perform action a1 { doc /* has changed @S200 */ }
            exhibit state modes {
                state s0 { doc /* safe @S103 */ }
            }
        }
        part scanMismatch : ScanMismatch {
            perform action a0 { doc /* prevents the bag from continuing on a route that depends on the unresolved identity @S088 */ }
        }
        part schedule : Schedule {
            perform action a0 { doc /* requires reassessment @S110 */ }
        }
        part scheduleRevisions : ScheduleRevisions {
            perform action a0 { doc /* move a departure earlier @S111 */ }
        }
        part screeningAndSortingEquipment : ScreeningAndSortingEquipment;
        part screeningCompletion : ScreeningCompletion;
        part screeningDisposition : ScreeningDisposition {
            exhibit state modes {
                state s0 { doc /* pending @S121 */ }
            }
        }
        part screeningEquipment : ScreeningEquipment {
            perform action a0 { doc /* records image quality and alarm status @S057 */ }
        }
        part screeningProcess : ScreeningProcess;
        part screeningRecord : ScreeningRecord {
            perform action a0 { doc /* agree @S062 */ }
            perform action a1 { doc /* places the bag into an exception status for additional examination @S063 */ }
        }
        part screeningResult : ScreeningResult {
            perform action a0 { doc /* places the bag in a controlled hold area @S210 */ }
        }
        part screeningStatus : ScreeningStatus {
            exhibit state modes {
                state s0 { doc /* valid @S092 */ }
            }
        }
        part secondaryInspectionChute : SecondaryInspectionChute {
            perform action a0 { doc /* provides a controlled path for bags selected for additional examination @S017 */ }
            perform action a1 { doc /* retains bags requiring further examination until the applicable disposition is recorded @S142 */ }
            perform action a2 { doc /* provides a controlled location for bags requiring physical examination @S169 */ }
        }
        part securityDutyManager : SecurityDutyManager {
            perform action a0 { doc /* coordinate security response and disposition for escalated screening events @S018 */ }
            perform action a1 { doc /* resolves release holds that require a security decision @S152 */ }
            perform action a2 { doc /* coordinates access control @S187 */ }
            perform action a3 { doc /* uses the seal log @S213 */ }
            perform action a4 { doc /* verify that recorded custody seals remain accounted for and that any discrepancy has been escalated @S213 */ }
            perform action a5 { doc /* assesses any condition that could compromise screening coverage, security controls, or custody continuity @S243 */ }
        }
        part securityResponse : SecurityResponse {
            perform action a0 { doc /* affects equipment or staff movement @S187 */ }
        }
        part selectedRoute : SelectedRoute {
            exhibit state modes {
                state s0 { doc /* available @S042 */ }
            }
        }
        part service : Service {
            perform action a0 { doc /* resumes @S103 */ }
        }
        part serviceMeasures : ServiceMeasures;
        part southGateScanner : SouthGateScanner {
            perform action a0 { doc /* provide screening interfaces for baggage moving through the system @S015 */ }
            perform action a1 { doc /* provides an independent read point for bags routed through its assigned entry path @S048 */ }
            perform action a2 { doc /* acquire screening images @S056 */ }
            perform action a3 { doc /* return a disposition for each bag that passes through them @S056 */ }
            perform action a4 { doc /* produces a Manual Rescan Receipt @S061 */ }
            perform action a5 { doc /* verify bag identity at their respective route decision points @S087 */ }
            perform action a6 { doc /* record screening outcomes for inducted bags @S117 */ }
            perform action a7 { doc /* provides the corresponding verification for bags processed in its coverage area @S140 */ }
            perform action a8 { doc /* report healthy status @S208 */ }
        }
        part staff : Staff {
            perform action a0 { doc /* confirm that the bag is eligible for carriage under the applicable airline rules @S027 */ }
            perform action a1 { doc /* verify the passenger and flight details @S028 */ }
            perform action a2 { doc /* accepting the bag into the checked-baggage process @S028 */ }
            perform action a3 { doc /* check bag dimensions and weight against the configured limits for standard conveyor handling @S034 */ }
            perform action a4 { doc /* confirm an approved handling route @S036 */ }
            perform action a5 { doc /* confirm that transfer-bag identifiers are legible and correspond to a valid onward flight record @S039 */ }
            perform action a6 { doc /* assess the available image @S051 */ }
            perform action a7 { doc /* record a disposition @S051 */ }
            perform action a8 { doc /* assess the available image @S058 */ }
            perform action a9 { doc /* record a disposition @S058 */ }
            perform action a10 { doc /* secure the area @S071 */ }
            perform action a11 { doc /* notify the Baggage Operations Supervisor @S071 */ }
            perform action a12 { doc /* return a bag to normal handling only after its identity, examination outcome, and routing authorization are consistent in the operating record @S078 */ }
            perform action a13 { doc /* prevent further bag entry @S192 */ }
            perform action a14 { doc /* keep the approach area clear @S192 */ }
            perform action a15 { doc /* understand the restriction @S198 */ }
            perform action a16 { doc /* keep bags in monitored areas @S205 */ }
            perform action a17 { doc /* prevent access by personnel who are not assigned to the active handling task @S205 */ }
        }
        part stopCommand : StopCommand {
            perform action a0 { doc /* places the affected equipment in a defined safe state @S181 */ }
            perform action a1 { doc /* disabling unrelated routes that remain safe to operate @S181 */ }
        }
        part systemPart : System {
            perform action a0 { doc /* prevents it from entering an outbound make-up path prematurely @S060 */ }
        }
        part systemBoundary : SystemBoundary {
            perform action a0 { doc /* includes the airport equipment and control functions that convey, screen, route, reconcile, and stage checked baggage @S002 */ }
            perform action a1 { doc /* excludes airline aircraft loading activities beyond the handoff at the outbound load control point @S003 */ }
        }
        part systemRecords : SystemRecords {
            perform action a0 { doc /* require reconciliation @S019 */ }
        }
        part tagRead : TagRead {
            perform action a0 { doc /* support an operator's identity check @S168 */ }
        }
        part target : Target;
        part thresholds : Thresholds {
            perform action a0 { doc /* are established in the approved operating plan @S246 */ }
            perform action a1 { doc /* reviewed against demand, flight schedules, and safety constraints @S246 */ }
        }
        part transferBagFeeder : TransferBagFeeder {
            perform action a0 { doc /* provides a separate induction interface for eligible transfer baggage @S005 */ }
            perform action a1 { doc /* identifies each inbound transfer bag @S037 */ }
            perform action a2 { doc /* records its arrival into the local handling process @S037 */ }
            perform action a3 { doc /* sends a Late Transfer Bag Card @S038 */ }
            perform action a4 { doc /* holds transfer bags from release until their screening status and intended onward handling are confirmed @S077 */ }
            perform action a5 { doc /* continues to hold transfer bags until screening status and intended onward handling are confirmed @S099 */ }
            perform action a6 { doc /* meters accepted transfer bags into the active handling sequence without bypassing required checks @S144 */ }
            perform action a7 { doc /* without bypassing required checks @S144 */ }
            perform action a8 { doc /* accepts transfer bags only when their identity and intended onward flight can be verified @S222 */ }
            perform action a9 { doc /* is monitored for feed rate, interruptions, and backlog against its scheduled demand @S238 */ }
        }
        part unmatchedRecords : UnmatchedRecords {
            perform action a0 { doc /* remain subject to resolution before acceptance @S235 */ }
        }
        part unresolvedImage : UnresolvedImage {
            perform action a0 { doc /* places the bag into an exception status for additional examination @S063 */ }
        }
        part unresolvedReconciliationDifferences : UnresolvedReconciliationDifferences;
        part unverifiedEquipmentState : UnverifiedEquipmentState {
            perform action a0 { doc /* could misroute baggage @S248 */ }
        }
        part usableCapacity : UsableCapacity {
            exhibit state modes {
                state s0 { doc /* constrained @S098 */ }
            }
        }
        part westMakeUpConveyor : WestMakeUpConveyor {
            perform action a0 { doc /* convey routed baggage toward the relevant loading areas @S020 */ }
            perform action a1 { doc /* receive flight groups according to active allocation rules @S125 */ }
            perform action a2 { doc /* provides the equivalent delivery function for positions in its operating area @S146 */ }
            perform action a3 { doc /* remains subject to the same controlled access and reconciliation rules as other make-up equipment @S221 */ }
            perform action a4 { doc /* are assessed separately @S240 */ }
        }
        flow f0 of CheckedBaggageItem from inductionTrayConveyor to screeningAndSortingEquipment { doc /* @S006 */ }
        flow f1 of CheckedBaggageItem from primaryCrossbeltSorter to makeUpAreas { doc /* @S014 */ }
        flow f2 of CheckedBaggageItem from eastMakeUpConveyor to loadingAreas { doc /* @S020 */ }
        flow f3 of CheckedBaggageItem from westMakeUpConveyor to loadingAreas { doc /* @S020 */ }
        flow f4 of BagItem from inductionTrayConveyor to primaryCrossbeltSorter { doc /* @S049 */ }
        flow f5 of BagItem from inductionTrayConveyor to screeningEquipment { doc /* @S054 */ }
        flow f6 of BagItem from inductionTrayConveyor to carousel7MakeUpUnit { doc /* @S076 */ }
        flow f7 of BagItem from inductionTrayConveyor to secondaryInspectionChute { doc /* @S093 */ }
        flow f8 of FlightCutoffAdvisoryItem from flightDataGateway to baggageControlSystem { doc /* @S113 */ }
        flow f9 of OversizeExceptionTicketItem from pier4BagDropUnit to imageResolutionDesk { doc /* @S141 */ }
        flow f10 of LateTransferBagCardItem from transferBagFeeder to bagReconciliationStation { doc /* @S143 */ }
        flow f11 of BagItem from eastMakeUpConveyor to makeUpPosition { doc /* @S145 */ }
        flow f12 of CarouselReleaseSlipItem from airlineRampCoordinator to carousel7MakeUpUnit { doc /* @S148 */ }
        flow f13 of BagImageItem from imageResolutionDesk to operator { doc /* @S156 */ }
        flow f14 of ExceptionDetailsItem from imageResolutionDesk to operator { doc /* @S156 */ }
        flow f15 of ChuteOccupancyNoteItem from primaryCrossbeltSorter to baggageOperationsSupervisor { doc /* @S184 */ }
        flow f16 of RouteItem from baggageControlSystem to authorizedPersonnel { doc /* @S191 */ }
        flow f18 of BagItem from inductionTrayConveyor to screeningProcess { doc /* @S206 */ }
        flow f19 of BagItem from primaryCrossbeltSorter to assignedMakeUpDestination { doc /* @S207 */ }
        flow f20 of BagItem from carousel7MakeUpUnit to nextHandlingStage { doc /* @S216 */ }
        flow f21 of BagMatchQueryItem from bagReconciliationStation to airlineRampCoordinator { doc /* @S219 */ }
        flow f22 of TransferBagsItem from target to transferBagFeeder { doc /* @S222 */ }
        flow f23 of LoadingRecordItem from target to outboundLoadControlDesk { doc /* @S223 */ }
        flow f24 of ContinuousViewOfBaggageThroughputEquipmentAvailabilityQueueGrowthScreeningStatusAndReconciliationExceptionsItem from operationalMonitoring to payload { doc /* @S227 */ }
        flow f25 of MissingDuplicateOrDelayedEventSequencesItem from baggageControlSystem to payload { doc /* @S228 */ }
        flow f26 of EquipmentStateChangesItem from concourseZoneController to operationsMonitoringFunction { doc /* @S229 */ }
        flow f27 of AlarmConditionsItem from concourseZoneController to operationsMonitoringFunction { doc /* @S229 */ }
        flow f28 of UnresolvedImagesItem from imageResolutionDesk to payload { doc /* @S234 */ }
        flow f29 of ReviewBacklogItem from imageResolutionDesk to payload { doc /* @S234 */ }
        flow f30 of ProcessingTimeItem from imageResolutionDesk to payload { doc /* @S234 */ }
        flow f31 of UnmatchedRecordsItem from bagReconciliationStation to payload { doc /* @S235 */ }
        flow f32 of CountDifferencesItem from bagReconciliationStation to payload { doc /* @S235 */ }
        flow f33 of ConditionItem from maintenanceTechnician to securityDutyManager { doc /* @S243 */ }
        flow f34 of TheBaggageOperationsSupervisorItem from staff to baggageOperationsSupervisor { doc /* joined @S071,S091 */ }
        flow f35 of AManualRescanReceiptItem from southGateScanner to imageResolutionDesk { doc /* joined @S061,S159 */ }
        flow f36 of ACalibrationWitnessTagItem from bagTagPrinter to maintenanceTechnician { doc /* joined @S074,S176 */ }
        flow f37 of TheRecoveryRouteCardItem from concourseZoneController to maintenanceTechnician { doc /* joined @S013,S185 */ }
        flow f38 of TheCustodySealLogItem from explosivesResponseTeam to securityDutyManager { doc /* joined @S120,S213 */ }
    }
    requirement def R0 { doc /* Before induction, the bag record must be valid @S042 */ subject s : BagRecord; }
    requirement def R1 { doc /* Before induction, the selected route must be available @S042 */ subject s : SelectedRoute; }
    requirement def R2 { doc /* Before induction, the receiving equipment must be ready @S042 */ subject s : ReceivingEquipment; }
    requirement def R3 { doc /* a manual rescan is required @S061 */ subject s : ManualRescan; }
    requirement def R4 { doc /* Guards and access panels remain in place during operation, and bypasses are permitted only under an approved maintenance procedure. @S183 */ subject s : Guards; }
    requirement def R5 { doc /* A scanner fault requires the affected feed to be held until the fault is assessed and the bag disposition is known. @S188 */ subject s : Feed; }
    requirement def R6 { doc /* Restart requires confirmation that personnel are clear, guards are restored, alarms are understood, and the intended route is available. @S202 */ subject s : Restart; }
    requirement def R7 { doc /* The North Gate Scanner and South Gate Scanner must report healthy status before their screening results are relied upon for release. @S208 */ subject s : NorthGateScanner; }
    requirement def R8 { doc /* The North Gate Scanner and South Gate Scanner must report healthy status before their screening results are relied upon for release. @S208 */ subject s : SouthGateScanner; }
    requirement def R9 { doc /* images that require operator assessment @S209 */ subject s : Images; }
    requirement def R10 { doc /* Orchard shall release a bag to the next handling stage only when the recorded screening disposition and assigned destination are valid. @S216 */ subject s : Carousel7MakeUpUnit; }
    requirement def R11 { doc /* The physical bags presented for loading must agree with the reconciled records, and every unexplained count or identity difference blocks acceptance. @S225 */ subject s : Bag; }
    requirement def R12 { doc /* The Explosives Response Team is escalated to when an unresolved security condition requires its response under airport procedures. @S244 */ subject s : ExplosivesResponseTeam; }
    requirement def R13 { doc /* A degraded mode may be used only when the remaining equipment and procedures preserve required screening, traceability, custody, and reconciliation controls. @S247 */ subject s : DegradedMode; }
    requirement def R14 { doc /* Operations must suspend the affected activity when required controls cannot be maintained or when an unverified equipment state could misroute baggage. @S248 */ subject s : Operations; }
    requirement def R15 { doc /* Return to service requires the fault to be corrected, required functional checks to pass, alarms to clear, and affected records to be reconciled. @S250 */ subject s : Service; }
}
