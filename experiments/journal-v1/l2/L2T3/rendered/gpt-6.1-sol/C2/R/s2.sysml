package L2Model {
    item def AircraftCautionAreasItem { doc /* @S146 */ }
    item def AircraftCoordinationDataItem { doc /* @S047 */ }
    item def ApprovedSuppressionObjectivesItem { doc /* @S146 */ }
    item def AssignedCommunicationsChannelItem { doc /* @S155 */ }
    item def AssignedIncidentContextItem { doc /* @S049 */ }
    item def AssignmentsItem { doc /* @S152 */ }
    item def AutomatedClassificationItem { doc /* @S106 */ }
    item def AviationStatusViewItem { doc /* @S081 */ }
    item def BatterySwapTicketItem { doc /* @S109 */ }
    item def CameraCleaningLogItem { doc /* @S163 */ }
    item def CameraViewsDetectionHistoryWeatherContextMapLayersAndStatusTransitionsItem { doc /* @S046 */ }
    item def ConfidenceValuesItem { doc /* @S039 */ }
    item def ConfirmedIncidentContextItem { doc /* @S072 */ }
    item def CrewAcknowledgementsItem { doc /* @S098 */ }
    item def CurrentAssignmentNotesItem { doc /* @S146 */ }
    item def CurrentDivisionAssignmentItem { doc /* @S155 */ }
    item def CurrentFirePerimeterIntelligenceItem { doc /* @S092 */ }
    item def DetectionsItem { doc /* @S202 */ }
    item def HazardsItem { doc /* @S152 */ }
    item def HumidityItem { doc /* @S113 */ }
    item def IncidentInformationItem { doc /* @S003 */ }
    item def LoadingStatusItem { doc /* @S047 */ }
    item def MapReferencesItem { doc /* @S049 */ }
    item def MissionNotesItem { doc /* @S047 */ }
    item def ObservationContextItem { doc /* @S053,S094 */ }
    item def OperationalStatusItem { doc /* @S003 */ }
    item def OriginalSpeakerIdentityItem { doc /* @S085 */ }
    item def PriorityAssignmentSummariesItem { doc /* @S171 */ }
    item def PublicSafetyInformationItem { doc /* @S210 */ }
    item def RallyLocationItem { doc /* @S155 */ }
    item def RecommendedActionsItem { doc /* @S003 */ }
    item def ReconnaissanceTaskStatusItem { doc /* @S168 */ }
    item def RetardantBatchSlipItem { doc /* @S141 */ }
    item def RidgeShadowMaskItem { doc /* @S162 */ }
    item def RouteGuidanceItem { doc /* @S155 */ }
    item def RunwayReleaseNoteItem { doc /* @S233 */ }
    item def SeparateBearingTrackItem { doc /* @S104 */ }
    item def StabilityFieldsItem { doc /* @S113 */ }
    item def StagingInformationItem { doc /* @S152 */ }
    item def SuppressionDropReceiptItem { doc /* @S234 */ }
    item def TaskStatusItem { doc /* @S035 */ }
    item def TemperatureItem { doc /* @S113 */ }
    item def ThermalSpotSnippetItem { doc /* @S106 */ }
    item def UpdatedIntelligenceItem { doc /* @S152 */ }
    item def UpdatesItem { doc /* @S049 */ }
    item def WeatherContextItem { doc /* @S046 */ }
    item def WeatherFieldsItem { doc /* @S117 */ }
    item def WindItem { doc /* @S113 */ }
    item def WindAndVisibilityContextItem { doc /* @S093 */ }
    item def WindShiftBulletinItem { doc /* @S136 */ }
    part def AbortBehavior { doc /* @S229 */ }
    part def AcceptanceCriteria { doc /* @S228 */ }
    part def AccessConstraints { doc /* @S161 */ }
    part def AccessRoads { doc /* @S002 */ }
    part def AccuracyOfIncidentStatusUpdates { doc /* @S218 */ }
    part def ActiveUser { doc /* @S222 */ }
    part def AdministrativePrivileges { doc /* @S188 */ }
    part def AdvisoryAnalyticsServices { doc /* @S025 */ }
    part def AffectedRadioRoute { doc /* @S086 */ }
    part def AfterActionReview { doc /* @S239 */ }
    part def AfterActionReviews { doc /* @S238 */ }
    part def AgencyPolicy { doc /* @S197 */ }
    part def AirAttackSupervisor { doc /* @S013,S047,S077,S079,S092,S094,S098,S123,S128,S136,S139,S153,S187,S206,S232 */ }
    part def Aircraft { doc /* @S008 */ }
    part def Airspace { doc /* @S107 */ }
    part def AirspaceRestrictedState { doc /* @S139 */ }
    part def AirspaceRestrictedStateWorkflow { doc /* @S236 */ }
    part def AlternateContactPaths { doc /* @S211 */ }
    part def AnalyticsServices { doc /* @S040 */ }
    part def AnnualRefresherTraining { doc /* @S214 */ }
    part def AppendOnlyAuditStore { doc /* @S189 */ }
    part def Aspect { doc /* @S116 */ }
    part def AssignmentAndStagingChanges { doc /* @S175 */ }
    part def AtmosphericGlare { doc /* @S057 */ }
    part def AuditRecords { doc /* @S190 */ }
    part def AuthorizedReviewer { doc /* @S067 */ }
    part def AuthorizedRole { doc /* @S021 */ }
    part def AuthorizedUsers { doc /* @S178 */ }
    part def AuthorizedWildfirePersonnel { doc /* @S003 */ }
    part def AutomatedConfidenceLevel { doc /* @S059 */ }
    part def AvailableObservations { doc /* @S012 */ }
    part def AviationPersonnel { doc /* @S064 */ }
    part def AviationRepresentatives { doc /* @S221 */ }
    part def AviationSupervisors { doc /* @S085,S093 */ }
    part def AviationSupportUnits { doc /* @S009 */ }
    part def BestKnownLocation { doc /* @S071 */ }
    part def BridgePath { doc /* @S086 */ }
    part def BroaderAnalyticsWorkflow { doc /* @S039 */ }
    part def CalderaIncidentCommandPortal { doc /* @S003,S046,S059,S069,S074,S076,S077,S086,S098,S119,S120,S127,S149,S154,S160,S177,S178,S185,S210,S227 */ }
    part def CalderaWildfireDetectionAndSuppressionSupportSystem { doc /* @S001,S019,S025,S099,S101,S139,S151,S152,S160,S167,S176,S198 */ }
    part def CallSigns { doc /* @S211 */ }
    part def CameraFamiliarization { doc /* @S203 */ }
    part def CellularService { doc /* @S029 */ }
    part def ChangesToSoftwareScreens { doc /* @S214 */ }
    part def ChangingConditions { doc /* @S017 */ }
    part def ChargingInterfaces { doc /* @S033 */ }
    part def CloudShadow { doc /* @S057 */ }
    part def CommandStaff { doc /* @S045,S046 */ }
    part def CommandVisibility { doc /* @S235 */ }
    part def CommandWorkflow { doc /* @S072 */ }
    part def CommonOperatingPicture { doc /* @S126 */ }
    part def CommunicationCompletionRate { doc /* @S218 */ }
    part def CommunicationsConditions { doc /* @S107 */ }
    part def CommunicationsPaths { doc /* @S025 */ }
    part def CommunicationsTraining { doc /* @S211 */ }
    part def Communities { doc /* @S002 */ }
    part def ConfidenceBasis { doc /* @S071 */ }
    part def ConfigurationChanges { doc /* @S245 */ }
    part def ConfiguredWeatherRules { doc /* @S043 */ }
    part def Confirmation { doc /* @S067 */ }
    part def ConfirmationReadbacks { doc /* @S211 */ }
    part def ConfirmedIgnitionState { doc /* @S071,S160 */ }
    part def ConfirmedIgnitionStateWorkflow { doc /* @S235 */ }
    part def ControlledFieldValidation { doc /* @S229 */ }
    part def CooperatingPublicSafetyPartners { doc /* @S009 */ }
    part def CorrectiveActions { doc /* @S241 */ }
    part def CountyEmergencyLiaison { doc /* @S010,S046,S089,S124,S150,S174,S187,S210,S234 */ }
    part def CountyEmergencyManagement { doc /* @S009 */ }
    part def CountyLiaisonProcedures { doc /* @S090 */ }
    part def CountyLiaisonRepresentatives { doc /* @S221 */ }
    part def CrewlineMobileTablet { doc /* @S016,S049,S146,S155,S159,S172,S231 */ }
    part def CrewlineMobileTabletClients { doc /* @S184 */ }
    part def CrewlineMobileTabletUsers { doc /* @S072 */ }
    part def Crews { doc /* @S008,S146,S158,S165,S171 */ }
    part def CurrentRecommendedCoordinationPosture { doc /* @S071 */ }
    part def DataLink { doc /* @S172 */ }
    part def DataStewardship { doc /* @S242 */ }
    part def DeletionWorkflows { doc /* @S198 */ }
    part def DeploymentGovernanceBoard { doc /* @S225,S226,S237,S246 */ }
    part def DeploymentGovernanceForTheCalderaWildfireDetectionAndSuppressionSupportSystem { doc /* @S224 */ }
    part def DesignatedRepresentativesForAviation { doc /* @S225 */ }
    part def DesignatedRepresentativesForCountyCoordinationFunctions { doc /* @S225 */ }
    part def DesignatedRepresentativesForDetection { doc /* @S225 */ }
    part def DesignatedRepresentativesForGroundCrew { doc /* @S225 */ }
    part def DetectionPerformance { doc /* @S244 */ }
    part def DetectionQuality { doc /* @S219 */ }
    part def DetectionSupport { doc /* @S020,S021 */ }
    part def DetectionWorkflow { doc /* @S051 */ }
    part def DismissedCases { doc /* @S075 */ }
    part def DocumentedCheck { doc /* @S213 */ }
    part def DocumentedRecoveryProcedures { doc /* @S199 */ }
    part def Drainages { doc /* @S002 */ }
    part def DronePilotOperator { doc /* @S015,S035,S036,S063,S079,S090,S109,S132,S170,S187,S205 */ }
    part def DroneTaskingService { doc /* @S005,S035,S062,S080,S108,S129,S168,S192,S229 */ }
    part def Dust { doc /* @S057 */ }
    part def DutyDetectionOfficer { doc /* @S011,S012,S046,S060,S061,S078,S086,S087,S106,S179,S202,S204 */ }
    part def EastRetardantLoadingPump { doc /* @S073,S141,S142,S194,S230 */ }
    part def EmergencyAccess { doc /* @S186 */ }
    part def EquipmentFault { doc /* @S199 */ }
    part def EscalationTiming { doc /* @S235 */ }
    part def EscapeRouteDegradation { doc /* @S165 */ }
    part def EvacuationZones { doc /* @S116 */ }
    part def Event { doc /* @S221 */ }
    part def Exception { doc /* @S173 */ }
    part def ExerciseControllers { doc /* @S217 */ }
    part def ExpiredPackage { doc /* @S159 */ }
    part def FalseAlarmReview { doc /* @S220 */ }
    part def FieldCleaningSupplies { doc /* @S199 */ }
    part def FieldComponent { doc /* @S191 */ }
    part def FieldConfigurations { doc /* @S200 */ }
    part def FieldCrewRepresentatives { doc /* @S221 */ }
    part def FieldObservations { doc /* @S161 */ }
    part def FieldObservers { doc /* @S064 */ }
    part def FieldResources { doc /* @S018 */ }
    part def FireBehaviorModel { doc /* @S117 */ }
    part def FireSpreadEstimates { doc /* @S161 */ }
    part def FixedRidgeSensors { doc /* @S025 */ }
    part def FlameGrowth { doc /* @S004 */ }
    part def FlightBattery { doc /* @S034 */ }
    part def Fuels { doc /* @S116 */ }
    part def GeospatialOverlays { doc /* @S116 */ }
    part def GroundCrewAssignments { doc /* @S157 */ }
    part def GroundCrews { doc /* @S152 */ }
    part def GroundTeams { doc /* @S168 */ }
    part def HardenedPowerDistribution { doc /* @S028 */ }
    part def Hazards { doc /* @S015,S165 */ }
    part def HelitackAssignments { doc /* @S167 */ }
    part def HelitackCrewLeader { doc /* @S015,S049,S097,S098,S147,S156,S173,S187,S208,S209 */ }
    part def HelitackCrews { doc /* @S152 */ }
    part def HighVolumeRawSensorData { doc /* @S197 */ }
    part def HorizonRidgeDroneDock { doc /* @S005,S033,S034,S051,S053,S130,S131,S229 */ }
    part def HorizonRidgeDroneDockStatus { doc /* @S169 */ }
    part def Ignition { doc /* @S017 */ }
    part def ImprovementPlan { doc /* @S247 */ }
    part def Incident { doc /* @S074,S076 */ }
    part def IncidentRecord { doc /* @S070 */ }
    part def IncidentStaff { doc /* @S005,S022 */ }
    part def Indication { doc /* @S060 */ }
    part def InformationSecurityRepresentation { doc /* @S225 */ }
    part def InitialQualification { doc /* @S213 */ }
    part def Inputs { doc /* @S126 */ }
    part def IntegrationChecks { doc /* @S230 */ }
    part def JurisdictionBoundaries { doc /* @S116 */ }
    part def KnownCommunicationsCoverage { doc /* @S116 */ }
    part def LaterOperators { doc /* @S069 */ }
    part def LessonsLearnedFromPriorIncidents { doc /* @S214 */ }
    part def LightningProtection { doc /* @S028 */ }
    part def LimitedAccess { doc /* @S165 */ }
    part def LiveExercises { doc /* @S216 */ }
    part def LocalEquipmentCabinets { doc /* @S028 */ }
    part def LocalFireAgencies { doc /* @S009 */ }
    part def LocalHealthMonitoring { doc /* @S033 */ }
    part def LocalObservations { doc /* @S212 */ }
    part def LocalSensorProcessing { doc /* @S030 */ }
    part def LocalWeatherCache { doc /* @S183 */ }
    part def LocalWindHumidityTemperatureAndStabilityContext { doc /* @S058 */ }
    part def LoggedInCrew { doc /* @S155 */ }
    part def MaintenanceActions { doc /* @S196 */ }
    part def MaintenanceController { doc /* @S034,S109 */ }
    part def MaintenanceRepresentation { doc /* @S225 */ }
    part def MaintenanceRepresentatives { doc /* @S221 */ }
    part def MaintenanceStaff { doc /* @S182 */ }
    part def MapProducts { doc /* @S123,S125 */ }
    part def MappingWorkflow { doc /* @S104 */ }
    part def MesoWestWeatherFusionNode { doc /* @S007,S042,S043,S046,S058,S093,S113,S114,S117,S136,S166,S183,S212,S228 */ }
    part def MessageBrevity { doc /* @S211 */ }
    part def NorthLookoutCameraMast { doc /* @S004,S026,S028,S030,S051,S053,S094,S103,S106,S182,S228 */ }
    part def Observation { doc /* @S051 */ }
    part def ObservationContext { doc /* @S094 */ }
    part def ObservationHistory { doc /* @S071 */ }
    part def Occlusion { doc /* @S062 */ }
    part def OperatingProcedures { doc /* @S012,S200 */ }
    part def OperationalArea { doc /* @S002 */ }
    part def OperationalData { doc /* @S243 */ }
    part def OperationalLeadership { doc /* @S225 */ }
    part def OperationalRecommendations { doc /* @S122 */ }
    part def OperationalRecord { doc /* @S065,S066 */ }
    part def OperationalRecords { doc /* @S197 */ }
    part def OperationalUsers { doc /* @S211,S236 */ }
    part def Operations { doc /* @S018 */ }
    part def OperationsLead { doc /* @S213 */ }
    part def OperationsRepresentatives { doc /* @S221 */ }
    part def OperatorAcknowledgement { doc /* @S235 */ }
    part def Operators { doc /* @S212 */ }
    part def Participant { doc /* @S201 */ }
    part def ParticipatingOrganizations { doc /* @S009 */ }
    part def PerformanceMeasures { doc /* @S218 */ }
    part def Personnel { doc /* @S016,S223 */ }
    part def PostIncidentReview { doc /* @S100 */ }
    part def PreIssuedSignedCredentials { doc /* @S186 */ }
    part def RadioBridging { doc /* @S085 */ }
    part def ReleaseCandidate { doc /* @S227 */ }
    part def RemoteRecreationAreas { doc /* @S002 */ }
    part def ReplacementNetworkEquipment { doc /* @S199 */ }
    part def RequestedIntelligence { doc /* @S168 */ }
    part def ReviewBoard { doc /* @S221 */ }
    part def ReviewFacilitators { doc /* @S240 */ }
    part def ReviewerIdentity { doc /* @S071 */ }
    part def RevisedThresholds { doc /* @S214 */ }
    part def Ridgelines { doc /* @S002 */ }
    part def Roads { doc /* @S116 */ }
    part def RuleChecks { doc /* @S121 */ }
    part def ScenarioWalkthroughs { doc /* @S213 */ }
    part def SeasonalHazardBriefings { doc /* @S214 */ }
    part def SeasonalReadiness { doc /* @S222 */ }
    part def SeasonalReadinessCampaign { doc /* @S247 */ }
    part def SecureNetworkTermination { doc /* @S033 */ }
    part def SecurityRelevantEvents { doc /* @S189 */ }
    part def SentinelFirelineAnalyticsEngine { doc /* @S006,S038,S053,S092,S111,S134,S161,S162,S164,S180,S202,S204,S227 */ }
    part def ServiceAccess { doc /* @S028 */ }
    part def SharedFireBehaviorAssessment { doc /* @S102 */ }
    part def SimplifiedView { doc /* @S124 */ }
    part def Slope { doc /* @S116 */ }
    part def SmallIgnition { doc /* @S002 */ }
    part def SmokeClassifierModule { doc /* @S006,S039,S056,S105,S106,S162,S163,S181,S204,S227 */ }
    part def SmokeColumnHeight { doc /* @S062 */ }
    part def SmokeColumns { doc /* @S004,S094 */ }
    part def SmokeReport { doc /* @S017 */ }
    part def SourceChannel { doc /* @S085 */ }
    part def SouthLookoutCameraMast { doc /* @S004,S027,S028,S051,S053,S094,S095,S104,S163,S182,S228 */ }
    part def SparePower { doc /* @S199 */ }
    part def SpreadModel { doc /* @S113 */ }
    part def StaffedOperationsPortal { doc /* @S025 */ }
    part def StagedReleaseProcess { doc /* @S224 */ }
    part def StateWildlandFireResources { doc /* @S009 */ }
    part def StatusReporting { doc /* @S229 */ }
    part def SteepSlopeExposure { doc /* @S165 */ }
    part def Structures { doc /* @S116 */ }
    part def SupervisedConsolePractice { doc /* @S213 */ }
    part def SupervisorDecision { doc /* @S143 */ }
    part def Supervisors { doc /* @S118 */ }
    part def SuppressionPlanning { doc /* @S127 */ }
    part def SuppressionSupport { doc /* @S022 */ }
    part def SuspectedIgnition { doc /* @S011,S068 */ }
    part def TabletopExercises { doc /* @S215 */ }
    part def TalonAirTankerDispatchConsole { doc /* @S047,S080,S081,S137,S138,S140,S148,S230,S233,S234 */ }
    part def Tanker { doc /* @S082 */ }
    part def TankerBaseManager { doc /* @S014,S047,S081,S082,S141,S144,S187,S207,S233 */ }
    part def TaskExecution { doc /* @S229 */ }
    part def Terrain { doc /* @S005,S027,S062 */ }
    part def TerrainShadowConditions { doc /* @S056 */ }
    part def ThermalCues { doc /* @S055 */ }
    part def TimeFromAutomatedDetectionToHumanReview { doc /* @S218 */ }
    part def TimeFromReviewToCommandNotification { doc /* @S218 */ }
    part def TimeIndexedWeatherUpdate { doc /* @S114 */ }
    part def TimeToResourceAssignment { doc /* @S218 */ }
    part def TrainingForTheCalderaWildfireDetectionAndSuppressionSupportSystem { doc /* @S200 */ }
    part def TrainingProgram { doc /* @S201 */ }
    part def UnstableSnags { doc /* @S165 */ }
    part def UpdatedContactRosters { doc /* @S214 */ }
    part def Users { doc /* @S125 */ }
    part def UtilityConflicts { doc /* @S165 */ }
    part def UtilityCorridors { doc /* @S002 */ }
    part def VHFRadioGatewayRepeater { doc /* @S008,S044,S064,S084,S145,S171,S193,S231 */ }
    part def VHFRadioGatewayRepeaterFailureModes { doc /* @S211 */ }
    part def VehicleExhaust { doc /* @S057 */ }
    part def VisibilityChanges { doc /* @S004 */ }
    part def WaiverToAcceptanceCriteria { doc /* @S237 */ }
    part def WaterSources { doc /* @S116 */ }
    part def Weather { doc /* @S107 */ }
    part def WeatherDerivedExposureFlags { doc /* @S166 */ }
    part def WeatherRatedEnclosures { doc /* @S033 */ }
    part def WeatherTraining { doc /* @S212 */ }
    part def WestRetardantLoadingPump { doc /* @S142,S195,S230 */ }
    part def WildfireThreatEnvironment { doc /* @S001 */ }
    part system {
        part abortBehavior : AbortBehavior {
            perform action a0 { doc /* remain stable under expected seasonal conditions @S229 */ }
        }
        part acceptanceCriteria : AcceptanceCriteria {
            perform action a0 { doc /* require the North Lookout Camera Mast, South Lookout Camera Mast, and MesoWest Weather Fusion Node to meet agreed availability, timing, and data-quality thresholds during the readiness window @S228 */ }
        }
        part accessConstraints : AccessConstraints {
            perform action a0 { doc /* change @S161 */ }
        }
        part accessRoads : AccessRoads;
        part accuracyOfIncidentStatusUpdates : AccuracyOfIncidentStatusUpdates;
        part activeUser : ActiveUser {
            perform action a0 { doc /* demonstrate current proficiency @S222 */ }
            perform action a1 { doc /* complete required safety briefings @S222 */ }
            perform action a2 { doc /* acknowledge the current operating procedures @S222 */ }
            perform action a3 { doc /* receiving operational access @S222 */ }
        }
        part administrativePrivileges : AdministrativePrivileges;
        part advisoryAnalyticsServices : AdvisoryAnalyticsServices;
        part affectedRadioRoute : AffectedRadioRoute {
            exhibit state modes {
                state s0 { doc /* impaired @S086 */ }
            }
        }
        part afterActionReview : AfterActionReview {
            perform action a0 { doc /* reconstruct the timeline from system logs, user accounts, communications records, and maintenance notes @S239 */ }
            perform action a1 { doc /* without assigning blame to individual operators @S239 */ }
        }
        part afterActionReviews : AfterActionReviews;
        part agencyPolicy : AgencyPolicy {
            perform action a0 { doc /* defined by agency policy @S197 */ }
        }
        part airAttackSupervisor : AirAttackSupervisor {
            perform action a0 { doc /* uses the system to understand fire location, smoke behavior, aircraft constraints, and resource priorities @S013 */ }
            perform action a1 { doc /* understand fire location, smoke behavior, aircraft constraints, and resource priorities @S013 */ }
            perform action a2 { doc /* advising on aerial tactics @S013 */ }
            perform action a3 { doc /* confirms the active operating window @S077 */ }
            perform action a4 { doc /* deconflicting fixed-wing, rotary-wing, and uncrewed routes @S079 */ }
            perform action a5 { doc /* reviews each temporary restriction against current fire perimeter intelligence from the Sentinel Fireline Analytics Engine @S092 */ }
            perform action a6 { doc /* approving a release of air assets @S092 */ }
            perform action a7 { doc /* assess whether smoke columns may reduce route visibility @S094 */ }
            perform action a8 { doc /* can verify that ground resources are clear @S098 */ }
            perform action a9 { doc /* authorizing flight activity @S098 */ }
            perform action a10 { doc /* receives map products that emphasize projected columns, flight hazards, target areas, and timing constraints without obscuring ground resource information @S123 */ }
            perform action a11 { doc /* reviews the promoted location, the confidence history, and the current airspace status @S128 */ }
            perform action a12 { doc /* authorizing reconnaissance or retardant planning @S128 */ }
            perform action a13 { doc /* uses the Wind Shift Bulletin @S136 */ }
            perform action a14 { doc /* reassess aircraft sequencing, holding areas, and drop approach direction @S136 */ }
            perform action a15 { doc /* confirms that the planned route and working altitude are acceptable @S139 */ }
            perform action a16 { doc /* selects the operational intent in the Caldera Incident Command Portal @S153 */ }
            perform action a17 { doc /* receive only the permissions required for their operational responsibilities @S187 */ }
            perform action a18 { doc /* interpret system status during aerial operations @S206 */ }
            perform action a19 { doc /* coordinate with the Talon Air Tanker Dispatch Console without bypassing airspace safety requirements @S206 */ }
            perform action a20 { doc /* bypassing airspace safety requirements @S206 */ }
            perform action a21 { doc /* confirm that deployment readiness evidence is sufficient @S232 */ }
        }
        part aircraft : Aircraft {
            perform action a0 { doc /* operate beyond reliable broadband coverage @S008 */ }
        }
        part airspace : Airspace {
            perform action a0 { doc /* permit flight operations @S107 */ }
        }
        part airspaceRestrictedState : AirspaceRestrictedState {
            perform action a0 { doc /* limits dispatch options @S139 */ }
        }
        part airspaceRestrictedStateWorkflow : AirspaceRestrictedStateWorkflow;
        part alternateContactPaths : AlternateContactPaths;
        part analyticsServices : AnalyticsServices {
            perform action a0 { doc /* retain event timing, source identifiers, model version information, and operator acknowledgments @S040 */ }
        }
        part annualRefresherTraining : AnnualRefresherTraining {
            perform action a0 { doc /* include changes to software screens, revised thresholds, updated contact rosters, seasonal hazard briefings, and lessons learned from prior incidents @S214 */ }
        }
        part appendOnlyAuditStore : AppendOnlyAuditStore;
        part aspect : Aspect;
        part assignmentAndStagingChanges : AssignmentAndStagingChanges {
            perform action a0 { doc /* preserve an audit trail @S175 */ }
        }
        part atmosphericGlare : AtmosphericGlare {
            perform action a0 { doc /* can produce similar signatures @S057 */ }
        }
        part auditRecords : AuditRecords {
            perform action a0 { doc /* include synchronized time, user identity, device identity, source network, affected record, and outcome @S190 */ }
        }
        part authorizedReviewer : AuthorizedReviewer {
            perform action a0 { doc /* recorded by an authorized reviewer @S067 */ }
        }
        part authorizedRole : AuthorizedRole {
            perform action a0 { doc /* accepts @S021 */ }
            perform action a1 { doc /* rejects @S021 */ }
            perform action a2 { doc /* requests further verification of a suspected ignition under agency procedure @S021 */ }
        }
        part authorizedUsers : AuthorizedUsers {
            perform action a0 { doc /* review cached incident data @S178 */ }
            perform action a1 { doc /* create queued updates @S178 */ }
        }
        part authorizedWildfirePersonnel : AuthorizedWildfirePersonnel;
        part automatedConfidenceLevel : AutomatedConfidenceLevel {
            perform action a0 { doc /* exceeds the screening threshold @S059 */ }
        }
        part availableObservations : AvailableObservations {
            perform action a0 { doc /* support that status @S012 */ }
        }
        part aviationPersonnel : AviationPersonnel {
            perform action a0 { doc /* can provide independent confirmation from their location @S064 */ }
        }
        part aviationRepresentatives : AviationRepresentatives;
        part aviationSupervisors : AviationSupervisors {
            perform action a0 { doc /* use that identity to validate tasking and hazard reports @S085 */ }
            perform action a1 { doc /* validate tasking and hazard reports @S085 */ }
            perform action a2 { doc /* used by aviation supervisors during route selection and holding-area planning @S093 */ }
        }
        part aviationSupportUnits : AviationSupportUnits;
        part bestKnownLocation : BestKnownLocation;
        part bridgePath : BridgePath {
            perform action a0 { doc /* fails @S086 */ }
        }
        part broaderAnalyticsWorkflow : BroaderAnalyticsWorkflow;
        part calderaIncidentCommandPortal : CalderaIncidentCommandPortal {
            perform action a0 { doc /* presenting incident information, recommended actions, and operational status to authorized wildfire personnel @S003 */ }
            perform action a1 { doc /* displays camera views, detection history, weather context, map layers, and status transitions such as Confirmed Ignition State and Airspace Restricted State @S046 */ }
            perform action a2 { doc /* opens a triage case for human review @S059 */ }
            perform action a3 { doc /* records the reason for each triage decision @S069 */ }
            perform action a4 { doc /* can associate the incident with the Airspace Restricted State @S074 */ }
            perform action a5 { doc /* supports coordinated air and ground operations @S076 */ }
            perform action a6 { doc /* shows the Airspace Restricted State @S077 */ }
            perform action a7 { doc /* marks the affected radio route as impaired @S086 */ }
            perform action a8 { doc /* requires manual acknowledgement by the Duty Detection Officer @S086 */ }
            perform action a9 { doc /* displays crew acknowledgements beside aviation tasks @S098 */ }
            perform action a10 { doc /* renders the current perimeter, projected spread, resource positions, and decision annotations into a common operating picture with role-based symbology @S119 */ }
            perform action a11 { doc /* produces the Crew Staging Pin from the approved map layer @S120 */ }
            perform action a12 { doc /* assigns it an effective time, location accuracy, and incident identifier @S120 */ }
            perform action a13 { doc /* promotes an accepted fire location into the operational map @S127 */ }
            perform action a14 { doc /* marks it available for aviation review @S127 */ }
            perform action a15 { doc /* preserves each aviation decision with the approving supervisor, operational period, and reason for change @S149 */ }
            perform action a16 { doc /* records each assignment package with an objective, time validity, confirmation status, and required acknowledgments @S154 */ }
            perform action a17 { doc /* marks affected crew assignments for review before release @S160 */ }
            perform action a18 { doc /* enters a disconnected operating mode @S177 */ }
            perform action a19 { doc /* clearly marks all displayed information with the last synchronization time @S177 */ }
            perform action a20 { doc /* allows authorized users to review cached incident data and create queued updates @S178 */ }
            perform action a21 { doc /* prevents irreversible releases until connectivity is restored @S178 */ }
            perform action a22 { doc /* complete documented functional testing against the approved mission scenarios @S227 */ }
            exhibit state modes {
                state s0 { doc /* disconnected operating mode @S177 */ }
            }
        }
        part calderaWildfireDetectionAndSuppressionSupportSystem : CalderaWildfireDetectionAndSuppressionSupportSystem {
            perform action a0 { doc /* operates in a wildfire threat environment shaped by dry fuels, steep terrain, variable winds, lightning, human-caused ignitions, and expanding wildland-urban interface exposure @S001 */ }
            perform action a1 { doc /* also supports recognition of an Airspace Restricted State @S019 */ }
            perform action a2 { doc /* keeps suppression planning visible @S099 */ }
            perform action a3 { doc /* preventing premature aircraft dispatch @S099 */ }
            perform action a4 { doc /* converts detection observations, aerial imagery, weather updates, and geospatial overlays into a shared fire behavior assessment for operational use @S101 */ }
            perform action a5 { doc /* holds the affected recommendation for Air Attack Supervisor review before further action @S151 */ }
            perform action a6 { doc /* enters the Airspace Restricted State @S167 */ }
            perform action a7 { doc /* favor continuity of command decisions over full automation @S176 */ }
            perform action a8 { doc /* protect retained data with encryption at rest, controlled export procedures, and deletion workflows that require documented authorization @S198 */ }
            exhibit state modes {
                state s0 { doc /* Airspace Restricted State @S019,S139,S167 */ }
                state s1 { doc /* Confirmed Ignition State @S099,S160 */ }
            }
        }
        part callSigns : CallSigns;
        part cameraFamiliarization : CameraFamiliarization {
            perform action a0 { doc /* cover the North Lookout Camera Mast and the South Lookout Camera Mast, including normal image behavior, degraded visibility conditions, routine inspection cues, and reporting of equipment faults @S203 */ }
        }
        part cellularService : CellularService {
            exhibit state modes {
                state s0 { doc /* degraded-mode @S029 */ }
            }
        }
        part changesToSoftwareScreens : ChangesToSoftwareScreens;
        part changingConditions : ChangingConditions {
            perform action a0 { doc /* require adjusted priorities @S017 */ }
        }
        part chargingInterfaces : ChargingInterfaces;
        part cloudShadow : CloudShadow {
            perform action a0 { doc /* can produce similar signatures @S057 */ }
        }
        part commandStaff : CommandStaff {
            perform action a0 { doc /* need consolidated situational information @S045 */ }
        }
        part commandVisibility : CommandVisibility {
            perform action a0 { doc /* meet the approved concept of operations @S235 */ }
        }
        part commandWorkflow : CommandWorkflow {
            perform action a0 { doc /* has been released for field distribution by the command workflow @S072 */ }
        }
        part commonOperatingPicture : CommonOperatingPicture {
            perform action a0 { doc /* shows the conflict explicitly @S126 */ }
            perform action a1 { doc /* requires review before the affected recommendation is promoted for command use @S126 */ }
        }
        part communicationCompletionRate : CommunicationCompletionRate;
        part communicationsConditions : CommunicationsConditions {
            perform action a0 { doc /* permit flight operations @S107 */ }
        }
        part communicationsPaths : CommunicationsPaths {
            perform action a0 { doc /* preserve incident command authority @S025 */ }
        }
        part communicationsTraining : CommunicationsTraining {
            perform action a0 { doc /* includes VHF Radio Gateway Repeater failure modes, alternate contact paths, call signs, message brevity, and confirmation readbacks @S211 */ }
        }
        part communities : Communities;
        part confidenceBasis : ConfidenceBasis;
        part configurationChanges : ConfigurationChanges;
        part configuredWeatherRules : ConfiguredWeatherRules {
            perform action a0 { doc /* identify a significant change in local wind behavior @S043 */ }
        }
        part confirmation : Confirmation;
        part confirmationReadbacks : ConfirmationReadbacks;
        part confirmedIgnitionState : ConfirmedIgnitionState {
            perform action a0 { doc /* changes the perimeter or priority area @S160 */ }
        }
        part confirmedIgnitionStateWorkflow : ConfirmedIgnitionStateWorkflow;
        part controlledFieldValidation : ControlledFieldValidation {
            perform action a0 { doc /* shows that task execution, abort behavior, and status reporting remain stable under expected seasonal conditions @S229 */ }
        }
        part cooperatingPublicSafetyPartners : CooperatingPublicSafetyPartners;
        part correctiveActions : CorrectiveActions;
        part countyEmergencyLiaison : CountyEmergencyLiaison {
            perform action a0 { doc /* represents county coordination needs related to public warning, road impacts, shelter considerations, and integration with emergency operations procedures @S010 */ }
            perform action a1 { doc /* sends the Drone Corridor Permit @S089 */ }
            perform action a2 { doc /* receives a simplified view that preserves perimeter confidence, threatened areas, and recommended public safety coordination actions while hiding tactical details not needed for civil coordination @S124 */ }
            perform action a3 { doc /* can view approved aviation status and public safety implications without gaining authority to alter dispatch or suppression records @S150 */ }
            perform action a4 { doc /* can view staging posture and public safety implications @S174 */ }
            perform action a5 { doc /* receive only the permissions required for their operational responsibilities @S187 */ }
            perform action a6 { doc /* interpret public-safety information from the Caldera Incident Command Portal @S210 */ }
            perform action a7 { doc /* coordinate notifications with county procedures @S210 */ }
            perform action a8 { doc /* use the Suppression Drop Receipt during post-incident reconciliation @S234 */ }
            perform action a9 { doc /* verify that reported suppression activity can be traced to county situation reporting @S234 */ }
        }
        part countyEmergencyManagement : CountyEmergencyManagement;
        part countyLiaisonProcedures : CountyLiaisonProcedures {
            perform action a0 { doc /* require that jurisdictional constraints be entered in the Caldera Incident Command Portal before the Drone Pilot Operator receives a route briefing @S090 */ }
        }
        part countyLiaisonRepresentatives : CountyLiaisonRepresentatives;
        part crewlineMobileTablet : CrewlineMobileTablet {
            perform action a0 { doc /* provides mobile access to approved operational information for personnel who need current situational awareness away from a command workstation @S016 */ }
            perform action a1 { doc /* provides the Helitack Crew Leader with field access to assigned incident context, map references, and updates that have been approved for mobile distribution @S049 */ }
            perform action a2 { doc /* shows approved suppression objectives, aircraft caution areas, and current assignment notes for crews operating near the incident @S146 */ }
            perform action a3 { doc /* displays the current division assignment, route guidance, rally location, and assigned communications channel for the logged-in crew @S155 */ }
            perform action a4 { doc /* caches the latest accepted staging information @S159 */ }
            perform action a5 { doc /* marks any expired package as unavailable for execution @S159 */ }
            perform action a6 { doc /* presents the last verified assignment package @S172 */ }
            perform action a7 { doc /* clearly identifies the time of last update @S172 */ }
        }
        part crewlineMobileTabletClients : CrewlineMobileTabletClients {
            perform action a0 { doc /* queue field updates locally @S184 */ }
            perform action a1 { doc /* encrypt the queue at rest @S184 */ }
            perform action a2 { doc /* reconcile conflicts @S184 */ }
            perform action a3 { doc /* preserving the original author, device time, and server acceptance time @S184 */ }
        }
        part crewlineMobileTabletUsers : CrewlineMobileTabletUsers {
            perform action a0 { doc /* receive only the confirmed incident context that has been released for field distribution by the command workflow @S072 */ }
        }
        part crews : Crews {
            perform action a0 { doc /* operate beyond reliable broadband coverage @S008 */ }
            perform action a1 { doc /* operating near the incident @S146 */ }
            perform action a2 { doc /* can confirm location without relying on informal landmarks @S158 */ }
            perform action a3 { doc /* cannot maintain a data session in canyon or timbered terrain @S171 */ }
        }
        part currentRecommendedCoordinationPosture : CurrentRecommendedCoordinationPosture;
        part dataLink : DataLink {
            exhibit state modes {
                state s0 { doc /* degraded @S172 */ }
            }
        }
        part dataStewardship : DataStewardship {
            perform action a0 { doc /* define retention, access control, quality review, and disposition rules for operational records, sensor data, model outputs, configuration records, and user activity records @S242 */ }
        }
        part deletionWorkflows : DeletionWorkflows {
            perform action a0 { doc /* require documented authorization @S198 */ }
        }
        part deploymentGovernanceBoard : DeploymentGovernanceBoard {
            perform action a0 { doc /* include operational leadership, maintenance representation, information security representation, and designated representatives for detection, aviation, ground crew, and county coordination functions @S225 */ }
            perform action a1 { doc /* approve each seasonal rollout @S226 */ }
            perform action a2 { doc /* reviewing residual risk, staffing readiness, configuration baselines, and open corrective actions from the prior operating period @S226 */ }
            perform action a3 { doc /* authorize limited use @S237 */ }
            perform action a4 { doc /* compare system performance, operational workload, maintenance burden, and user feedback against the acceptance criteria approved for that season @S246 */ }
        }
        part deploymentGovernanceForTheCalderaWildfireDetectionAndSuppressionSupportSystem : DeploymentGovernanceForTheCalderaWildfireDetectionAndSuppressionSupportSystem;
        part designatedRepresentativesForAviation : DesignatedRepresentativesForAviation;
        part designatedRepresentativesForCountyCoordinationFunctions : DesignatedRepresentativesForCountyCoordinationFunctions;
        part designatedRepresentativesForDetection : DesignatedRepresentativesForDetection;
        part designatedRepresentativesForGroundCrew : DesignatedRepresentativesForGroundCrew;
        part detectionPerformance : DetectionPerformance {
            perform action a0 { doc /* improves without unacceptable increases in false alerts @S244 */ }
        }
        part detectionQuality : DetectionQuality;
        part detectionSupport : DetectionSupport {
            perform action a0 { doc /* begins with observation, automated screening, operator review, and presentation of confidence, location, and context for suspected fire activity @S020 */ }
            perform action a1 { doc /* ends at the point where an authorized role accepts, rejects, or requests further verification of a suspected ignition under agency procedure @S021 */ }
        }
        part detectionWorkflow : DetectionWorkflow {
            perform action a0 { doc /* begins @S051 */ }
        }
        part dismissedCases : DismissedCases {
            perform action a0 { doc /* remain searchable for audit and model improvement @S075 */ }
            perform action a1 { doc /* do not create a suppression assignment or public incident notification @S075 */ }
        }
        part documentedCheck : DocumentedCheck;
        part documentedRecoveryProcedures : DocumentedRecoveryProcedures;
        part drainages : Drainages;
        part dronePilotOperator : DronePilotOperator {
            perform action a0 { doc /* use the system @S015 */ }
            perform action a1 { doc /* maintain shared awareness of field conditions, mission timing, and hazards that could affect crew safety @S015 */ }
            perform action a2 { doc /* uses Drone Tasking Service to review proposed routes, current dock status, and operational constraints @S036 */ }
            perform action a3 { doc /* review proposed routes, current dock status, and operational constraints @S036 */ }
            perform action a4 { doc /* coordinating any field action through established procedures @S036 */ }
            perform action a5 { doc /* confirms that the proposed verification task is safe for launch conditions and consistent with current operating constraints @S063 */ }
            perform action a6 { doc /* launches from the Horizon Ridge Drone Dock @S079 */ }
            perform action a7 { doc /* receives a route briefing @S090 */ }
            perform action a8 { doc /* uses the swap ticket @S109 */ }
            perform action a9 { doc /* keep imaging sorties aligned with available aircraft endurance and expected return time @S109 */ }
            perform action a10 { doc /* confirms that the proposed route is consistent with field conditions and can be flown without interfering with suppression aircraft @S132 */ }
            perform action a11 { doc /* confirms launch readiness separately from crew assignment acceptance @S170 */ }
            perform action a12 { doc /* keep reconnaissance execution independent from ground deployment @S170 */ }
            perform action a13 { doc /* receive only the permissions required for their operational responsibilities @S187 */ }
        }
        part droneTaskingService : DroneTaskingService {
            perform action a0 { doc /* support directed aerial observation @S005 */ }
            perform action a1 { doc /* manages approved unmanned flight requests @S035 */ }
            perform action a2 { doc /* records mission constraints @S035 */ }
            perform action a3 { doc /* presents task status @S035 */ }
            perform action a4 { doc /* without acting as an independent authority for flight release @S035 */ }
            perform action a5 { doc /* may prepare a verification task for the Horizon Ridge Drone Dock @S062 */ }
            perform action a6 { doc /* shall not issue a launch task that conflicts with an active aviation lane maintained by the Talon Air Tanker Dispatch Console @S080 */ }
            perform action a7 { doc /* packages approved imaging objectives as map footprints, altitude bands, and revisit intervals @S108 */ }
            perform action a8 { doc /* converts reconnaissance objectives into trackable missions with launch windows, image requirements, altitude limits, and abort criteria @S129 */ }
            perform action a9 { doc /* maintains reconnaissance task status @S168 */ }
            perform action a10 { doc /* validates the corridor permit @S192 */ }
            perform action a11 { doc /* releasing an automated flight task @S192 */ }
            exhibit state modes {
                state s0 { doc /* degraded communications mode @S192 */ }
            }
        }
        part dust : Dust {
            perform action a0 { doc /* can produce similar signatures @S057 */ }
        }
        part dutyDetectionOfficer : DutyDetectionOfficer {
            perform action a0 { doc /* monitoring detection cues @S011 */ }
            perform action a1 { doc /* requesting verification @S011 */ }
            perform action a2 { doc /* recommending whether a suspected ignition should be escalated @S011 */ }
            perform action a3 { doc /* may recommend a Confirmed Ignition State @S012 */ }
            perform action a4 { doc /* reviews the triage case @S060 */ }
            perform action a5 { doc /* compares current imagery with recent frames @S060 */ }
            perform action a6 { doc /* checks whether the indication is growing, drifting, or disappearing @S060 */ }
            perform action a7 { doc /* may request a fresh pan, tilt, or zoom view from the nearest fixed camera @S061 */ }
            perform action a8 { doc /* records the restriction basis in the Caldera Incident Command Portal @S078 */ }
            perform action a9 { doc /* must verify that the impaired route has an alternate contact method @S087 */ }
            perform action a10 { doc /* uses the spot snippet @S106 */ }
            perform action a11 { doc /* compare the automated classification with visible flame, smoke color, and terrain context @S106 */ }
            perform action a12 { doc /* accepting the observation into the assessment queue @S106 */ }
            perform action a13 { doc /* receives a visible warning @S179 */ }
            perform action a14 { doc /* operate the Caldera Incident Command Portal @S202 */ }
            perform action a15 { doc /* review detections @S202 */ }
            perform action a16 { doc /* validate confidence indicators @S202 */ }
            perform action a17 { doc /* escalate suspected ignitions according to the approved incident workflow @S202 */ }
            perform action a18 { doc /* learn how the Sentinel Fireline Analytics Engine and the Smoke Classifier Module present uncertainty @S204 */ }
        }
        part eastRetardantLoadingPump : EastRetardantLoadingPump {
            perform action a0 { doc /* sends the Retardant Batch Slip @S073 */ }
            perform action a1 { doc /* report equipment state, flow readiness, and out-of-service conditions @S142 */ }
            perform action a2 { doc /* support base capacity estimates @S142 */ }
            perform action a3 { doc /* enter a metered recirculation mode @S194 */ }
            perform action a4 { doc /* pass integration checks @S230 */ }
            exhibit state modes {
                state s0 { doc /* metered recirculation mode @S194 */ }
            }
        }
        part emergencyAccess : EmergencyAccess {
            perform action a0 { doc /* uses pre-issued signed credentials @S186 */ }
        }
        part equipmentFault : EquipmentFault {
            perform action a0 { doc /* stops detection or suppression-support operations @S199 */ }
        }
        part escalationTiming : EscalationTiming {
            perform action a0 { doc /* meet the approved concept of operations @S235 */ }
        }
        part escapeRouteDegradation : EscapeRouteDegradation;
        part evacuationZones : EvacuationZones;
        part eventPart : Event {
            perform action a0 { doc /* affected more than one operational function @S221 */ }
        }
        part exception : Exception {
            perform action a0 { doc /* prevents safe execution @S173 */ }
        }
        part exerciseControllers : ExerciseControllers {
            perform action a0 { doc /* inject realistic complications such as intermittent network service, obscured camera views, delayed field confirmation, resource conflicts, and conflicting reports from external observers @S217 */ }
        }
        part expiredPackage : ExpiredPackage {
            exhibit state modes {
                state s0 { doc /* unavailable for execution @S159 */ }
            }
        }
        part falseAlarmReview : FalseAlarmReview {
            perform action a0 { doc /* identify the apparent cause, affected sensors or analytic outputs, operator actions, dispatch consequences, and any recommended tuning or training change @S220 */ }
        }
        part fieldCleaningSupplies : FieldCleaningSupplies;
        part fieldComponent : FieldComponent {
            perform action a0 { doc /* buffer signed audit records locally @S191 */ }
            perform action a1 { doc /* forward them without modification @S191 */ }
        }
        part fieldConfigurations : FieldConfigurations {
            perform action a0 { doc /* change @S200 */ }
        }
        part fieldCrewRepresentatives : FieldCrewRepresentatives;
        part fieldObservations : FieldObservations {
            perform action a0 { doc /* change @S161 */ }
        }
        part fieldObservers : FieldObservers {
            perform action a0 { doc /* can provide independent confirmation from their location @S064 */ }
        }
        part fieldResources : FieldResources {
            perform action a0 { doc /* need updated information @S018 */ }
        }
        part fireBehaviorModel : FireBehaviorModel {
            perform action a0 { doc /* combines the accepted perimeter, recent growth vectors, weather fields, and fuel conditions @S117 */ }
            perform action a1 { doc /* estimate short-term spread direction and rate @S117 */ }
        }
        part fireSpreadEstimates : FireSpreadEstimates {
            perform action a0 { doc /* change @S161 */ }
        }
        part fixedRidgeSensors : FixedRidgeSensors;
        part flameGrowth : FlameGrowth;
        part flightBattery : FlightBattery {
            perform action a0 { doc /* has reached the configured replacement threshold @S034 */ }
        }
        part fuels : Fuels;
        part geospatialOverlays : GeospatialOverlays;
        part groundCrewAssignments : GroundCrewAssignments {
            perform action a0 { doc /* avoid analytic scores that are not needed for tactical movement @S157 */ }
        }
        part groundCrews : GroundCrews {
            perform action a0 { doc /* receive assignments, staging information, hazards, and updated intelligence from the support system during active wildfire operations @S152 */ }
        }
        part groundTeams : GroundTeams {
            perform action a0 { doc /* can see whether requested intelligence is pending, active, or complete @S168 */ }
        }
        part hardenedPowerDistribution : HardenedPowerDistribution;
        part hazards : Hazards {
            perform action a0 { doc /* could affect crew safety @S015 */ }
        }
        part helitackAssignments : HelitackAssignments {
            perform action a0 { doc /* show the restriction boundary @S167 */ }
            perform action a1 { doc /* require confirmation @S167 */ }
        }
        part helitackCrewLeader : HelitackCrewLeader {
            perform action a0 { doc /* use the system @S015 */ }
            perform action a1 { doc /* maintain shared awareness of field conditions, mission timing, and hazards that could affect crew safety @S015 */ }
            perform action a2 { doc /* uses the Crewline Mobile Tablet @S097 */ }
            perform action a3 { doc /* acknowledge air-to-ground instructions @S097 */ }
            perform action a4 { doc /* report whether crews are inside any planned drop or reconnaissance area @S097 */ }
            perform action a5 { doc /* acknowledges nearby aircraft activity @S147 */ }
            perform action a6 { doc /* receives the same operational package with aviation constraints and landing zone notes after Air Attack Supervisor approval @S156 */ }
            perform action a7 { doc /* acknowledges assignment receipt @S173 */ }
            perform action a8 { doc /* reports readiness @S173 */ }
            perform action a9 { doc /* records any exception that prevents safe execution @S173 */ }
            perform action a10 { doc /* receive only the permissions required for their operational responsibilities @S187 */ }
            perform action a11 { doc /* use the staging pin @S209 */ }
            perform action a12 { doc /* confirm that the assigned crew is positioned at the exercise location @S209 */ }
        }
        part helitackCrews : HelitackCrews {
            perform action a0 { doc /* receive assignments, staging information, hazards, and updated intelligence from the support system during active wildfire operations @S152 */ }
        }
        part highVolumeRawSensorData : HighVolumeRawSensorData {
            perform action a0 { doc /* follow a shorter approved retention schedule @S197 */ }
        }
        part horizonRidgeDroneDock : HorizonRidgeDroneDock {
            perform action a0 { doc /* support directed aerial observation @S005 */ }
            perform action a1 { doc /* produces the Battery Swap Ticket @S034 */ }
            perform action a2 { doc /* provides an observation that may indicate a new ignition @S051 */ }
            perform action a3 { doc /* supports initial attack @S130 */ }
            perform action a4 { doc /* keeping assigned aircraft charged, positioned, and ready for rapid launch @S130 */ }
            perform action a5 { doc /* report launch readiness, aircraft health, and recovery availability @S131 */ }
        }
        part horizonRidgeDroneDockStatus : HorizonRidgeDroneDockStatus {
            perform action a0 { doc /* does not by itself authorize crew movement into a new area @S169 */ }
        }
        part ignition : Ignition;
        part improvementPlan : ImprovementPlan {
            perform action a0 { doc /* define which procedures, training materials, interfaces, algorithms, and support arrangements will be revised before the next seasonal readiness campaign begins @S247 */ }
        }
        part incident : Incident {
            perform action a0 { doc /* enters a managed response posture @S076 */ }
            exhibit state modes {
                state s0 { doc /* Airspace Restricted State @S074 */ }
                state s1 { doc /* managed response posture @S076 */ }
            }
        }
        part incidentRecord : IncidentRecord {
            perform action a0 { doc /* becomes available for suppression planning @S070 */ }
            exhibit state modes {
                state s0 { doc /* Confirmed Ignition State @S070 */ }
            }
        }
        part incidentStaff : IncidentStaff {
            perform action a0 { doc /* need updated scene awareness @S005 */ }
            perform action a1 { doc /* need coordinated information for resource movement, aviation planning, field safety, and ongoing assessment of fire behavior @S022 */ }
        }
        part indication : Indication {
            perform action a0 { doc /* is growing @S060 */ }
            perform action a1 { doc /* drifting @S060 */ }
            perform action a2 { doc /* disappearing @S060 */ }
        }
        part informationSecurityRepresentation : InformationSecurityRepresentation;
        part initialQualification : InitialQualification {
            perform action a0 { doc /* include supervised console practice, scenario walkthroughs, and a documented check by an instructor who is authorized by the operations lead @S213 */ }
        }
        part inputs : Inputs {
            perform action a0 { doc /* conflict @S126 */ }
        }
        part integrationChecks : IntegrationChecks {
            perform action a0 { doc /* verify operator controls, fault handling, and audit capture @S230 */ }
        }
        part jurisdictionBoundaries : JurisdictionBoundaries;
        part knownCommunicationsCoverage : KnownCommunicationsCoverage;
        part laterOperators : LaterOperators {
            perform action a0 { doc /* can understand whether the case was advanced, held, or dismissed @S069 */ }
        }
        part lessonsLearnedFromPriorIncidents : LessonsLearnedFromPriorIncidents;
        part lightningProtection : LightningProtection;
        part limitedAccess : LimitedAccess;
        part liveExercises : LiveExercises {
            perform action a0 { doc /* include field crews, aircraft coordination staff, drone operations staff, and command-center personnel @S216 */ }
        }
        part localEquipmentCabinets : LocalEquipmentCabinets;
        part localFireAgencies : LocalFireAgencies;
        part localHealthMonitoring : LocalHealthMonitoring;
        part localObservations : LocalObservations {
            perform action a0 { doc /* conflict with displayed values @S212 */ }
        }
        part localSensorProcessing : LocalSensorProcessing {
            perform action a0 { doc /* identifies a candidate heat signature @S030 */ }
        }
        part localWeatherCache : LocalWeatherCache {
            perform action a0 { doc /* support near-term fire behavior review @S183 */ }
        }
        part localWindHumidityTemperatureAndStabilityContext : LocalWindHumidityTemperatureAndStabilityContext {
            perform action a0 { doc /* helps determine whether an indication is plausible for active combustion @S058 */ }
        }
        part loggedInCrew : LoggedInCrew;
        part maintenanceActions : MaintenanceActions;
        part maintenanceController : MaintenanceController {
            perform action a0 { doc /* records that a flight battery has reached the configured replacement threshold @S034 */ }
        }
        part maintenanceRepresentation : MaintenanceRepresentation;
        part maintenanceRepresentatives : MaintenanceRepresentatives;
        part maintenanceStaff : MaintenanceStaff {
            perform action a0 { doc /* distinguish sensor failure from environmental obscuration @S182 */ }
        }
        part mapProducts : MapProducts {
            perform action a0 { doc /* emphasize projected columns, flight hazards, target areas, and timing constraints @S123 */ }
            perform action a1 { doc /* without obscuring ground resource information @S123 */ }
            perform action a2 { doc /* records source time, processing time, model version, analyst acceptance, and supersession status @S125 */ }
        }
        part mappingWorkflow : MappingWorkflow {
            perform action a0 { doc /* can triangulate a probable origin area @S104 */ }
            perform action a1 { doc /* bound the uncertainty ellipse @S104 */ }
        }
        part mesoWestWeatherFusionNode : MesoWestWeatherFusionNode {
            perform action a0 { doc /* contributes localized weather context @S007 */ }
            perform action a1 { doc /* ingests station observations, forecast grids, and configured quality checks @S042 */ }
            perform action a2 { doc /* provide a consistent weather picture for the operating area @S042 */ }
            perform action a3 { doc /* sends the Wind Shift Bulletin @S043 */ }
            perform action a4 { doc /* provides local wind, humidity, temperature, and stability context @S058 */ }
            perform action a5 { doc /* supplies wind and visibility context used by aviation supervisors during route selection and holding-area planning @S093 */ }
            perform action a6 { doc /* ingests station observations, forecast grids, and local quality checks @S113 */ }
            perform action a7 { doc /* maintain the wind, humidity, temperature, and stability fields used by the spread model @S113 */ }
            perform action a8 { doc /* publishes a time-indexed weather update that marks significant forecast changes and identifies which map products require recomputation @S114 */ }
            perform action a9 { doc /* provides weather-derived exposure flags @S166 */ }
            perform action a10 { doc /* retain a local weather cache @S183 */ }
            perform action a11 { doc /* supports situational awareness @S212 */ }
            perform action a12 { doc /* meet agreed availability, timing, and data-quality thresholds during the readiness window @S228 */ }
        }
        part messageBrevity : MessageBrevity;
        part northLookoutCameraMast : NorthLookoutCameraMast {
            perform action a0 { doc /* provide fixed observation coverage over high-risk sectors @S004 */ }
            perform action a1 { doc /* provide long-range visual coverage of drainages, access roads, and known ignition corridors @S026 */ }
            perform action a2 { doc /* sends the Thermal Spot Snippet @S030 */ }
            perform action a3 { doc /* provides an observation that may indicate a new ignition @S051 */ }
            perform action a4 { doc /* provide observation context that helps the Air Attack Supervisor assess whether smoke columns may reduce route visibility @S094 */ }
            perform action a5 { doc /* captures a time-stamped smoke column bearing @S103 */ }
            perform action a6 { doc /* reports the pan, tilt, zoom, and confidence values needed to project the observation onto terrain @S103 */ }
            perform action a7 { doc /* report heartbeat, temperature, storage, and pointing-status telemetry @S182 */ }
            perform action a8 { doc /* meet agreed availability, timing, and data-quality thresholds during the readiness window @S228 */ }
        }
        part observation : Observation {
            perform action a0 { doc /* may indicate a new ignition @S051 */ }
        }
        part observationContext : ObservationContext {
            perform action a0 { doc /* helps the Air Attack Supervisor assess whether smoke columns may reduce route visibility @S094 */ }
        }
        part observationHistory : ObservationHistory;
        part occlusion : Occlusion {
            perform action a0 { doc /* prevents a clear fixed-camera view @S062 */ }
        }
        part operatingProcedures : OperatingProcedures {
            perform action a0 { doc /* support that status @S012 */ }
            perform action a1 { doc /* change @S200 */ }
        }
        part operationalArea : OperationalArea;
        part operationalData : OperationalData {
            perform action a0 { doc /* preserve enough context to support later engineering review and regulatory inquiry @S243 */ }
        }
        part operationalLeadership : OperationalLeadership;
        part operationalRecommendations : OperationalRecommendations {
            perform action a0 { doc /* may include confirming an ignition, increasing camera monitoring, requesting drone coverage, preparing aviation options, repositioning ground crews, or notifying county partners @S122 */ }
        }
        part operationalRecord : OperationalRecord {
            perform action a0 { doc /* uses Air Attack Supervisor @S065 */ }
            perform action a1 { doc /* uses Talon Air Tanker Dispatch Console @S066 */ }
        }
        part operationalRecords : OperationalRecords {
            perform action a0 { doc /* support command decisions and safety reviews @S197 */ }
            perform action a1 { doc /* be retained for the incident record period defined by agency policy @S197 */ }
        }
        part operationalUsers : OperationalUsers {
            perform action a0 { doc /* receive communications training that includes VHF Radio Gateway Repeater failure modes, alternate contact paths, call signs, message brevity, and confirmation readbacks @S211 */ }
            perform action a1 { doc /* can recognize restrictions @S236 */ }
            perform action a2 { doc /* apply required controls @S236 */ }
            perform action a3 { doc /* recover normal coordination @S236 */ }
        }
        part operations : Operations {
            perform action a0 { doc /* should pause for safety reasons @S018 */ }
        }
        part operationsLead : OperationsLead {
            perform action a0 { doc /* is authorized by the operations lead @S213 */ }
        }
        part operationsRepresentatives : OperationsRepresentatives;
        part operatorAcknowledgement : OperatorAcknowledgement {
            perform action a0 { doc /* meet the approved concept of operations @S235 */ }
        }
        part operators : Operators {
            perform action a0 { doc /* treat weather inputs when local observations conflict with displayed values @S212 */ }
        }
        part participant : Participant {
            perform action a0 { doc /* practices the decisions, system functions, communications, and safety constraints that apply to the assigned position @S201 */ }
        }
        part participatingOrganizations : ParticipatingOrganizations;
        part performanceMeasures : PerformanceMeasures {
            perform action a0 { doc /* include time from automated detection to human review, time from review to command notification, time to resource assignment, communication completion rate, and accuracy of incident status updates @S218 */ }
        }
        part personnel : Personnel {
            perform action a0 { doc /* need current situational awareness away from a command workstation @S016 */ }
            perform action a1 { doc /* do not meet proficiency requirements @S223 */ }
            perform action a2 { doc /* complete remedial training and a repeat evaluation @S223 */ }
            perform action a3 { doc /* performing unsupervised duties in the Caldera Wildfire Detection and Suppression Support System @S223 */ }
        }
        part postIncidentReview : PostIncidentReview {
            perform action a0 { doc /* can reconstruct both aviation decisions and interagency notifications @S100 */ }
        }
        part preIssuedSignedCredentials : PreIssuedSignedCredentials {
            perform action a0 { doc /* expire automatically @S186 */ }
        }
        part radioBridging : RadioBridging {
            perform action a0 { doc /* shall preserve the original speaker identity @S085 */ }
        }
        part releaseCandidate : ReleaseCandidate {
            perform action a0 { doc /* not enter operational service @S227 */ }
        }
        part remoteRecreationAreas : RemoteRecreationAreas;
        part replacementNetworkEquipment : ReplacementNetworkEquipment;
        part requestedIntelligence : RequestedIntelligence {
            exhibit state modes {
                state s0 { doc /* active @S168 */ }
                state s1 { doc /* complete @S168 */ }
                state s2 { doc /* pending @S168 */ }
            }
        }
        part reviewBoard : ReviewBoard {
            perform action a0 { doc /* include operations, aviation, field crew, maintenance, and county liaison representatives when the event affected more than one operational function @S221 */ }
        }
        part reviewFacilitators : ReviewFacilitators {
            perform action a0 { doc /* document what was expected to happen, what actually happened, why differences occurred, and which corrective actions are necessary before the next readiness cycle @S240 */ }
        }
        part reviewerIdentity : ReviewerIdentity;
        part revisedThresholds : RevisedThresholds;
        part ridgelines : Ridgelines;
        part roads : Roads;
        part ruleChecks : RuleChecks {
            perform action a0 { doc /* compare projected fire arrival times with values at risk, road access, crew travel time, and aircraft availability @S121 */ }
        }
        part scenarioWalkthroughs : ScenarioWalkthroughs;
        part seasonalHazardBriefings : SeasonalHazardBriefings;
        part seasonalReadiness : SeasonalReadiness {
            perform action a0 { doc /* require each active user to demonstrate current proficiency, complete required safety briefings, and acknowledge the current operating procedures before receiving operational access @S222 */ }
        }
        part seasonalReadinessCampaign : SeasonalReadinessCampaign {
            perform action a0 { doc /* begins @S247 */ }
        }
        part secureNetworkTermination : SecureNetworkTermination;
        part securityRelevantEvents : SecurityRelevantEvents;
        part sentinelFirelineAnalyticsEngine : SentinelFirelineAnalyticsEngine {
            perform action a0 { doc /* assist in screening imagery and other observations for potential fire activity @S006 */ }
            perform action a1 { doc /* screening imagery and other observations for potential fire activity @S006 */ }
            perform action a2 { doc /* aggregates camera detections, weather inputs, geospatial context, and operator feedback into traceable recommendations for fire detection and suppression support @S038 */ }
            perform action a3 { doc /* receives the observation context @S053 */ }
            perform action a4 { doc /* normalizes image, thermal, and weather attributes into a common event record @S053 */ }
            perform action a5 { doc /* identifies heat signatures, smoke edges, flame fronts, and potential spot fire indicators in the registered imagery @S111 */ }
            perform action a6 { doc /* compares recent reconnaissance observations with camera detections and weather-driven projections @S134 */ }
            perform action a7 { doc /* support tactical recommendations @S134 */ }
            perform action a8 { doc /* updates hazard summaries @S161 */ }
            perform action a9 { doc /* applies the Ridge Shadow Mask @S162 */ }
            perform action a10 { doc /* estimating crew-visible fire edge confidence in steep terrain @S162 */ }
            perform action a11 { doc /* issues a crew exposure refresh @S164 */ }
            perform action a12 { doc /* continue using the last approved model configuration after a repository outage @S180 */ }
            perform action a13 { doc /* reject unversioned rules or unsigned analytic packages @S180 */ }
            perform action a14 { doc /* present uncertainty @S204 */ }
            perform action a15 { doc /* complete documented functional testing against the approved mission scenarios @S227 */ }
        }
        part serviceAccess : ServiceAccess;
        part sharedFireBehaviorAssessment : SharedFireBehaviorAssessment {
            perform action a0 { doc /* begins when visual detections are correlated with incident geometry, terrain, fuel type, and current resource locations in the mapping workspace @S102 */ }
        }
        part simplifiedView : SimplifiedView {
            perform action a0 { doc /* preserves perimeter confidence, threatened areas, and recommended public safety coordination actions @S124 */ }
            perform action a1 { doc /* hiding tactical details not needed for civil coordination @S124 */ }
        }
        part slope : Slope;
        part smallIgnition : SmallIgnition {
            perform action a0 { doc /* can become a life-safety incident within minutes @S002 */ }
        }
        part smokeClassifierModule : SmokeClassifierModule {
            perform action a0 { doc /* assist in screening imagery and other observations for potential fire activity @S006 */ }
            perform action a1 { doc /* screening imagery and other observations for potential fire activity @S006 */ }
            perform action a2 { doc /* runs as a bounded analytics component @S039 */ }
            perform action a3 { doc /* scores visual observations for plume likelihood @S039 */ }
            perform action a4 { doc /* passes confidence values to the broader analytics workflow @S039 */ }
            perform action a5 { doc /* produces the Ridge Shadow Mask @S056 */ }
            perform action a6 { doc /* assigns each observation a smoke likelihood, growth trend, and obscuration flag @S105 */ }
            perform action a7 { doc /* uses the Camera Cleaning Log @S163 */ }
            perform action a8 { doc /* suppress confidence changes caused by lens contamination and service timing @S163 */ }
            perform action a9 { doc /* label detections as advisory @S181 */ }
            perform action a10 { doc /* present uncertainty @S204 */ }
            perform action a11 { doc /* complete documented functional testing against the approved mission scenarios @S227 */ }
        }
        part smokeColumnHeight : SmokeColumnHeight {
            perform action a0 { doc /* prevents a clear fixed-camera view @S062 */ }
        }
        part smokeColumns : SmokeColumns {
            perform action a0 { doc /* may reduce route visibility @S094 */ }
        }
        part smokeReport : SmokeReport {
            perform action a0 { doc /* warrants verification @S017 */ }
        }
        part sourceChannel : SourceChannel {
            perform action a0 { doc /* provides it @S085 */ }
        }
        part southLookoutCameraMast : SouthLookoutCameraMast {
            perform action a0 { doc /* provide fixed observation coverage over high-risk sectors @S004 */ }
            perform action a1 { doc /* covers the opposing viewshed @S027 */ }
            perform action a2 { doc /* provides overlapping observation where terrain breaks line of sight from the northern site @S027 */ }
            perform action a3 { doc /* provides an observation that may indicate a new ignition @S051 */ }
            perform action a4 { doc /* provide observation context that helps the Air Attack Supervisor assess whether smoke columns may reduce route visibility @S094 */ }
            perform action a5 { doc /* produces the Camera Cleaning Log as part of its maintenance reporting @S095 */ }
            perform action a6 { doc /* supplies a separate bearing track @S104 */ }
            perform action a7 { doc /* report heartbeat, temperature, storage, and pointing-status telemetry @S182 */ }
            perform action a8 { doc /* meet agreed availability, timing, and data-quality thresholds during the readiness window @S228 */ }
        }
        part sparePower : SparePower;
        part spreadModel : SpreadModel {
            perform action a0 { doc /* used by the spread model @S113 */ }
        }
        part staffedOperationsPortal : StaffedOperationsPortal;
        part stagedReleaseProcess : StagedReleaseProcess {
            perform action a0 { doc /* follows completion of seasonal readiness activities @S224 */ }
        }
        part stateWildlandFireResources : StateWildlandFireResources;
        part statusReporting : StatusReporting {
            perform action a0 { doc /* remain stable under expected seasonal conditions @S229 */ }
        }
        part steepSlopeExposure : SteepSlopeExposure;
        part structures : Structures;
        part supervisedConsolePractice : SupervisedConsolePractice;
        part supervisorDecision : SupervisorDecision;
        part supervisors : Supervisors {
            perform action a0 { doc /* can see both the most likely path and the practical planning margin @S118 */ }
        }
        part suppressionPlanning : SuppressionPlanning {
            perform action a0 { doc /* begins @S127 */ }
        }
        part suppressionSupport : SuppressionSupport {
            perform action a0 { doc /* begins after incident staff need coordinated information for resource movement, aviation planning, field safety, and ongoing assessment of fire behavior @S022 */ }
        }
        part suspectedIgnition : SuspectedIgnition {
            perform action a0 { doc /* remains in triage @S068 */ }
            exhibit state modes {
                state s0 { doc /* triage @S068 */ }
            }
        }
        part tabletopExercises : TabletopExercises {
            perform action a0 { doc /* test detection triage, command notification, airspace coordination, tanker-base coordination, crew deployment, and public-agency liaison actions @S215 */ }
        }
        part talonAirTankerDispatchConsole : TalonAirTankerDispatchConsole {
            perform action a0 { doc /* supports the Air Attack Supervisor and Tanker Base Manager @S047 */ }
            perform action a1 { doc /* presenting aircraft coordination data, loading status, and mission notes relevant to suppression support @S047 */ }
            perform action a2 { doc /* maintained by the Talon Air Tanker Dispatch Console @S080 */ }
            perform action a3 { doc /* provides the aviation status view used by the Tanker Base Manager to sequence retardant aircraft availability @S081 */ }
            perform action a4 { doc /* maintains a planning view of tanker availability, estimated time to target, base turnaround time, and assigned incident priority @S137 */ }
            perform action a5 { doc /* prevent a dispatch plan from being released when required aviation approvals, airspace status, or tanker readiness fields are incomplete @S138 */ }
            perform action a6 { doc /* produces the Runway Release Note @S140 */ }
            perform action a7 { doc /* sends the Suppression Drop Receipt @S148 */ }
            perform action a8 { doc /* pass integration checks @S230 */ }
        }
        part tanker : Tanker {
            perform action a0 { doc /* can accept an assignment @S082 */ }
        }
        part tankerBaseManager : TankerBaseManager {
            perform action a0 { doc /* uses the system to understand mission demand, loading status, and operational tempo associated with the Talon Air Tanker Dispatch Console, East Retardant Loading Pump, and West Retardant Loading Pump @S014 */ }
            perform action a1 { doc /* understand mission demand, loading status, and operational tempo associated with the Talon Air Tanker Dispatch Console, East Retardant Loading Pump, and West Retardant Loading Pump @S014 */ }
            perform action a2 { doc /* used by the Tanker Base Manager to sequence retardant aircraft availability @S081 */ }
            perform action a3 { doc /* sequence retardant aircraft availability @S081 */ }
            perform action a4 { doc /* coordinates pump readiness for the East Retardant Loading Pump and the West Retardant Loading Pump @S082 */ }
            perform action a5 { doc /* confirming that a tanker can accept an assignment @S082 */ }
            perform action a6 { doc /* uses the batch slip @S141 */ }
            perform action a7 { doc /* confirm that the loading record matches the aircraft assignment and planned retardant quantity @S141 */ }
            perform action a8 { doc /* resolves discrepancies in loading status @S144 */ }
            perform action a9 { doc /* receive only the permissions required for their operational responsibilities @S187 */ }
            perform action a10 { doc /* receive practical instruction on status entry, loading coordination, and abnormal-condition reporting for the East Retardant Loading Pump and the West Retardant Loading Pump @S207 */ }
            perform action a11 { doc /* use the Runway Release Note during acceptance review @S233 */ }
            perform action a12 { doc /* verify that tanker-base operating constraints are documented before seasonal activation @S233 */ }
        }
        part taskExecution : TaskExecution {
            perform action a0 { doc /* remain stable under expected seasonal conditions @S229 */ }
        }
        part terrain : Terrain {
            perform action a0 { doc /* blocks line of sight @S005 */ }
            perform action a1 { doc /* breaks line of sight from the northern site @S027 */ }
            perform action a2 { doc /* prevents a clear fixed-camera view @S062 */ }
        }
        part terrainShadowConditions : TerrainShadowConditions {
            perform action a0 { doc /* could otherwise inflate a smoke confidence score @S056 */ }
        }
        part thermalCues : ThermalCues {
            perform action a0 { doc /* persist across sequential frames @S055 */ }
            perform action a1 { doc /* align with a visible smoke indication @S055 */ }
        }
        part timeFromAutomatedDetectionToHumanReview : TimeFromAutomatedDetectionToHumanReview;
        part timeFromReviewToCommandNotification : TimeFromReviewToCommandNotification;
        part timeIndexedWeatherUpdate : TimeIndexedWeatherUpdate {
            perform action a0 { doc /* marks significant forecast changes @S114 */ }
            perform action a1 { doc /* identifies which map products require recomputation @S114 */ }
        }
        part timeToResourceAssignment : TimeToResourceAssignment;
        part trainingForTheCalderaWildfireDetectionAndSuppressionSupportSystem : TrainingForTheCalderaWildfireDetectionAndSuppressionSupportSystem;
        part trainingProgram : TrainingProgram;
        part unstableSnags : UnstableSnags;
        part updatedContactRosters : UpdatedContactRosters;
        part users : Users {
            perform action a0 { doc /* can distinguish current guidance from archived assessments @S125 */ }
        }
        part utilityConflicts : UtilityConflicts;
        part utilityCorridors : UtilityCorridors;
        part vHFRadioGatewayRepeater : VHFRadioGatewayRepeater {
            perform action a0 { doc /* supports continuity between digital coordination and field radio practices @S008 */ }
            perform action a1 { doc /* provides a monitored bridge between selected radio traffic and operator workstations @S044 */ }
            perform action a2 { doc /* supports voice coordination @S064 */ }
            perform action a3 { doc /* bridges command, air-to-ground, and county liaison talk paths @S084 */ }
            perform action a4 { doc /* provides an operational fallback for relaying approved aviation instructions when data connectivity is degraded @S145 */ }
            perform action a5 { doc /* relaying approved aviation instructions @S145 */ }
            perform action a6 { doc /* mirrors priority assignment summaries for crews that cannot maintain a data session in canyon or timbered terrain @S171 */ }
            perform action a7 { doc /* queue outbound voice-to-data acknowledgments for at least fifteen minutes during backhaul loss @S193 */ }
            perform action a8 { doc /* forward them @S193 */ }
        }
        part vHFRadioGatewayRepeaterFailureModes : VHFRadioGatewayRepeaterFailureModes;
        part vehicleExhaust : VehicleExhaust {
            perform action a0 { doc /* can produce similar signatures @S057 */ }
        }
        part visibilityChanges : VisibilityChanges;
        part waiverToAcceptanceCriteria : WaiverToAcceptanceCriteria {
            perform action a0 { doc /* identify the operational impact, compensating procedure, expiration date, and accountable owner @S237 */ }
        }
        part waterSources : WaterSources;
        part weather : Weather {
            perform action a0 { doc /* permit flight operations @S107 */ }
        }
        part weatherDerivedExposureFlags : WeatherDerivedExposureFlags {
            perform action a0 { doc /* support staging decisions near ridgelines and drainages @S166 */ }
        }
        part weatherRatedEnclosures : WeatherRatedEnclosures;
        part weatherTraining : WeatherTraining {
            perform action a0 { doc /* explain how the MesoWest Weather Fusion Node supports situational awareness and how operators should treat weather inputs when local observations conflict with displayed values @S212 */ }
        }
        part westRetardantLoadingPump : WestRetardantLoadingPump {
            perform action a0 { doc /* report equipment state, flow readiness, and out-of-service conditions @S142 */ }
            perform action a1 { doc /* support base capacity estimates @S142 */ }
            perform action a2 { doc /* pass integration checks @S230 */ }
            exhibit state modes {
                state s0 { doc /* operational availability @S195 */ }
            }
        }
        part wildfireThreatEnvironment : WildfireThreatEnvironment {
            perform action a0 { doc /* shaped by dry fuels, steep terrain, variable winds, lightning, human-caused ignitions, and expanding wildland-urban interface exposure @S001 */ }
        }
        flow f0 of IncidentInformationItem from calderaIncidentCommandPortal to authorizedWildfirePersonnel { doc /* @S003 */ }
        flow f1 of RecommendedActionsItem from calderaIncidentCommandPortal to authorizedWildfirePersonnel { doc /* @S003 */ }
        flow f2 of OperationalStatusItem from calderaIncidentCommandPortal to authorizedWildfirePersonnel { doc /* @S003 */ }
        flow f3 of TaskStatusItem from droneTaskingService to dronePilotOperator { doc /* @S035 */ }
        flow f4 of ConfidenceValuesItem from smokeClassifierModule to broaderAnalyticsWorkflow { doc /* @S039 */ }
        flow f5 of CameraViewsDetectionHistoryWeatherContextMapLayersAndStatusTransitionsItem from calderaIncidentCommandPortal to dutyDetectionOfficer { doc /* @S046 */ }
        flow f6 of CameraViewsDetectionHistoryWeatherContextMapLayersAndStatusTransitionsItem from calderaIncidentCommandPortal to countyEmergencyLiaison { doc /* @S046 */ }
        flow f7 of CameraViewsDetectionHistoryWeatherContextMapLayersAndStatusTransitionsItem from calderaIncidentCommandPortal to commandStaff { doc /* @S046 */ }
        flow f8 of WeatherContextItem from mesoWestWeatherFusionNode to calderaIncidentCommandPortal { doc /* @S046 */ }
        flow f9 of AircraftCoordinationDataItem from talonAirTankerDispatchConsole to airAttackSupervisor { doc /* @S047 */ }
        flow f10 of LoadingStatusItem from talonAirTankerDispatchConsole to airAttackSupervisor { doc /* @S047 */ }
        flow f11 of MissionNotesItem from talonAirTankerDispatchConsole to airAttackSupervisor { doc /* @S047 */ }
        flow f12 of AircraftCoordinationDataItem from talonAirTankerDispatchConsole to tankerBaseManager { doc /* @S047 */ }
        flow f13 of LoadingStatusItem from talonAirTankerDispatchConsole to tankerBaseManager { doc /* @S047 */ }
        flow f14 of MissionNotesItem from talonAirTankerDispatchConsole to tankerBaseManager { doc /* @S047 */ }
        flow f15 of AssignedIncidentContextItem from crewlineMobileTablet to helitackCrewLeader { doc /* @S049 */ }
        flow f16 of MapReferencesItem from crewlineMobileTablet to helitackCrewLeader { doc /* @S049 */ }
        flow f17 of UpdatesItem from crewlineMobileTablet to helitackCrewLeader { doc /* @S049 */ }
        flow f18 of ObservationContextItem from northLookoutCameraMast to sentinelFirelineAnalyticsEngine { doc /* @S053 */ }
        flow f19 of ObservationContextItem from southLookoutCameraMast to sentinelFirelineAnalyticsEngine { doc /* @S053 */ }
        flow f20 of ObservationContextItem from horizonRidgeDroneDock to sentinelFirelineAnalyticsEngine { doc /* @S053 */ }
        flow f21 of ConfirmedIncidentContextItem from commandWorkflow to crewlineMobileTabletUsers { doc /* @S072 */ }
        flow f22 of AviationStatusViewItem from talonAirTankerDispatchConsole to tankerBaseManager { doc /* @S081 */ }
        flow f23 of OriginalSpeakerIdentityItem from sourceChannel to aviationSupervisors { doc /* @S085 */ }
        flow f24 of CurrentFirePerimeterIntelligenceItem from sentinelFirelineAnalyticsEngine to airAttackSupervisor { doc /* @S092 */ }
        flow f25 of WindAndVisibilityContextItem from mesoWestWeatherFusionNode to aviationSupervisors { doc /* @S093 */ }
        flow f26 of ObservationContextItem from northLookoutCameraMast to airAttackSupervisor { doc /* @S094 */ }
        flow f27 of ObservationContextItem from southLookoutCameraMast to airAttackSupervisor { doc /* @S094 */ }
        flow f28 of CrewAcknowledgementsItem from helitackCrewLeader to calderaIncidentCommandPortal { doc /* @S098 */ }
        flow f29 of CrewAcknowledgementsItem from calderaIncidentCommandPortal to airAttackSupervisor { doc /* @S098 */ }
        flow f30 of SeparateBearingTrackItem from southLookoutCameraMast to mappingWorkflow { doc /* @S104 */ }
        flow f31 of ThermalSpotSnippetItem from northLookoutCameraMast to dutyDetectionOfficer { doc /* @S106 */ }
        flow f32 of AutomatedClassificationItem from smokeClassifierModule to dutyDetectionOfficer { doc /* @S106 */ }
        flow f33 of BatterySwapTicketItem from maintenanceController to dronePilotOperator { doc /* @S109 */ }
        flow f34 of WindItem from mesoWestWeatherFusionNode to spreadModel { doc /* @S113 */ }
        flow f35 of HumidityItem from mesoWestWeatherFusionNode to spreadModel { doc /* @S113 */ }
        flow f36 of TemperatureItem from mesoWestWeatherFusionNode to spreadModel { doc /* @S113 */ }
        flow f37 of StabilityFieldsItem from mesoWestWeatherFusionNode to spreadModel { doc /* @S113 */ }
        flow f38 of WeatherFieldsItem from mesoWestWeatherFusionNode to fireBehaviorModel { doc /* @S117 */ }
        flow f39 of WindShiftBulletinItem from mesoWestWeatherFusionNode to airAttackSupervisor { doc /* @S136 */ }
        flow f40 of RetardantBatchSlipItem from eastRetardantLoadingPump to tankerBaseManager { doc /* @S141 */ }
        flow f41 of ApprovedSuppressionObjectivesItem from crewlineMobileTablet to crews { doc /* @S146 */ }
        flow f42 of AircraftCautionAreasItem from crewlineMobileTablet to crews { doc /* @S146 */ }
        flow f43 of CurrentAssignmentNotesItem from crewlineMobileTablet to crews { doc /* @S146 */ }
        flow f44 of AssignmentsItem from calderaWildfireDetectionAndSuppressionSupportSystem to helitackCrews { doc /* @S152 */ }
        flow f45 of StagingInformationItem from calderaWildfireDetectionAndSuppressionSupportSystem to helitackCrews { doc /* @S152 */ }
        flow f46 of HazardsItem from calderaWildfireDetectionAndSuppressionSupportSystem to helitackCrews { doc /* @S152 */ }
        flow f47 of UpdatedIntelligenceItem from calderaWildfireDetectionAndSuppressionSupportSystem to helitackCrews { doc /* @S152 */ }
        flow f48 of AssignmentsItem from calderaWildfireDetectionAndSuppressionSupportSystem to groundCrews { doc /* @S152 */ }
        flow f49 of StagingInformationItem from calderaWildfireDetectionAndSuppressionSupportSystem to groundCrews { doc /* @S152 */ }
        flow f50 of HazardsItem from calderaWildfireDetectionAndSuppressionSupportSystem to groundCrews { doc /* @S152 */ }
        flow f51 of UpdatedIntelligenceItem from calderaWildfireDetectionAndSuppressionSupportSystem to groundCrews { doc /* @S152 */ }
        flow f52 of CurrentDivisionAssignmentItem from crewlineMobileTablet to loggedInCrew { doc /* @S155 */ }
        flow f53 of RouteGuidanceItem from crewlineMobileTablet to loggedInCrew { doc /* @S155 */ }
        flow f54 of RallyLocationItem from crewlineMobileTablet to loggedInCrew { doc /* @S155 */ }
        flow f55 of AssignedCommunicationsChannelItem from crewlineMobileTablet to loggedInCrew { doc /* @S155 */ }
        flow f56 of RidgeShadowMaskItem from smokeClassifierModule to sentinelFirelineAnalyticsEngine { doc /* @S162 */ }
        flow f57 of CameraCleaningLogItem from southLookoutCameraMast to smokeClassifierModule { doc /* @S163 */ }
        flow f58 of ReconnaissanceTaskStatusItem from droneTaskingService to groundTeams { doc /* @S168 */ }
        flow f59 of PriorityAssignmentSummariesItem from vHFRadioGatewayRepeater to crews { doc /* @S171 */ }
        flow f60 of DetectionsItem from sentinelFirelineAnalyticsEngine to dutyDetectionOfficer { doc /* @S202 */ }
        flow f61 of PublicSafetyInformationItem from calderaIncidentCommandPortal to countyEmergencyLiaison { doc /* @S210 */ }
        flow f62 of RunwayReleaseNoteItem from talonAirTankerDispatchConsole to tankerBaseManager { doc /* @S233 */ }
        flow f63 of SuppressionDropReceiptItem from talonAirTankerDispatchConsole to countyEmergencyLiaison { doc /* @S234 */ }
    }
    requirement def R0 { doc /* smoke columns, flame growth, and visibility changes must be assessed quickly @S004 */ subject s : SmokeColumns; }
    requirement def R1 { doc /* smoke columns, flame growth, and visibility changes must be assessed quickly @S004 */ subject s : FlameGrowth; }
    requirement def R2 { doc /* smoke columns, flame growth, and visibility changes must be assessed quickly @S004 */ subject s : VisibilityChanges; }
    requirement def R3 { doc /* a suspected ignition should be escalated @S011 */ subject s : SuspectedIgnition; }
    requirement def R4 { doc /* whether an ignition should be treated as confirmed @S017 */ subject s : Ignition; }
    requirement def R5 { doc /* whether operations should pause for safety reasons @S018 */ subject s : Operations; }
    requirement def R6 { doc /* Confirmation requires at least one persistent smoke indication or thermal cue, plus either independent sensor corroboration, field report corroboration, or a direct human visual judgment recorded by an authorized reviewer. @S067 */ subject s : Confirmation; }
    requirement def R7 { doc /* The Drone Tasking Service shall not issue a launch task that conflicts with an active aviation lane maintained by the Talon Air Tanker Dispatch Console. @S080 */ subject s : DroneTaskingService; }
    requirement def R8 { doc /* Radio bridging shall preserve the original speaker identity when the source channel provides it, because aviation supervisors use that identity to validate tasking and hazard reports. @S085 */ subject s : RadioBridging; }
    requirement def R9 { doc /* If a bridge path fails, the Caldera Incident Command Portal marks the affected radio route as impaired and requires manual acknowledgement by the Duty Detection Officer. @S086 */ subject s : DutyDetectionOfficer; }
    requirement def R10 { doc /* Orion must verify that the impaired route has an alternate contact method before any new aviation coordination message is accepted. @S087 */ subject s : DutyDetectionOfficer; }
    requirement def R11 { doc /* County liaison procedures require that jurisdictional constraints be entered in the Caldera Incident Command Portal before the Drone Pilot Operator receives a route briefing. @S090 */ subject s : CountyLiaisonProcedures; }
    requirement def R12 { doc /* When inputs conflict, the common operating picture shows the conflict explicitly and requires review before the affected recommendation is promoted for command use. @S126 */ subject s : CommonOperatingPicture; }
    requirement def R13 { doc /* Kestrel is required to report launch readiness, aircraft health, and recovery availability before a reconnaissance task can be released. @S131 */ subject s : HorizonRidgeDroneDock; }
    requirement def R14 { doc /* Marigold must prevent a dispatch plan from being released when required aviation approvals, airspace status, or tanker readiness fields are incomplete. @S138 */ subject s : TalonAirTankerDispatchConsole; }
    requirement def R15 { doc /* a supervisor decision is still required before aircraft are committed @S143 */ subject s : SupervisorDecision; }
    requirement def R16 { doc /* When the system enters the Airspace Restricted State, helitack assignments show the restriction boundary and require confirmation before aircraft-dependent movement is planned. @S167 */ subject s : HelitackAssignments; }
    requirement def R17 { doc /* During prolonged wildfire operations, the system shall favor continuity of command decisions over full automation when communications, power, or sensor coverage is impaired. @S176 */ subject s : CalderaWildfireDetectionAndSuppressionSupportSystem; }
    requirement def R18 { doc /* The Sentinel Fireline Analytics Engine shall continue using the last approved model configuration after a repository outage and shall reject unversioned rules or unsigned analytic packages. @S180 */ subject s : SentinelFirelineAnalyticsEngine; }
    requirement def R19 { doc /* The Smoke Classifier Module shall label detections as advisory when either camera mast is unavailable or when image quality falls below the validated threshold. @S181 */ subject s : SmokeClassifierModule; }
    requirement def R20 { doc /* The North Lookout Camera Mast and the South Lookout Camera Mast shall report heartbeat, temperature, storage, and pointing-status telemetry so that maintenance staff can distinguish sensor failure from environmental obscuration. @S182 */ subject s : NorthLookoutCameraMast; }
    requirement def R21 { doc /* The North Lookout Camera Mast and the South Lookout Camera Mast shall report heartbeat, temperature, storage, and pointing-status telemetry so that maintenance staff can distinguish sensor failure from environmental obscuration. @S182 */ subject s : SouthLookoutCameraMast; }
    requirement def R22 { doc /* The MesoWest Weather Fusion Node shall retain a local weather cache sufficient to support near-term fire behavior review when upstream feeds are intermittent. @S183 */ subject s : MesoWestWeatherFusionNode; }
    requirement def R23 { doc /* Crewline Mobile Tablet clients shall queue field updates locally, encrypt the queue at rest, and reconcile conflicts by preserving the original author, device time, and server acceptance time. @S184 */ subject s : CrewlineMobileTabletClients; }
    requirement def R24 { doc /* All interactive access to the Caldera Incident Command Portal requires named accounts, role-based authorization, and multifactor authentication when the authentication service is reachable. @S185 */ subject s : CalderaIncidentCommandPortal; }
    requirement def R25 { doc /* When the authentication service is unreachable, emergency access uses pre-issued signed credentials that expire automatically and require supervisor review after restoration. @S186 */ subject s : PreIssuedSignedCredentials; }
    requirement def R26 { doc /* Administrative privileges for production configuration changes require separate approval from operational command roles and are not granted through field user accounts. @S188 */ subject s : AdministrativePrivileges; }
    requirement def R27 { doc /* Security-relevant events, including failed logons, role changes, queued update releases, model changes, and maintenance overrides, shall be written to an append-only audit store. @S189 */ subject s : SecurityRelevantEvents; }
    requirement def R28 { doc /* Audit records shall include synchronized time, user identity, device identity, source network, affected record, and outcome so that incident reconstruction remains possible after the event. @S190 */ subject s : AuditRecords; }
    requirement def R29 { doc /* If central audit storage is unavailable, each field component shall buffer signed audit records locally and forward them without modification when connectivity returns. @S191 */ subject s : FieldComponent; }
    requirement def R30 { doc /* Badger shall queue outbound voice-to-data acknowledgments for at least fifteen minutes during backhaul loss and forward them when the link is restored. @S193 */ subject s : VHFRadioGatewayRepeater; }
    requirement def R31 { doc /* East Retardant Loading Pump shall enter a metered recirculation mode when pressure variance exceeds the calibrated maintenance limit. @S194 */ subject s : EastRetardantLoadingPump; }
    requirement def R32 { doc /* The West Retardant Loading Pump shall be inspected at shift change for hose wear, valve position, controller alarms, and leakage before it is returned to operational availability. @S195 */ subject s : WestRetardantLoadingPump; }
    requirement def R33 { doc /* Maintenance actions on field equipment shall be recorded with technician identity, time, observed condition, corrective action, and verification result before the equipment status is changed. @S196 */ subject s : MaintenanceActions; }
    requirement def R34 { doc /* Operational records that support command decisions and safety reviews shall be retained for the incident record period defined by agency policy, while high-volume raw sensor data may follow a shorter approved retention schedule. @S197 */ subject s : OperationalRecords; }
    requirement def R35 { doc /* The system shall protect retained data with encryption at rest, controlled export procedures, and deletion workflows that require documented authorization. @S198 */ subject s : CalderaWildfireDetectionAndSuppressionSupportSystem; }
    requirement def R36 { doc /* deletion workflows that require documented authorization @S198 */ subject s : DeletionWorkflows; }
    requirement def R37 { doc /* For incidents lasting multiple operational periods, spare power, replacement network equipment, field cleaning supplies, and documented recovery procedures shall be staged so that no single equipment fault stops detection or suppression-support operations. @S199 */ subject s : SparePower; }
    requirement def R38 { doc /* For incidents lasting multiple operational periods, spare power, replacement network equipment, field cleaning supplies, and documented recovery procedures shall be staged so that no single equipment fault stops detection or suppression-support operations. @S199 */ subject s : ReplacementNetworkEquipment; }
    requirement def R39 { doc /* For incidents lasting multiple operational periods, spare power, replacement network equipment, field cleaning supplies, and documented recovery procedures shall be staged so that no single equipment fault stops detection or suppression-support operations. @S199 */ subject s : FieldCleaningSupplies; }
    requirement def R40 { doc /* For incidents lasting multiple operational periods, spare power, replacement network equipment, field cleaning supplies, and documented recovery procedures shall be staged so that no single equipment fault stops detection or suppression-support operations. @S199 */ subject s : DocumentedRecoveryProcedures; }
    requirement def R41 { doc /* Training for the Caldera Wildfire Detection and Suppression Support System shall be completed before each fire season and refreshed whenever operating procedures or field configurations change. @S200 */ subject s : TrainingForTheCalderaWildfireDetectionAndSuppressionSupportSystem; }
    requirement def R42 { doc /* The training program shall be role based so that each participant practices the decisions, system functions, communications, and safety constraints that apply to the assigned position. @S201 */ subject s : TrainingProgram; }
    requirement def R43 { doc /* The Duty Detection Officer shall be trained to operate the Caldera Incident Command Portal, review detections, validate confidence indicators, and escalate suspected ignitions according to the approved incident workflow. @S202 */ subject s : DutyDetectionOfficer; }
    requirement def R44 { doc /* Camera familiarization shall cover the North Lookout Camera Mast and the South Lookout Camera Mast, including normal image behavior, degraded visibility conditions, routine inspection cues, and reporting of equipment faults. @S203 */ subject s : CameraFamiliarization; }
    requirement def R45 { doc /* The Duty Detection Officer shall also learn how the Sentinel Fireline Analytics Engine and the Smoke Classifier Module present uncertainty so that human confirmation remains part of every operational decision. @S204 */ subject s : DutyDetectionOfficer; }
    requirement def R46 { doc /* The Drone Pilot Operator shall be trained on Horizon Ridge Drone Dock procedures, Drone Tasking Service mission controls, safe launch checks, recovery actions, and loss-of-link coordination. @S205 */ subject s : DronePilotOperator; }
    requirement def R47 { doc /* The Air Attack Supervisor shall be trained to interpret system status during aerial operations and to coordinate with the Talon Air Tanker Dispatch Console without bypassing airspace safety requirements. @S206 */ subject s : AirAttackSupervisor; }
    requirement def R48 { doc /* The Tanker Base Manager shall receive practical instruction on status entry, loading coordination, and abnormal-condition reporting for the East Retardant Loading Pump and the West Retardant Loading Pump. @S207 */ subject s : TankerBaseManager; }
    requirement def R49 { doc /* The Helitack Crew Leader shall be trained on use of the Crewline Mobile Tablet, field acknowledgments, location updates, and communication discipline during changing fire behavior. @S208 */ subject s : HelitackCrewLeader; }
    requirement def R50 { doc /* During field mobilization drills, the Helitack Crew Leader shall use the staging pin to confirm that the assigned crew is positioned at the exercise location. @S209 */ subject s : HelitackCrewLeader; }
    requirement def R51 { doc /* The County Emergency Liaison shall be trained to interpret public-safety information from the Caldera Incident Command Portal and to coordinate notifications with county procedures. @S210 */ subject s : CountyEmergencyLiaison; }
    requirement def R52 { doc /* All operational users shall receive communications training that includes VHF Radio Gateway Repeater failure modes, alternate contact paths, call signs, message brevity, and confirmation readbacks. @S211 */ subject s : OperationalUsers; }
    requirement def R53 { doc /* Weather training shall explain how the MesoWest Weather Fusion Node supports situational awareness and how operators should treat weather inputs when local observations conflict with displayed values. @S212 */ subject s : WeatherTraining; }
    requirement def R54 { doc /* operators should treat weather inputs when local observations conflict with displayed values @S212 */ subject s : Operators; }
    requirement def R55 { doc /* Initial qualification shall include supervised console practice, scenario walkthroughs, and a documented check by an instructor who is authorized by the operations lead. @S213 */ subject s : InitialQualification; }
    requirement def R56 { doc /* Annual refresher training shall include changes to software screens, revised thresholds, updated contact rosters, seasonal hazard briefings, and lessons learned from prior incidents. @S214 */ subject s : AnnualRefresherTraining; }
    requirement def R57 { doc /* Tabletop exercises shall be conducted before the expected peak fire period and shall test detection triage, command notification, airspace coordination, tanker-base coordination, crew deployment, and public-agency liaison actions. @S215 */ subject s : TabletopExercises; }
    requirement def R58 { doc /* Live exercises shall be scheduled at least once per season when conditions permit and shall include field crews, aircraft coordination staff, drone operations staff, and command-center personnel. @S216 */ subject s : LiveExercises; }
    requirement def R59 { doc /* Exercise controllers shall inject realistic complications such as intermittent network service, obscured camera views, delayed field confirmation, resource conflicts, and conflicting reports from external observers. @S217 */ subject s : ExerciseControllers; }
    requirement def R60 { doc /* Performance measures shall include time from automated detection to human review, time from review to command notification, time to resource assignment, communication completion rate, and accuracy of incident status updates. @S218 */ subject s : PerformanceMeasures; }
    requirement def R61 { doc /* Detection quality shall be evaluated using confirmed events, benign smoke sources, weather-related artifacts, and operator notes so that both missed detections and false alarms are visible to program management. @S219 */ subject s : DetectionQuality; }
    requirement def R62 { doc /* Every false-alarm review shall identify the apparent cause, affected sensors or analytic outputs, operator actions, dispatch consequences, and any recommended tuning or training change. @S220 */ subject s : FalseAlarmReview; }
    requirement def R63 { doc /* The review board shall include operations, aviation, field crew, maintenance, and county liaison representatives when the event affected more than one operational function. @S221 */ subject s : ReviewBoard; }
    requirement def R64 { doc /* Seasonal readiness shall require each active user to demonstrate current proficiency, complete required safety briefings, and acknowledge the current operating procedures before receiving operational access. @S222 */ subject s : SeasonalReadiness; }
    requirement def R65 { doc /* Personnel who do not meet proficiency requirements shall complete remedial training and a repeat evaluation before performing unsupervised duties in the Caldera Wildfire Detection and Suppression Support System. @S223 */ subject s : Personnel; }
    requirement def R66 { doc /* Deployment governance for the Caldera Wildfire Detection and Suppression Support System shall be managed as a staged release process that follows completion of seasonal readiness activities. @S224 */ subject s : DeploymentGovernanceForTheCalderaWildfireDetectionAndSuppressionSupportSystem; }
    requirement def R67 { doc /* The deployment governance board shall include operational leadership, maintenance representation, information security representation, and designated representatives for detection, aviation, ground crew, and county coordination functions. @S225 */ subject s : DeploymentGovernanceBoard; }
    requirement def R68 { doc /* The board shall approve each seasonal rollout only after reviewing residual risk, staffing readiness, configuration baselines, and open corrective actions from the prior operating period. @S226 */ subject s : DeploymentGovernanceBoard; }
    requirement def R69 { doc /* A release candidate shall not enter operational service until the Caldera Incident Command Portal, Sentinel Fireline Analytics Engine, and Smoke Classifier Module complete documented functional testing against the approved mission scenarios. @S227 */ subject s : ReleaseCandidate; }
    requirement def R70 { doc /* Acceptance criteria shall require the North Lookout Camera Mast, South Lookout Camera Mast, and MesoWest Weather Fusion Node to meet agreed availability, timing, and data-quality thresholds during the readiness window. @S228 */ subject s : AcceptanceCriteria; }
    requirement def R71 { doc /* The Drone Tasking Service and Horizon Ridge Drone Dock shall be accepted only after controlled field validation shows that task execution, abort behavior, and status reporting remain stable under expected seasonal conditions. @S229 */ subject s : DroneTaskingService; }
    requirement def R72 { doc /* The Drone Tasking Service and Horizon Ridge Drone Dock shall be accepted only after controlled field validation shows that task execution, abort behavior, and status reporting remain stable under expected seasonal conditions. @S229 */ subject s : HorizonRidgeDroneDock; }
    requirement def R73 { doc /* The Talon Air Tanker Dispatch Console, East Retardant Loading Pump, and West Retardant Loading Pump shall pass integration checks that verify operator controls, fault handling, and audit capture before activation. @S230 */ subject s : TalonAirTankerDispatchConsole; }
    requirement def R74 { doc /* The Talon Air Tanker Dispatch Console, East Retardant Loading Pump, and West Retardant Loading Pump shall pass integration checks that verify operator controls, fault handling, and audit capture before activation. @S230 */ subject s : EastRetardantLoadingPump; }
    requirement def R75 { doc /* The Talon Air Tanker Dispatch Console, East Retardant Loading Pump, and West Retardant Loading Pump shall pass integration checks that verify operator controls, fault handling, and audit capture before activation. @S230 */ subject s : WestRetardantLoadingPump; }
    requirement def R76 { doc /* The VHF Radio Gateway Repeater and Crewline Mobile Tablet shall be validated for coverage, message persistence, authentication behavior, and degraded-network operation before release approval. @S231 */ subject s : VHFRadioGatewayRepeater; }
    requirement def R77 { doc /* The VHF Radio Gateway Repeater and Crewline Mobile Tablet shall be validated for coverage, message persistence, authentication behavior, and degraded-network operation before release approval. @S231 */ subject s : CrewlineMobileTablet; }
    requirement def R78 { doc /* Redtail shall confirm that deployment readiness evidence is sufficient before air operations functionality is enabled for the season. @S232 */ subject s : AirAttackSupervisor; }
    requirement def R79 { doc /* The Tanker Base Manager shall use the Runway Release Note during acceptance review to verify that tanker-base operating constraints are documented before seasonal activation. @S233 */ subject s : TankerBaseManager; }
    requirement def R80 { doc /* The County Emergency Liaison shall use the Suppression Drop Receipt during post-incident reconciliation to verify that reported suppression activity can be traced to county situation reporting. @S234 */ subject s : CountyEmergencyLiaison; }
    requirement def R81 { doc /* Acceptance of the Confirmed Ignition State workflow shall require traceable evidence that operator acknowledgement, escalation timing, and command visibility meet the approved concept of operations. @S235 */ subject s : ConfirmedIgnitionStateWorkflow; }
    requirement def R82 { doc /* Acceptance of the Airspace Restricted State workflow shall require evidence that operational users can recognize restrictions, apply required controls, and recover normal coordination when restrictions are lifted. @S236 */ subject s : AirspaceRestrictedStateWorkflow; }
    requirement def R83 { doc /* Any waiver to acceptance criteria shall identify the operational impact, compensating procedure, expiration date, and accountable owner before the board may authorize limited use. @S237 */ subject s : WaiverToAcceptanceCriteria; }
    requirement def R84 { doc /* After-action reviews shall be held after major incidents, readiness exercises, significant false alarms, missed detections, and any event that exposes a gap in operational coordination. @S238 */ subject s : AfterActionReviews; }
    requirement def R85 { doc /* Each after-action review shall reconstruct the timeline from system logs, user accounts, communications records, and maintenance notes without assigning blame to individual operators. @S239 */ subject s : AfterActionReview; }
    requirement def R86 { doc /* Review facilitators shall document what was expected to happen, what actually happened, why differences occurred, and which corrective actions are necessary before the next readiness cycle. @S240 */ subject s : ReviewFacilitators; }
    requirement def R87 { doc /* Corrective actions shall be entered into a controlled improvement backlog with assigned ownership, target completion dates, verification methods, and linkage to the originating event. @S241 */ subject s : CorrectiveActions; }
    requirement def R88 { doc /* Data stewardship shall define retention, access control, quality review, and disposition rules for operational records, sensor data, model outputs, configuration records, and user activity records. @S242 */ subject s : DataStewardship; }
    requirement def R89 { doc /* Operational data used for model evaluation shall be protected from unauthorized alteration @S243 */ subject s : OperationalData; }
    requirement def R90 { doc /* Operational data used for model evaluation shall preserve enough context to support later engineering review and regulatory inquiry. @S243 */ subject s : OperationalData; }
    requirement def R91 { doc /* Configuration changes to field equipment shall be versioned, reviewed, and tested in a nonoperational environment before being promoted into the seasonal baseline. @S245 */ subject s : ConfigurationChanges; }
    requirement def R92 { doc /* At the end of each fire season, the governance board shall compare system performance, operational workload, maintenance burden, and user feedback against the acceptance criteria approved for that season. @S246 */ subject s : DeploymentGovernanceBoard; }
    requirement def R93 { doc /* The resulting improvement plan shall define which procedures, training materials, interfaces, algorithms, and support arrangements will be revised before the next seasonal readiness campaign begins. @S247 */ subject s : ImprovementPlan; }
}
