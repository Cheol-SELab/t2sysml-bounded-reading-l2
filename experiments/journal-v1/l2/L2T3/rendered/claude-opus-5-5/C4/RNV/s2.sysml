package L2Model {
    item def AircraftCoordinationDataLoadingStatusAndMissionNotesItem { doc /* @S047 */ }
    item def AssignedIncidentContextMapReferencesAndUpdatesItem { doc /* @S049 */ }
    item def AviationStatusViewItem { doc /* @S081 */ }
    item def ConfidenceValuesItem { doc /* @S039 */ }
    item def ConfirmedIncidentContextItem { doc /* @S072 */ }
    item def CrewAcknowledgementsItem { doc /* @S098 */ }
    item def CrewLocationReportItem { doc /* @S097 */ }
    item def FirePerimeterIntelligenceItem { doc /* @S092 */ }
    item def LoadingStatusItem { doc /* @S144 */ }
    item def MapProductsItem { doc /* @S123 */ }
    item def ObservationContextItem { doc /* @S053,S094 */ }
    item def OperationalPackageWithAviationConstraintsAndLandingZoneNotesItem { doc /* @S156 */ }
    item def PublicSafetyInformationItem { doc /* @S210 */ }
    item def RestrictionBasisItem { doc /* @S078 */ }
    item def RetardantBatchSlipItem { doc /* @S141 */ }
    item def SignedAuditRecordsItem { doc /* @S191 */ }
    item def SimplifiedViewItem { doc /* @S124 */ }
    item def SuppressionDropReceiptItem { doc /* @S234 */ }
    item def TheCameraCleaningLogItem { doc /* @S163 */ }
    item def TheCrewStagingPinItem { doc /* @S209 */ }
    item def TheRidgeShadowMaskItem { doc /* @S162 */ }
    item def TheRunwayReleaseNoteItem { doc /* @S233 */ }
    item def TheWindShiftBulletinItem { doc /* @S136 */ }
    item def TriageCaseItem { doc /* @S060 */ }
    item def UncertaintyItem { doc /* @S204 */ }
    item def VerificationTaskItem { doc /* @S062 */ }
    item def VideoItem { doc /* @S029 */ }
    item def WeatherInputsItem { doc /* @S038,S212 */ }
    item def WindHumidityTemperatureAndStabilityFieldsItem { doc /* @S113 */ }
    part def ActiveUser { doc /* @S222 */ }
    part def AdvisoryAnalyticsServices { doc /* @S025 */ }
    part def AfterActionReview { doc /* @S239 */ }
    part def AfterActionReviews { doc /* @S238 */ }
    part def AirAttackSupervisor { doc /* @S013,S047,S077,S079,S092,S094,S098,S123,S128,S136,S139,S153,S156,S187,S206,S232 */ }
    part def AirspaceRestrictedState { doc /* @S139,S236 */ }
    part def AnalyticsServices { doc /* @S040 */ }
    part def AppendOnlyAuditStore { doc /* @S189,S191 */ }
    part def Aspect { doc /* @S116 */ }
    part def AviationRepresentatives { doc /* @S221 */ }
    part def CalderaIncidentCommandPortal { doc /* @S003,S045,S046,S059,S060,S068,S069,S070,S072,S074,S076,S077,S078,S086,S090,S098,S119,S120,S123,S124,S127,S149,S154,S160,S177,S178,S185,S209,S210,S227 */ }
    part def CalderaWildfireDetectionAndSuppressionSupportSystem { doc /* @S001,S004,S012,S199,S200,S213,S214,S215,S216,S218,S219,S220,S224 */ }
    part def CameraFamiliarization { doc /* @S203 */ }
    part def ChargingInterfaces { doc /* @S033 */ }
    part def CommonOperatingPicture { doc /* @S126 */ }
    part def CommunicationsPaths { doc /* @S025 */ }
    part def ConfirmedIgnitionState { doc /* @S067,S235 */ }
    part def ControlledImprovementBacklog { doc /* @S241 */ }
    part def CountyEmergencyLiaison { doc /* @S010,S089,S124,S150,S174,S187,S210,S234 */ }
    part def CountyLiaisonRepresentatives { doc /* @S221 */ }
    part def CrewlineMobileTablet { doc /* @S016,S049,S072,S097,S146,S155,S156,S159,S172,S184,S231 */ }
    part def DataStewardship { doc /* @S242 */ }
    part def DeploymentGovernanceBoard { doc /* @S225,S226,S237,S246 */ }
    part def DesignatedRepresentativesForDetectionAviationGroundCrewAndCountyCoordinationFunctions { doc /* @S225 */ }
    part def DronePilotOperator { doc /* @S015,S036,S063,S079,S090,S109,S132,S170,S187,S205 */ }
    part def DroneTaskingService { doc /* @S005,S035,S062,S080,S108,S129,S168,S192,S229 */ }
    part def DutyDetectionOfficer { doc /* @S011,S012,S060,S061,S078,S086,S087,S106,S179,S202,S204 */ }
    part def EastRetardantLoadingPump { doc /* @S073,S141,S142,S194,S230 */ }
    part def EvacuationZones { doc /* @S116 */ }
    part def ExerciseControllers { doc /* @S217 */ }
    part def FieldComponent { doc /* @S191 */ }
    part def FieldCrewRepresentatives { doc /* @S221 */ }
    part def FieldEquipment { doc /* @S245 */ }
    part def FireBehaviorModel { doc /* @S113,S117 */ }
    part def FixedRidgeSensors { doc /* @S025 */ }
    part def Fuels { doc /* @S116 */ }
    part def GeospatialOverlays { doc /* @S116 */ }
    part def HelitackCrewLeader { doc /* @S015,S049,S097,S147,S156,S173,S187,S208,S209 */ }
    part def HorizonRidgeDroneDock { doc /* @S005,S033,S034,S051,S053,S062,S130,S131,S229 */ }
    part def ImprovementPlan { doc /* @S247 */ }
    part def InformationSecurityRepresentation { doc /* @S225 */ }
    part def JurisdictionBoundaries { doc /* @S116 */ }
    part def KnownCommunicationsCoverage { doc /* @S116 */ }
    part def LocalHealthMonitoring { doc /* @S033 */ }
    part def MaintenanceController { doc /* @S034 */ }
    part def MaintenanceRepresentation { doc /* @S225 */ }
    part def MaintenanceRepresentatives { doc /* @S221 */ }
    part def MapProducts { doc /* @S125 */ }
    part def MesoWestWeatherFusionNode { doc /* @S007,S038,S042,S043,S058,S093,S113,S114,S136,S166,S183,S212,S228 */ }
    part def NorthLookoutCameraMast { doc /* @S004,S026,S029,S030,S051,S053,S094,S103,S182,S228 */ }
    part def OperationalLeadership { doc /* @S225 */ }
    part def OperationalRecords { doc /* @S197 */ }
    part def OperationalUsers { doc /* @S211,S236 */ }
    part def OperationsLead { doc /* @S213 */ }
    part def OperationsNetwork { doc /* @S029 */ }
    part def OperationsRepresentatives { doc /* @S221 */ }
    part def Operators { doc /* @S212 */ }
    part def Personnel { doc /* @S223 */ }
    part def ReleaseCandidate { doc /* @S227 */ }
    part def ReviewBoard { doc /* @S221 */ }
    part def ReviewFacilitators { doc /* @S240 */ }
    part def Roads { doc /* @S116 */ }
    part def SecureNetworkTermination { doc /* @S033 */ }
    part def SentinelFirelineAnalyticsEngine { doc /* @S006,S038,S039,S053,S092,S096,S111,S134,S161,S162,S164,S180,S204,S227,S244 */ }
    part def Slope { doc /* @S116 */ }
    part def SmokeClassifierModule { doc /* @S006,S039,S056,S105,S162,S163,S181,S204,S227,S244 */ }
    part def SouthLookoutCameraMast { doc /* @S004,S027,S029,S051,S053,S094,S095,S104,S163,S182,S228 */ }
    part def StaffedOperationsPortal { doc /* @S025 */ }
    part def Structures { doc /* @S116 */ }
    part def System { doc /* @S019,S025,S046,S099,S101,S151,S167,S176,S198 */ }
    part def TalonAirTankerDispatchConsole { doc /* @S047,S080,S081,S137,S138,S140,S143,S144,S148,S230,S233,S234 */ }
    part def TankerBaseManager { doc /* @S014,S047,S081,S082,S141,S144,S187,S207,S233 */ }
    part def TrainingProgram { doc /* @S201 */ }
    part def VHFRadioGatewayRepeater { doc /* @S008,S044,S064,S084,S085,S145,S171,S193,S231 */ }
    part def Waiver { doc /* @S237 */ }
    part def WaterSources { doc /* @S116 */ }
    part def WeatherRatedEnclosures { doc /* @S033 */ }
    part def WestRetardantLoadingPump { doc /* @S142,S195,S230 */ }
    part system {
        part activeUser : ActiveUser {
            perform action a0 { doc /* demonstrate current proficiency @S222 */ }
            perform action a1 { doc /* complete required safety briefings @S222 */ }
            perform action a2 { doc /* acknowledge the current operating procedures @S222 */ }
            perform action a3 { doc /* receiving operational access @S222 */ }
        }
        part advisoryAnalyticsServices : AdvisoryAnalyticsServices;
        part afterActionReview : AfterActionReview {
            perform action a0 { doc /* reconstruct the timeline from system logs, user accounts, communications records, and maintenance notes @S239 */ }
        }
        part afterActionReviews : AfterActionReviews;
        part airAttackSupervisor : AirAttackSupervisor {
            perform action a0 { doc /* uses the system to understand fire location, smoke behavior, aircraft constraints, and resource priorities @S013 */ }
            perform action a1 { doc /* advising on aerial tactics @S013 */ }
            perform action a2 { doc /* confirms the active operating window @S077 */ }
            perform action a3 { doc /* deconflicting fixed-wing, rotary-wing, and uncrewed routes @S079 */ }
            perform action a4 { doc /* reviews each temporary restriction against current fire perimeter intelligence @S092 */ }
            perform action a5 { doc /* approving a release of air assets @S092 */ }
            perform action a6 { doc /* assess whether smoke columns may reduce route visibility @S094 */ }
            perform action a7 { doc /* verify that ground resources are clear @S098 */ }
            perform action a8 { doc /* authorizing flight activity @S098 */ }
            perform action a9 { doc /* receives map products @S123 */ }
            perform action a10 { doc /* reviews the promoted location, the confidence history, and the current airspace status @S128 */ }
            perform action a11 { doc /* authorizing reconnaissance or retardant planning @S128 */ }
            perform action a12 { doc /* uses the Wind Shift Bulletin to reassess aircraft sequencing, holding areas, and drop approach direction @S136 */ }
            perform action a13 { doc /* confirms that the planned route and working altitude are acceptable @S139 */ }
            perform action a14 { doc /* selects the operational intent in the Caldera Incident Command Portal @S153 */ }
            perform action a15 { doc /* Air Attack Supervisor approval @S156 */ }
            perform action a16 { doc /* receive only the permissions required for their operational responsibilities @S187 */ }
            perform action a17 { doc /* interpret system status during aerial operations @S206 */ }
            perform action a18 { doc /* coordinate with the Talon Air Tanker Dispatch Console @S206 */ }
            perform action a19 { doc /* confirm that deployment readiness evidence is sufficient @S232 */ }
        }
        part airspaceRestrictedState : AirspaceRestrictedState {
            perform action a0 { doc /* limits dispatch options @S139 */ }
        }
        part analyticsServices : AnalyticsServices {
            perform action a0 { doc /* retain event timing, source identifiers, model version information, and operator acknowledgments @S040 */ }
        }
        part appendOnlyAuditStore : AppendOnlyAuditStore;
        part aspect : Aspect;
        part aviationRepresentatives : AviationRepresentatives;
        part calderaIncidentCommandPortal : CalderaIncidentCommandPortal {
            perform action a0 { doc /* presenting incident information, recommended actions, and operational status @S003 */ }
            perform action a1 { doc /* is the primary operator interface for the Duty Detection Officer, County Emergency Liaison, and other command staff @S045 */ }
            perform action a2 { doc /* displays camera views, detection history, weather context, map layers, and status transitions @S046 */ }
            perform action a3 { doc /* opens a triage case for human review @S059 */ }
            perform action a4 { doc /* records the reason for each triage decision @S069 */ }
            perform action a5 { doc /* associate the incident with the Airspace Restricted State @S074 */ }
            perform action a6 { doc /* supports coordinated air and ground operations @S076 */ }
            perform action a7 { doc /* shows the Airspace Restricted State @S077 */ }
            perform action a8 { doc /* marks the affected radio route as impaired @S086 */ }
            perform action a9 { doc /* displays crew acknowledgements beside aviation tasks @S098 */ }
            perform action a10 { doc /* renders the current perimeter, projected spread, resource positions, and decision annotations into a common operating picture @S119 */ }
            perform action a11 { doc /* produces the Crew Staging Pin from the approved map layer @S120 */ }
            perform action a12 { doc /* assigns it an effective time, location accuracy, and incident identifier @S120 */ }
            perform action a13 { doc /* promotes an accepted fire location into the operational map @S127 */ }
            perform action a14 { doc /* marks it available for aviation review @S127 */ }
            perform action a15 { doc /* preserves each aviation decision with the approving supervisor, operational period, and reason for change @S149 */ }
            perform action a16 { doc /* records each assignment package with an objective, time validity, confirmation status, and required acknowledgments @S154 */ }
            perform action a17 { doc /* marks affected crew assignments for review before release @S160 */ }
            perform action a18 { doc /* marks all displayed information with the last synchronization time @S177 */ }
            perform action a19 { doc /* allows authorized users to review cached incident data and create queued updates @S178 */ }
            perform action a20 { doc /* prevents irreversible releases @S178 */ }
            perform action a21 { doc /* complete documented functional testing against the approved mission scenarios @S227 */ }
            exhibit state modes {
                state s0 { doc /* Airspace Restricted State @S074 */ }
                state s1 { doc /* Confirmed Ignition State @S070,S160 */ }
                state s2 { doc /* disconnected operating mode @S177 */ }
                state s3 { doc /* extended attack @S149 */ }
                state s4 { doc /* triage @S068 */ }
            }
        }
        part calderaWildfireDetectionAndSuppressionSupportSystem : CalderaWildfireDetectionAndSuppressionSupportSystem {
            perform action a0 { doc /* operates in a wildfire threat environment @S001 */ }
            exhibit state modes {
                state s0 { doc /* Confirmed Ignition State @S012 */ }
            }
        }
        part cameraFamiliarization : CameraFamiliarization;
        part chargingInterfaces : ChargingInterfaces;
        part commonOperatingPicture : CommonOperatingPicture {
            perform action a0 { doc /* shows the conflict explicitly @S126 */ }
        }
        part communicationsPaths : CommunicationsPaths;
        part confirmedIgnitionState : ConfirmedIgnitionState;
        part controlledImprovementBacklog : ControlledImprovementBacklog;
        part countyEmergencyLiaison : CountyEmergencyLiaison {
            perform action a0 { doc /* represents county coordination needs @S010 */ }
            perform action a1 { doc /* sends the Drone Corridor Permit @S089 */ }
            perform action a2 { doc /* receives a simplified view @S124 */ }
            perform action a3 { doc /* can view approved aviation status and public safety implications @S150 */ }
            perform action a4 { doc /* view staging posture and public safety implications @S174 */ }
            perform action a5 { doc /* receive only the permissions required for their operational responsibilities @S187 */ }
            perform action a6 { doc /* interpret public-safety information @S210 */ }
            perform action a7 { doc /* coordinate notifications with county procedures @S210 */ }
            perform action a8 { doc /* use the Suppression Drop Receipt during post-incident reconciliation @S234 */ }
            perform action a9 { doc /* verify that reported suppression activity can be traced to county situation reporting @S234 */ }
        }
        part countyLiaisonRepresentatives : CountyLiaisonRepresentatives;
        part crewlineMobileTablet : CrewlineMobileTablet {
            perform action a0 { doc /* provides mobile access to approved operational information @S016 */ }
            perform action a1 { doc /* provides the Helitack Crew Leader with field access to assigned incident context, map references, and updates @S049 */ }
            perform action a2 { doc /* receive only the confirmed incident context @S072 */ }
            perform action a3 { doc /* shows approved suppression objectives, aircraft caution areas, and current assignment notes @S146 */ }
            perform action a4 { doc /* displays the current division assignment, route guidance, rally location, and assigned communications channel @S155 */ }
            perform action a5 { doc /* caches the latest accepted staging information @S159 */ }
            perform action a6 { doc /* marks any expired package as unavailable for execution @S159 */ }
            perform action a7 { doc /* presents the last verified assignment package @S172 */ }
            perform action a8 { doc /* identifies the time of last update @S172 */ }
            perform action a9 { doc /* queue field updates locally @S184 */ }
            perform action a10 { doc /* encrypt the queue at rest @S184 */ }
            perform action a11 { doc /* reconcile conflicts by preserving the original author, device time, and server acceptance time @S184 */ }
        }
        part dataStewardship : DataStewardship {
            perform action a0 { doc /* define retention, access control, quality review, and disposition rules for operational records, sensor data, model outputs, configuration records, and user activity records @S242 */ }
        }
        part deploymentGovernanceBoard : DeploymentGovernanceBoard {
            perform action a0 { doc /* approve each seasonal rollout @S226 */ }
            perform action a1 { doc /* reviewing residual risk, staffing readiness, configuration baselines, and open corrective actions from the prior operating period @S226 */ }
            perform action a2 { doc /* authorize limited use @S237 */ }
            perform action a3 { doc /* compare system performance, operational workload, maintenance burden, and user feedback against the acceptance criteria approved for that season @S246 */ }
        }
        part designatedRepresentativesForDetectionAviationGroundCrewAndCountyCoordinationFunctions : DesignatedRepresentativesForDetectionAviationGroundCrewAndCountyCoordinationFunctions;
        part dronePilotOperator : DronePilotOperator {
            perform action a0 { doc /* use the system to maintain shared awareness of field conditions, mission timing, and hazards @S015 */ }
            perform action a1 { doc /* review proposed routes, current dock status, and operational constraints @S036 */ }
            perform action a2 { doc /* coordinating any field action through established procedures @S036 */ }
            perform action a3 { doc /* confirms that the proposed verification task is safe for launch conditions and consistent with current operating constraints @S063 */ }
            perform action a4 { doc /* launches from the Horizon Ridge Drone Dock @S079 */ }
            perform action a5 { doc /* receives a route briefing @S090 */ }
            perform action a6 { doc /* keep imaging sorties aligned with available aircraft endurance and expected return time @S109 */ }
            perform action a7 { doc /* confirms that the proposed route is consistent with field conditions and can be flown without interfering with suppression aircraft @S132 */ }
            perform action a8 { doc /* confirms launch readiness @S170 */ }
            perform action a9 { doc /* receive only the permissions required for their operational responsibilities @S187 */ }
        }
        part droneTaskingService : DroneTaskingService {
            perform action a0 { doc /* support directed aerial observation @S005 */ }
            perform action a1 { doc /* manages approved unmanned flight requests @S035 */ }
            perform action a2 { doc /* records mission constraints @S035 */ }
            perform action a3 { doc /* presents task status @S035 */ }
            perform action a4 { doc /* prepare a verification task for the Horizon Ridge Drone Dock @S062 */ }
            perform action a5 { doc /* packages approved imaging objectives as map footprints, altitude bands, and revisit intervals @S108 */ }
            perform action a6 { doc /* converts reconnaissance objectives into trackable missions with launch windows, image requirements, altitude limits, and abort criteria @S129 */ }
            perform action a7 { doc /* maintains reconnaissance task status @S168 */ }
            perform action a8 { doc /* validates the corridor permit @S192 */ }
            perform action a9 { doc /* releasing an automated flight task @S192 */ }
            exhibit state modes {
                state s0 { doc /* degraded communications mode @S192 */ }
            }
        }
        part dutyDetectionOfficer : DutyDetectionOfficer {
            perform action a0 { doc /* monitoring detection cues @S011 */ }
            perform action a1 { doc /* requesting verification @S011 */ }
            perform action a2 { doc /* recommending whether a suspected ignition should be escalated @S011 */ }
            perform action a3 { doc /* recommend a Confirmed Ignition State @S012 */ }
            perform action a4 { doc /* reviews the triage case @S060 */ }
            perform action a5 { doc /* compares current imagery with recent frames @S060 */ }
            perform action a6 { doc /* checks whether the indication is growing, drifting, or disappearing @S060 */ }
            perform action a7 { doc /* request a fresh pan, tilt, or zoom view from the nearest fixed camera @S061 */ }
            perform action a8 { doc /* records the restriction basis in the Caldera Incident Command Portal @S078 */ }
            perform action a9 { doc /* manual acknowledgement @S086 */ }
            perform action a10 { doc /* verify that the impaired route has an alternate contact method @S087 */ }
            perform action a11 { doc /* compare the automated classification with visible flame, smoke color, and terrain context @S106 */ }
            perform action a12 { doc /* accepting the observation into the assessment queue @S106 */ }
            perform action a13 { doc /* receives a visible warning @S179 */ }
            perform action a14 { doc /* operate the Caldera Incident Command Portal @S202 */ }
            perform action a15 { doc /* review detections @S202 */ }
            perform action a16 { doc /* validate confidence indicators @S202 */ }
            perform action a17 { doc /* escalate suspected ignitions @S202 */ }
        }
        part eastRetardantLoadingPump : EastRetardantLoadingPump {
            perform action a0 { doc /* sends the Retardant Batch Slip @S073 */ }
            perform action a1 { doc /* report equipment state, flow readiness, and out-of-service conditions @S142 */ }
            perform action a2 { doc /* enter a metered recirculation mode @S194 */ }
            perform action a3 { doc /* pass integration checks that verify operator controls, fault handling, and audit capture @S230 */ }
            exhibit state modes {
                state s0 { doc /* metered recirculation mode @S194 */ }
            }
        }
        part evacuationZones : EvacuationZones;
        part exerciseControllers : ExerciseControllers {
            perform action a0 { doc /* inject realistic complications @S217 */ }
        }
        part fieldComponent : FieldComponent {
            perform action a0 { doc /* buffer signed audit records locally @S191 */ }
            perform action a1 { doc /* forward them without modification @S191 */ }
        }
        part fieldCrewRepresentatives : FieldCrewRepresentatives;
        part fieldEquipment : FieldEquipment;
        part fireBehaviorModel : FireBehaviorModel {
            perform action a0 { doc /* combines the accepted perimeter, recent growth vectors, weather fields, and fuel conditions @S117 */ }
            perform action a1 { doc /* estimate short-term spread direction and rate @S117 */ }
        }
        part fixedRidgeSensors : FixedRidgeSensors;
        part fuels : Fuels;
        part geospatialOverlays : GeospatialOverlays;
        part helitackCrewLeader : HelitackCrewLeader {
            perform action a0 { doc /* use the system to maintain shared awareness of field conditions, mission timing, and hazards @S015 */ }
            perform action a1 { doc /* acknowledge air-to-ground instructions @S097 */ }
            perform action a2 { doc /* report whether crews are inside any planned drop or reconnaissance area @S097 */ }
            perform action a3 { doc /* acknowledges nearby aircraft activity @S147 */ }
            perform action a4 { doc /* receives the same operational package with aviation constraints and landing zone notes @S156 */ }
            perform action a5 { doc /* acknowledges assignment receipt @S173 */ }
            perform action a6 { doc /* reports readiness @S173 */ }
            perform action a7 { doc /* records any exception that prevents safe execution @S173 */ }
            perform action a8 { doc /* receive only the permissions required for their operational responsibilities @S187 */ }
            perform action a9 { doc /* use the staging pin @S209 */ }
            perform action a10 { doc /* confirm that the assigned crew is positioned at the exercise location @S209 */ }
        }
        part horizonRidgeDroneDock : HorizonRidgeDroneDock {
            perform action a0 { doc /* support directed aerial observation @S005 */ }
            perform action a1 { doc /* produces the Battery Swap Ticket @S034 */ }
            perform action a2 { doc /* supports initial attack @S130 */ }
            perform action a3 { doc /* keeping assigned aircraft charged, positioned, and ready for rapid launch @S130 */ }
            perform action a4 { doc /* report launch readiness, aircraft health, and recovery availability @S131 */ }
        }
        part improvementPlan : ImprovementPlan {
            perform action a0 { doc /* define which procedures, training materials, interfaces, algorithms, and support arrangements will be revised @S247 */ }
        }
        part informationSecurityRepresentation : InformationSecurityRepresentation;
        part jurisdictionBoundaries : JurisdictionBoundaries;
        part knownCommunicationsCoverage : KnownCommunicationsCoverage;
        part localHealthMonitoring : LocalHealthMonitoring;
        part maintenanceController : MaintenanceController {
            perform action a0 { doc /* records that a flight battery has reached the configured replacement threshold @S034 */ }
        }
        part maintenanceRepresentation : MaintenanceRepresentation;
        part maintenanceRepresentatives : MaintenanceRepresentatives;
        part mapProducts : MapProducts {
            perform action a0 { doc /* records source time, processing time, model version, analyst acceptance, and supersession status @S125 */ }
        }
        part mesoWestWeatherFusionNode : MesoWestWeatherFusionNode {
            perform action a0 { doc /* contributes localized weather context @S007 */ }
            perform action a1 { doc /* ingests station observations, forecast grids, and configured quality checks @S042 */ }
            perform action a2 { doc /* provide a consistent weather picture for the operating area @S042 */ }
            perform action a3 { doc /* sends the Wind Shift Bulletin @S043 */ }
            perform action a4 { doc /* identify a significant change in local wind behavior @S043 */ }
            perform action a5 { doc /* provides local wind, humidity, temperature, and stability context @S058 */ }
            perform action a6 { doc /* supplies wind and visibility context @S093 */ }
            perform action a7 { doc /* ingests station observations, forecast grids, and local quality checks @S113 */ }
            perform action a8 { doc /* maintain the wind, humidity, temperature, and stability fields used by the spread model @S113 */ }
            perform action a9 { doc /* publishes a time-indexed weather update @S114 */ }
            perform action a10 { doc /* marks significant forecast changes @S114 */ }
            perform action a11 { doc /* identifies which map products require recomputation @S114 */ }
            perform action a12 { doc /* provides weather-derived exposure flags @S166 */ }
            perform action a13 { doc /* retain a local weather cache @S183 */ }
            perform action a14 { doc /* supports situational awareness @S212 */ }
            perform action a15 { doc /* meet agreed availability, timing, and data-quality thresholds @S228 */ }
        }
        part northLookoutCameraMast : NorthLookoutCameraMast {
            perform action a0 { doc /* provide fixed observation coverage over high-risk sectors @S004 */ }
            perform action a1 { doc /* provide long-range visual coverage of drainages, access roads, and known ignition corridors @S026 */ }
            perform action a2 { doc /* sends the Thermal Spot Snippet @S030 */ }
            perform action a3 { doc /* identifies a candidate heat signature @S030 */ }
            perform action a4 { doc /* provide observation context @S094 */ }
            perform action a5 { doc /* captures a time-stamped smoke column bearing @S103 */ }
            perform action a6 { doc /* reports the pan, tilt, zoom, and confidence values @S103 */ }
            perform action a7 { doc /* report heartbeat, temperature, storage, and pointing-status telemetry @S182 */ }
            perform action a8 { doc /* meet agreed availability, timing, and data-quality thresholds @S228 */ }
        }
        part operationalLeadership : OperationalLeadership;
        part operationalRecords : OperationalRecords;
        part operationalUsers : OperationalUsers {
            perform action a0 { doc /* receive communications training @S211 */ }
            perform action a1 { doc /* recognize restrictions @S236 */ }
            perform action a2 { doc /* apply required controls @S236 */ }
            perform action a3 { doc /* recover normal coordination @S236 */ }
        }
        part operationsLead : OperationsLead {
            perform action a0 { doc /* authorized instructor @S213 */ }
        }
        part operationsNetwork : OperationsNetwork;
        part operationsRepresentatives : OperationsRepresentatives;
        part operators : Operators {
            perform action a0 { doc /* treat weather inputs @S212 */ }
        }
        part personnel : Personnel {
            perform action a0 { doc /* complete remedial training and a repeat evaluation @S223 */ }
            perform action a1 { doc /* performing unsupervised duties @S223 */ }
        }
        part releaseCandidate : ReleaseCandidate {
            perform action a0 { doc /* enter operational service @S227 */ }
        }
        part reviewBoard : ReviewBoard;
        part reviewFacilitators : ReviewFacilitators {
            perform action a0 { doc /* document what was expected to happen, what actually happened, why differences occurred, and which corrective actions are necessary @S240 */ }
        }
        part roads : Roads;
        part secureNetworkTermination : SecureNetworkTermination;
        part sentinelFirelineAnalyticsEngine : SentinelFirelineAnalyticsEngine {
            perform action a0 { doc /* assist in screening imagery and other observations for potential fire activity @S006 */ }
            perform action a1 { doc /* aggregates camera detections, weather inputs, geospatial context, and operator feedback into traceable recommendations @S038 */ }
            perform action a2 { doc /* receives the observation context @S053 */ }
            perform action a3 { doc /* normalizes image, thermal, and weather attributes into a common event record @S053 */ }
            perform action a4 { doc /* temporarily down-weighted the Smoke Classifier Module @S096 */ }
            perform action a5 { doc /* identifies heat signatures, smoke edges, flame fronts, and potential spot fire indicators in the registered imagery @S111 */ }
            perform action a6 { doc /* compares recent reconnaissance observations with camera detections and weather-driven projections @S134 */ }
            perform action a7 { doc /* support tactical recommendations @S134 */ }
            perform action a8 { doc /* updates hazard summaries @S161 */ }
            perform action a9 { doc /* applies the Ridge Shadow Mask @S162 */ }
            perform action a10 { doc /* estimating crew-visible fire edge confidence in steep terrain @S162 */ }
            perform action a11 { doc /* issues a crew exposure refresh @S164 */ }
            perform action a12 { doc /* continue using the last approved model configuration @S180 */ }
            perform action a13 { doc /* reject unversioned rules or unsigned analytic packages @S180 */ }
            perform action a14 { doc /* present uncertainty @S204 */ }
            perform action a15 { doc /* complete documented functional testing against the approved mission scenarios @S227 */ }
        }
        part slope : Slope;
        part smokeClassifierModule : SmokeClassifierModule {
            perform action a0 { doc /* assist in screening imagery and other observations for potential fire activity @S006 */ }
            perform action a1 { doc /* scores visual observations for plume likelihood @S039 */ }
            perform action a2 { doc /* passes confidence values to the broader analytics workflow @S039 */ }
            perform action a3 { doc /* produces the Ridge Shadow Mask @S056 */ }
            perform action a4 { doc /* assigns each observation a smoke likelihood, growth trend, and obscuration flag @S105 */ }
            perform action a5 { doc /* uses the Camera Cleaning Log to suppress confidence changes caused by lens contamination and service timing @S163 */ }
            perform action a6 { doc /* label detections as advisory @S181 */ }
            perform action a7 { doc /* present uncertainty @S204 */ }
            perform action a8 { doc /* complete documented functional testing against the approved mission scenarios @S227 */ }
        }
        part southLookoutCameraMast : SouthLookoutCameraMast {
            perform action a0 { doc /* provide fixed observation coverage over high-risk sectors @S004 */ }
            perform action a1 { doc /* covers the opposing viewshed @S027 */ }
            perform action a2 { doc /* provides overlapping observation @S027 */ }
            perform action a3 { doc /* provide observation context @S094 */ }
            perform action a4 { doc /* produces the Camera Cleaning Log @S095 */ }
            perform action a5 { doc /* supplies a separate bearing track @S104 */ }
            perform action a6 { doc /* report heartbeat, temperature, storage, and pointing-status telemetry @S182 */ }
            perform action a7 { doc /* meet agreed availability, timing, and data-quality thresholds @S228 */ }
        }
        part staffedOperationsPortal : StaffedOperationsPortal;
        part structures : Structures;
        part systemPart : System {
            perform action a0 { doc /* supports recognition of an Airspace Restricted State @S019 */ }
            perform action a1 { doc /* keeps suppression planning visible @S099 */ }
            perform action a2 { doc /* preventing premature aircraft dispatch @S099 */ }
            perform action a3 { doc /* converts detection observations, aerial imagery, weather updates, and geospatial overlays into a shared fire behavior assessment @S101 */ }
            perform action a4 { doc /* holds the affected recommendation for Air Attack Supervisor review @S151 */ }
            perform action a5 { doc /* favor continuity of command decisions over full automation @S176 */ }
            perform action a6 { doc /* protect retained data with encryption at rest @S198 */ }
            exhibit state modes {
                state s0 { doc /* Airspace Restricted State @S019,S046,S167 */ }
                state s1 { doc /* Confirmed Ignition State @S046,S099 */ }
            }
        }
        part talonAirTankerDispatchConsole : TalonAirTankerDispatchConsole {
            perform action a0 { doc /* presenting aircraft coordination data, loading status, and mission notes relevant to suppression support @S047 */ }
            perform action a1 { doc /* maintained active aviation lane @S080 */ }
            perform action a2 { doc /* provides the aviation status view @S081 */ }
            perform action a3 { doc /* maintains a planning view of tanker availability, estimated time to target, base turnaround time, and assigned incident priority @S137 */ }
            perform action a4 { doc /* prevent a dispatch plan from being released @S138 */ }
            perform action a5 { doc /* produces the Runway Release Note @S140 */ }
            perform action a6 { doc /* sends the Suppression Drop Receipt @S148 */ }
            perform action a7 { doc /* pass integration checks that verify operator controls, fault handling, and audit capture @S230 */ }
        }
        part tankerBaseManager : TankerBaseManager {
            perform action a0 { doc /* uses the system to understand mission demand, loading status, and operational tempo @S014 */ }
            perform action a1 { doc /* sequence retardant aircraft availability @S081 */ }
            perform action a2 { doc /* coordinates pump readiness for the East Retardant Loading Pump and the West Retardant Loading Pump @S082 */ }
            perform action a3 { doc /* confirming that a tanker can accept an assignment @S082 */ }
            perform action a4 { doc /* uses the batch slip to confirm that the loading record matches the aircraft assignment and planned retardant quantity @S141 */ }
            perform action a5 { doc /* resolves discrepancies in loading status @S144 */ }
            perform action a6 { doc /* receive only the permissions required for their operational responsibilities @S187 */ }
            perform action a7 { doc /* receive practical instruction on status entry, loading coordination, and abnormal-condition reporting @S207 */ }
            perform action a8 { doc /* use the Runway Release Note during acceptance review @S233 */ }
            perform action a9 { doc /* verify that tanker-base operating constraints are documented @S233 */ }
        }
        part trainingProgram : TrainingProgram;
        part vHFRadioGatewayRepeater : VHFRadioGatewayRepeater {
            perform action a0 { doc /* supports continuity between digital coordination and field radio practices @S008 */ }
            perform action a1 { doc /* provides a monitored bridge between selected radio traffic and operator workstations @S044 */ }
            perform action a2 { doc /* supports voice coordination @S064 */ }
            perform action a3 { doc /* bridges command, air-to-ground, and county liaison talk paths @S084 */ }
            perform action a4 { doc /* preserve the original speaker identity @S085 */ }
            perform action a5 { doc /* provides an operational fallback for relaying approved aviation instructions @S145 */ }
            perform action a6 { doc /* mirrors priority assignment summaries @S171 */ }
            perform action a7 { doc /* queue outbound voice-to-data acknowledgments @S193 */ }
            perform action a8 { doc /* forward them @S193 */ }
        }
        part waiver : Waiver;
        part waterSources : WaterSources;
        part weatherRatedEnclosures : WeatherRatedEnclosures;
        part westRetardantLoadingPump : WestRetardantLoadingPump {
            perform action a0 { doc /* report equipment state, flow readiness, and out-of-service conditions @S142 */ }
            perform action a1 { doc /* pass integration checks that verify operator controls, fault handling, and audit capture @S230 */ }
            exhibit state modes {
                state s0 { doc /* operational availability @S195 */ }
            }
        }
        flow f0 of VideoItem from northLookoutCameraMast to operationsNetwork { doc /* @S029 */ }
        flow f1 of VideoItem from southLookoutCameraMast to operationsNetwork { doc /* @S029 */ }
        flow f2 of WeatherInputsItem from mesoWestWeatherFusionNode to sentinelFirelineAnalyticsEngine { doc /* @S038 */ }
        flow f3 of ConfidenceValuesItem from smokeClassifierModule to sentinelFirelineAnalyticsEngine { doc /* @S039 */ }
        flow f4 of AircraftCoordinationDataLoadingStatusAndMissionNotesItem from talonAirTankerDispatchConsole to airAttackSupervisor { doc /* @S047 */ }
        flow f5 of AircraftCoordinationDataLoadingStatusAndMissionNotesItem from talonAirTankerDispatchConsole to tankerBaseManager { doc /* @S047 */ }
        flow f6 of AssignedIncidentContextMapReferencesAndUpdatesItem from crewlineMobileTablet to helitackCrewLeader { doc /* @S049 */ }
        flow f7 of ObservationContextItem from northLookoutCameraMast to sentinelFirelineAnalyticsEngine { doc /* @S053 */ }
        flow f8 of ObservationContextItem from southLookoutCameraMast to sentinelFirelineAnalyticsEngine { doc /* @S053 */ }
        flow f9 of ObservationContextItem from horizonRidgeDroneDock to sentinelFirelineAnalyticsEngine { doc /* @S053 */ }
        flow f10 of TriageCaseItem from calderaIncidentCommandPortal to dutyDetectionOfficer { doc /* @S060 */ }
        flow f11 of VerificationTaskItem from droneTaskingService to horizonRidgeDroneDock { doc /* @S062 */ }
        flow f12 of ConfirmedIncidentContextItem from calderaIncidentCommandPortal to crewlineMobileTablet { doc /* @S072 */ }
        flow f13 of RestrictionBasisItem from dutyDetectionOfficer to calderaIncidentCommandPortal { doc /* @S078 */ }
        flow f14 of AviationStatusViewItem from talonAirTankerDispatchConsole to tankerBaseManager { doc /* @S081 */ }
        flow f15 of FirePerimeterIntelligenceItem from sentinelFirelineAnalyticsEngine to airAttackSupervisor { doc /* @S092 */ }
        flow f16 of ObservationContextItem from northLookoutCameraMast to airAttackSupervisor { doc /* @S094 */ }
        flow f17 of ObservationContextItem from southLookoutCameraMast to airAttackSupervisor { doc /* @S094 */ }
        flow f18 of CrewLocationReportItem from helitackCrewLeader to crewlineMobileTablet { doc /* @S097 */ }
        flow f19 of CrewAcknowledgementsItem from calderaIncidentCommandPortal to airAttackSupervisor { doc /* @S098 */ }
        flow f20 of WindHumidityTemperatureAndStabilityFieldsItem from mesoWestWeatherFusionNode to fireBehaviorModel { doc /* @S113 */ }
        flow f21 of MapProductsItem from calderaIncidentCommandPortal to airAttackSupervisor { doc /* @S123 */ }
        flow f22 of SimplifiedViewItem from calderaIncidentCommandPortal to countyEmergencyLiaison { doc /* @S124 */ }
        flow f23 of LoadingStatusItem from talonAirTankerDispatchConsole to tankerBaseManager { doc /* @S144 */ }
        flow f24 of OperationalPackageWithAviationConstraintsAndLandingZoneNotesItem from crewlineMobileTablet to helitackCrewLeader { doc /* @S156 */ }
        flow f25 of SignedAuditRecordsItem from fieldComponent to appendOnlyAuditStore { doc /* @S191 */ }
        flow f26 of UncertaintyItem from sentinelFirelineAnalyticsEngine to dutyDetectionOfficer { doc /* @S204 */ }
        flow f27 of UncertaintyItem from smokeClassifierModule to dutyDetectionOfficer { doc /* @S204 */ }
        flow f28 of PublicSafetyInformationItem from calderaIncidentCommandPortal to countyEmergencyLiaison { doc /* @S210 */ }
        flow f29 of WeatherInputsItem from mesoWestWeatherFusionNode to operators { doc /* @S212 */ }
        flow f30 of SuppressionDropReceiptItem from talonAirTankerDispatchConsole to countyEmergencyLiaison { doc /* @S234 */ }
        flow f31 of TheWindShiftBulletinItem from mesoWestWeatherFusionNode to airAttackSupervisor { doc /* joined @S043,S136 */ }
        flow f32 of RetardantBatchSlipItem from eastRetardantLoadingPump to tankerBaseManager { doc /* joined @S073,S141 */ }
        flow f33 of TheRidgeShadowMaskItem from smokeClassifierModule to sentinelFirelineAnalyticsEngine { doc /* joined @S056,S162 */ }
        flow f34 of TheCameraCleaningLogItem from southLookoutCameraMast to smokeClassifierModule { doc /* joined @S095,S163 */ }
        flow f35 of TheCrewStagingPinItem from calderaIncidentCommandPortal to helitackCrewLeader { doc /* joined @S120,S209 */ }
        flow f36 of TheRunwayReleaseNoteItem from talonAirTankerDispatchConsole to tankerBaseManager { doc /* joined @S140,S233 */ }
    }
    requirement def R0 { doc /* smoke columns, flame growth, and visibility changes must be assessed quickly @S004 */ subject s : CalderaWildfireDetectionAndSuppressionSupportSystem; }
    requirement def R1 { doc /* Confirmation requires at least one persistent smoke indication or thermal cue, plus either independent sensor corroboration, field report corroboration, or a direct human visual judgment recorded by an authorized reviewer. @S067 */ subject s : ConfirmedIgnitionState; }
    requirement def R2 { doc /* The Drone Tasking Service shall not issue a launch task that conflicts with an active aviation lane maintained by the Talon Air Tanker Dispatch Console. @S080 */ subject s : DroneTaskingService; }
    requirement def R3 { doc /* Radio bridging shall preserve the original speaker identity when the source channel provides it. @S085 */ subject s : VHFRadioGatewayRepeater; }
    requirement def R4 { doc /* If a bridge path fails, the Caldera Incident Command Portal marks the affected radio route as impaired and requires manual acknowledgement by the Duty Detection Officer. @S086 */ subject s : CalderaIncidentCommandPortal; }
    requirement def R5 { doc /* Orion must verify that the impaired route has an alternate contact method before any new aviation coordination message is accepted. @S087 */ subject s : DutyDetectionOfficer; }
    requirement def R6 { doc /* County liaison procedures require that jurisdictional constraints be entered in the Caldera Incident Command Portal before the Drone Pilot Operator receives a route briefing. @S090 */ subject s : CalderaIncidentCommandPortal; }
    requirement def R7 { doc /* When inputs conflict, the common operating picture shows the conflict explicitly and requires review before the affected recommendation is promoted for command use. @S126 */ subject s : CommonOperatingPicture; }
    requirement def R8 { doc /* Kestrel is required to report launch readiness, aircraft health, and recovery availability before a reconnaissance task can be released. @S131 */ subject s : HorizonRidgeDroneDock; }
    requirement def R9 { doc /* Marigold must prevent a dispatch plan from being released when required aviation approvals, airspace status, or tanker readiness fields are incomplete. @S138 */ subject s : TalonAirTankerDispatchConsole; }
    requirement def R10 { doc /* During prolonged wildfire operations, the system shall favor continuity of command decisions over full automation when communications, power, or sensor coverage is impaired. @S176 */ subject s : System; }
    requirement def R11 { doc /* The Sentinel Fireline Analytics Engine shall continue using the last approved model configuration after a repository outage and shall reject unversioned rules or unsigned analytic packages. @S180 */ subject s : SentinelFirelineAnalyticsEngine; }
    requirement def R12 { doc /* The Smoke Classifier Module shall label detections as advisory when either camera mast is unavailable or when image quality falls below the validated threshold. @S181 */ subject s : SmokeClassifierModule; }
    requirement def R13 { doc /* The North Lookout Camera Mast and the South Lookout Camera Mast shall report heartbeat, temperature, storage, and pointing-status telemetry so that maintenance staff can distinguish sensor failure from environmental obscuration. @S182 */ subject s : NorthLookoutCameraMast; }
    requirement def R14 { doc /* The North Lookout Camera Mast and the South Lookout Camera Mast shall report heartbeat, temperature, storage, and pointing-status telemetry so that maintenance staff can distinguish sensor failure from environmental obscuration. @S182 */ subject s : SouthLookoutCameraMast; }
    requirement def R15 { doc /* The MesoWest Weather Fusion Node shall retain a local weather cache sufficient to support near-term fire behavior review when upstream feeds are intermittent. @S183 */ subject s : MesoWestWeatherFusionNode; }
    requirement def R16 { doc /* Crewline Mobile Tablet clients shall queue field updates locally, encrypt the queue at rest, and reconcile conflicts by preserving the original author, device time, and server acceptance time. @S184 */ subject s : CrewlineMobileTablet; }
    requirement def R17 { doc /* All interactive access to the Caldera Incident Command Portal requires named accounts, role-based authorization, and multifactor authentication when the authentication service is reachable. @S185 */ subject s : CalderaIncidentCommandPortal; }
    requirement def R18 { doc /* Security-relevant events, including failed logons, role changes, queued update releases, model changes, and maintenance overrides, shall be written to an append-only audit store. @S189 */ subject s : AppendOnlyAuditStore; }
    requirement def R19 { doc /* If central audit storage is unavailable, each field component shall buffer signed audit records locally and forward them without modification when connectivity returns. @S191 */ subject s : FieldComponent; }
    requirement def R20 { doc /* Badger shall queue outbound voice-to-data acknowledgments for at least fifteen minutes during backhaul loss and forward them when the link is restored. @S193 */ subject s : VHFRadioGatewayRepeater; }
    requirement def R21 { doc /* East Retardant Loading Pump shall enter a metered recirculation mode when pressure variance exceeds the calibrated maintenance limit. @S194 */ subject s : EastRetardantLoadingPump; }
    requirement def R22 { doc /* The West Retardant Loading Pump shall be inspected at shift change for hose wear, valve position, controller alarms, and leakage before it is returned to operational availability. @S195 */ subject s : WestRetardantLoadingPump; }
    requirement def R23 { doc /* Operational records that support command decisions and safety reviews shall be retained for the incident record period defined by agency policy @S197 */ subject s : OperationalRecords; }
    requirement def R24 { doc /* The system shall protect retained data with encryption at rest, controlled export procedures, and deletion workflows that require documented authorization. @S198 */ subject s : System; }
    requirement def R25 { doc /* spare power, replacement network equipment, field cleaning supplies, and documented recovery procedures shall be staged so that no single equipment fault stops detection or suppression-support operations @S199 */ subject s : CalderaWildfireDetectionAndSuppressionSupportSystem; }
    requirement def R26 { doc /* Training for the Caldera Wildfire Detection and Suppression Support System shall be completed before each fire season and refreshed whenever operating procedures or field configurations change. @S200 */ subject s : CalderaWildfireDetectionAndSuppressionSupportSystem; }
    requirement def R27 { doc /* The training program shall be role based so that each participant practices the decisions, system functions, communications, and safety constraints that apply to the assigned position. @S201 */ subject s : TrainingProgram; }
    requirement def R28 { doc /* The Duty Detection Officer shall be trained to operate the Caldera Incident Command Portal, review detections, validate confidence indicators, and escalate suspected ignitions according to the approved incident workflow. @S202 */ subject s : DutyDetectionOfficer; }
    requirement def R29 { doc /* Camera familiarization shall cover the North Lookout Camera Mast and the South Lookout Camera Mast, including normal image behavior, degraded visibility conditions, routine inspection cues, and reporting of equipment faults. @S203 */ subject s : CameraFamiliarization; }
    requirement def R30 { doc /* The Duty Detection Officer shall also learn how the Sentinel Fireline Analytics Engine and the Smoke Classifier Module present uncertainty so that human confirmation remains part of every operational decision. @S204 */ subject s : DutyDetectionOfficer; }
    requirement def R31 { doc /* The Drone Pilot Operator shall be trained on Horizon Ridge Drone Dock procedures, Drone Tasking Service mission controls, safe launch checks, recovery actions, and loss-of-link coordination. @S205 */ subject s : DronePilotOperator; }
    requirement def R32 { doc /* The Air Attack Supervisor shall be trained to interpret system status during aerial operations and to coordinate with the Talon Air Tanker Dispatch Console without bypassing airspace safety requirements. @S206 */ subject s : AirAttackSupervisor; }
    requirement def R33 { doc /* The Tanker Base Manager shall receive practical instruction on status entry, loading coordination, and abnormal-condition reporting for the East Retardant Loading Pump and the West Retardant Loading Pump. @S207 */ subject s : TankerBaseManager; }
    requirement def R34 { doc /* The Helitack Crew Leader shall be trained on use of the Crewline Mobile Tablet, field acknowledgments, location updates, and communication discipline during changing fire behavior. @S208 */ subject s : HelitackCrewLeader; }
    requirement def R35 { doc /* During field mobilization drills, the Helitack Crew Leader shall use the staging pin to confirm that the assigned crew is positioned at the exercise location. @S209 */ subject s : HelitackCrewLeader; }
    requirement def R36 { doc /* The County Emergency Liaison shall be trained to interpret public-safety information from the Caldera Incident Command Portal and to coordinate notifications with county procedures. @S210 */ subject s : CountyEmergencyLiaison; }
    requirement def R37 { doc /* All operational users shall receive communications training that includes VHF Radio Gateway Repeater failure modes, alternate contact paths, call signs, message brevity, and confirmation readbacks. @S211 */ subject s : OperationalUsers; }
    requirement def R38 { doc /* Weather training shall explain how the MesoWest Weather Fusion Node supports situational awareness and how operators should treat weather inputs when local observations conflict with displayed values. @S212 */ subject s : MesoWestWeatherFusionNode; }
    requirement def R39 { doc /* Initial qualification shall include supervised console practice, scenario walkthroughs, and a documented check by an instructor who is authorized by the operations lead. @S213 */ subject s : CalderaWildfireDetectionAndSuppressionSupportSystem; }
    requirement def R40 { doc /* Annual refresher training shall include changes to software screens, revised thresholds, updated contact rosters, seasonal hazard briefings, and lessons learned from prior incidents. @S214 */ subject s : CalderaWildfireDetectionAndSuppressionSupportSystem; }
    requirement def R41 { doc /* Tabletop exercises shall be conducted before the expected peak fire period and shall test detection triage, command notification, airspace coordination, tanker-base coordination, crew deployment, and public-agency liaison actions. @S215 */ subject s : CalderaWildfireDetectionAndSuppressionSupportSystem; }
    requirement def R42 { doc /* Live exercises shall be scheduled at least once per season when conditions permit and shall include field crews, aircraft coordination staff, drone operations staff, and command-center personnel. @S216 */ subject s : CalderaWildfireDetectionAndSuppressionSupportSystem; }
    requirement def R43 { doc /* Exercise controllers shall inject realistic complications such as intermittent network service, obscured camera views, delayed field confirmation, resource conflicts, and conflicting reports from external observers. @S217 */ subject s : ExerciseControllers; }
    requirement def R44 { doc /* Performance measures shall include time from automated detection to human review, time from review to command notification, time to resource assignment, communication completion rate, and accuracy of incident status updates. @S218 */ subject s : CalderaWildfireDetectionAndSuppressionSupportSystem; }
    requirement def R45 { doc /* Detection quality shall be evaluated using confirmed events, benign smoke sources, weather-related artifacts, and operator notes so that both missed detections and false alarms are visible to program management. @S219 */ subject s : CalderaWildfireDetectionAndSuppressionSupportSystem; }
    requirement def R46 { doc /* Every false-alarm review shall identify the apparent cause, affected sensors or analytic outputs, operator actions, dispatch consequences, and any recommended tuning or training change. @S220 */ subject s : CalderaWildfireDetectionAndSuppressionSupportSystem; }
    requirement def R47 { doc /* The review board shall include operations, aviation, field crew, maintenance, and county liaison representatives when the event affected more than one operational function. @S221 */ subject s : ReviewBoard; }
    requirement def R48 { doc /* Seasonal readiness shall require each active user to demonstrate current proficiency, complete required safety briefings, and acknowledge the current operating procedures before receiving operational access. @S222 */ subject s : ActiveUser; }
    requirement def R49 { doc /* Personnel who do not meet proficiency requirements shall complete remedial training and a repeat evaluation before performing unsupervised duties in the Caldera Wildfire Detection and Suppression Support System. @S223 */ subject s : Personnel; }
    requirement def R50 { doc /* Deployment governance for the Caldera Wildfire Detection and Suppression Support System shall be managed as a staged release process that follows completion of seasonal readiness activities. @S224 */ subject s : CalderaWildfireDetectionAndSuppressionSupportSystem; }
    requirement def R51 { doc /* The deployment governance board shall include operational leadership, maintenance representation, information security representation, and designated representatives for detection, aviation, ground crew, and county coordination functions. @S225 */ subject s : DeploymentGovernanceBoard; }
    requirement def R52 { doc /* The board shall approve each seasonal rollout only after reviewing residual risk, staffing readiness, configuration baselines, and open corrective actions from the prior operating period. @S226 */ subject s : DeploymentGovernanceBoard; }
    requirement def R53 { doc /* A release candidate shall not enter operational service until the Caldera Incident Command Portal, Sentinel Fireline Analytics Engine, and Smoke Classifier Module complete documented functional testing against the approved mission scenarios. @S227 */ subject s : ReleaseCandidate; }
    requirement def R54 { doc /* Acceptance criteria shall require the North Lookout Camera Mast, South Lookout Camera Mast, and MesoWest Weather Fusion Node to meet agreed availability, timing, and data-quality thresholds during the readiness window. @S228 */ subject s : NorthLookoutCameraMast; }
    requirement def R55 { doc /* Acceptance criteria shall require the North Lookout Camera Mast, South Lookout Camera Mast, and MesoWest Weather Fusion Node to meet agreed availability, timing, and data-quality thresholds during the readiness window. @S228 */ subject s : SouthLookoutCameraMast; }
    requirement def R56 { doc /* Acceptance criteria shall require the North Lookout Camera Mast, South Lookout Camera Mast, and MesoWest Weather Fusion Node to meet agreed availability, timing, and data-quality thresholds during the readiness window. @S228 */ subject s : MesoWestWeatherFusionNode; }
    requirement def R57 { doc /* The Drone Tasking Service and Horizon Ridge Drone Dock shall be accepted only after controlled field validation shows that task execution, abort behavior, and status reporting remain stable under expected seasonal conditions. @S229 */ subject s : DroneTaskingService; }
    requirement def R58 { doc /* The Drone Tasking Service and Horizon Ridge Drone Dock shall be accepted only after controlled field validation shows that task execution, abort behavior, and status reporting remain stable under expected seasonal conditions. @S229 */ subject s : HorizonRidgeDroneDock; }
    requirement def R59 { doc /* The Talon Air Tanker Dispatch Console, East Retardant Loading Pump, and West Retardant Loading Pump shall pass integration checks that verify operator controls, fault handling, and audit capture before activation. @S230 */ subject s : TalonAirTankerDispatchConsole; }
    requirement def R60 { doc /* The Talon Air Tanker Dispatch Console, East Retardant Loading Pump, and West Retardant Loading Pump shall pass integration checks that verify operator controls, fault handling, and audit capture before activation. @S230 */ subject s : EastRetardantLoadingPump; }
    requirement def R61 { doc /* The Talon Air Tanker Dispatch Console, East Retardant Loading Pump, and West Retardant Loading Pump shall pass integration checks that verify operator controls, fault handling, and audit capture before activation. @S230 */ subject s : WestRetardantLoadingPump; }
    requirement def R62 { doc /* The VHF Radio Gateway Repeater and Crewline Mobile Tablet shall be validated for coverage, message persistence, authentication behavior, and degraded-network operation before release approval. @S231 */ subject s : VHFRadioGatewayRepeater; }
    requirement def R63 { doc /* The VHF Radio Gateway Repeater and Crewline Mobile Tablet shall be validated for coverage, message persistence, authentication behavior, and degraded-network operation before release approval. @S231 */ subject s : CrewlineMobileTablet; }
    requirement def R64 { doc /* Redtail shall confirm that deployment readiness evidence is sufficient before air operations functionality is enabled for the season. @S232 */ subject s : AirAttackSupervisor; }
    requirement def R65 { doc /* The Tanker Base Manager shall use the Runway Release Note during acceptance review to verify that tanker-base operating constraints are documented before seasonal activation. @S233 */ subject s : TankerBaseManager; }
    requirement def R66 { doc /* The County Emergency Liaison shall use the Suppression Drop Receipt during post-incident reconciliation to verify that reported suppression activity can be traced to county situation reporting. @S234 */ subject s : CountyEmergencyLiaison; }
    requirement def R67 { doc /* Acceptance of the Confirmed Ignition State workflow shall require traceable evidence that operator acknowledgement, escalation timing, and command visibility meet the approved concept of operations. @S235 */ subject s : ConfirmedIgnitionState; }
    requirement def R68 { doc /* Acceptance of the Airspace Restricted State workflow shall require evidence that operational users can recognize restrictions, apply required controls, and recover normal coordination when restrictions are lifted. @S236 */ subject s : AirspaceRestrictedState; }
    requirement def R69 { doc /* Any waiver to acceptance criteria shall identify the operational impact, compensating procedure, expiration date, and accountable owner before the board may authorize limited use. @S237 */ subject s : Waiver; }
    requirement def R70 { doc /* After-action reviews shall be held after major incidents, readiness exercises, significant false alarms, missed detections, and any event that exposes a gap in operational coordination. @S238 */ subject s : AfterActionReviews; }
    requirement def R71 { doc /* Each after-action review shall reconstruct the timeline from system logs, user accounts, communications records, and maintenance notes without assigning blame to individual operators. @S239 */ subject s : AfterActionReview; }
    requirement def R72 { doc /* Review facilitators shall document what was expected to happen, what actually happened, why differences occurred, and which corrective actions are necessary before the next readiness cycle. @S240 */ subject s : ReviewFacilitators; }
    requirement def R73 { doc /* Corrective actions shall be entered into a controlled improvement backlog with assigned ownership, target completion dates, verification methods, and linkage to the originating event. @S241 */ subject s : ControlledImprovementBacklog; }
    requirement def R74 { doc /* Data stewardship shall define retention, access control, quality review, and disposition rules for operational records, sensor data, model outputs, configuration records, and user activity records. @S242 */ subject s : DataStewardship; }
    requirement def R75 { doc /* Changes to the Sentinel Fireline Analytics Engine or Smoke Classifier Module shall be evaluated with representative seasonal data before deployment to confirm that detection performance improves without unacceptable increases in false alerts. @S244 */ subject s : SentinelFirelineAnalyticsEngine; }
    requirement def R76 { doc /* Changes to the Sentinel Fireline Analytics Engine or Smoke Classifier Module shall be evaluated with representative seasonal data before deployment to confirm that detection performance improves without unacceptable increases in false alerts. @S244 */ subject s : SmokeClassifierModule; }
    requirement def R77 { doc /* Configuration changes to field equipment shall be versioned, reviewed, and tested in a nonoperational environment before being promoted into the seasonal baseline. @S245 */ subject s : FieldEquipment; }
    requirement def R78 { doc /* At the end of each fire season, the governance board shall compare system performance, operational workload, maintenance burden, and user feedback against the acceptance criteria approved for that season. @S246 */ subject s : DeploymentGovernanceBoard; }
    requirement def R79 { doc /* The resulting improvement plan shall define which procedures, training materials, interfaces, algorithms, and support arrangements will be revised before the next seasonal readiness campaign begins. @S247 */ subject s : ImprovementPlan; }
}
